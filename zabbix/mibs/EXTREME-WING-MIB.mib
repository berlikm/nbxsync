--
-- EXTREME-WING-MIB.my
-- MIB generated by MG-SOFT Visual MIB Builder Version 6.0  Build 88
-- Tuesday, November 29, 2011 at 14:31:15
--

	EXTREME-WING-MIB DEFINITIONS ::= BEGIN
 
		IMPORTS
			OBJECT-GROUP, MODULE-COMPLIANCE, NOTIFICATION-GROUP			
				FROM SNMPv2-CONF			
			Integer32, Unsigned32, Counter32, Counter64, 
			OBJECT-TYPE, MODULE-IDENTITY, OBJECT-IDENTITY, NOTIFICATION-TYPE			
				FROM SNMPv2-SMI			
			DisplayString, MacAddress, TruthValue, RowStatus			
				FROM SNMPv2-TC			
			wirelessProducts		
				FROM EXTREME-BASE-MIB;
	
		-- 1.3.6.1.4.1.1916.2.131.50
		extremeWingMIB MODULE-IDENTITY 
			LAST-UPDATED "201109210447Z"            -- August 23, 2011 at 00:25 GMT
			ORGANIZATION 
				"Extreme Networks"
			CONTACT-INFO 
				"Extreme Networks"
			DESCRIPTION 
				"WiNG MIB"
			REVISION "201109211647Z"		-- September 21, 2011 at 16:47 GMT
			DESCRIPTION 
				"Added l2tpv3-tunnel-policy Table"
			REVISION "201108231224Z"		-- August 23, 2011 at 12:24 GMT
			DESCRIPTION 
				"Implemented extremeWingCfgProfDynRoute and extremeWingCfgDevDynRoute Groups."
			REVISION "201107291725Z"		-- July 29, 2011 at 17:25 GMT
			DESCRIPTION 
				"Fixed OID mapping in extremeWingStatsDevWlApDetectTable."
			REVISION "201107291340Z"		-- July 29, 2011 at 13:40 GMT
			DESCRIPTION 
				"Added extremeWingActionDisassociateClient group"
			REVISION "201107251654Z"		-- July 25, 2011 at 16:54 GMT
			DESCRIPTION 
				"Added extremeWingStatsDevWlApDetectTable and cleaned tables below ."
			REVISION "201107251312Z"		-- July 25, 2011 at 13:12 GMT
			DESCRIPTION 
				"Changed the Description of Configuration Checksum as per reviewer comments."
			REVISION "201107251140Z"		-- July 25, 2011 at 11:40 GMT
			DESCRIPTION 
				"Added Configuration Checksum Action group with In and Out subgroups"
			REVISION "201107191736Z"		-- July 19, 2011 at 17:36 GMT
			DESCRIPTION 
				"Added Adopted AP IP Address fiels in extremeWingStatsRfdWlApInfoTable"
			REVISION "201107191448Z"		-- July 19, 2011 at 14:48 GMT
			DESCRIPTION 
				"Added txRetriedBytes for ClientStatDetail and RadioStatDetail"
			REVISION "201103211357Z"		-- March 21, 2011 at 13:57 GMT
			DESCRIPTION 
				"01a05
				Corrected description of objects."
			REVISION "201102091502Z"		-- February 09, 2011 at 15:02 GMT
			DESCRIPTION 
				"01a04
				Added tables under extremeWingStats for 5.1 release."
			REVISION "201009271513Z"		-- September 27, 2010 at 15:13 GMT
			DESCRIPTION 
				"01a03
				Added system object identifier for AP4700."
			REVISION "201008041549Z"		-- August 04, 2010 at 15:49 GMT
			DESCRIPTION 
				"01a02
				Added system object identifiers for AP4511 and AP4021."
			REVISION "201002031404Z"		-- February 03, 2010 at 14:04 GMT
			DESCRIPTION 
				"01a01
				Initial revision"
			::= { wirelessProducts 50 }

		
	
--
-- Type definitions
--
	
-- pattern "[0-9a-zA-Z]([0-9a-zA-Z\-_ ]*[0-9a-zA-Z])?"
		ExtremeWingIdentifier ::= OCTET STRING (SIZE (1..96))

-- This datatype always means that the MIB variable is
-- a simple ENUM that when written to 'doActionRightNow', 
-- causes the described action to take place, (much like 
-- a button pressed in a UI).
-- 
-- Such a value does NOT remain in state 'doActionRightNow'
-- while the operation is in-process, but instead when read 
-- always returns 'idleState'.
		ExtremeWingDoActionNow ::= INTEGER
			{
			doActionRightNow(1),
			idleState(2)
			}

	
	
--
-- Node definitions
--
	
		-- 1.3.6.1.4.1.1916.2.131.50.0
		extremeWingNotifications OBJECT IDENTIFIER ::= { extremeWingMIB 0 }

		
		-- 1.3.6.1.4.1.1916.2.131.50.0.1
		extremeWingTrapGeneric NOTIFICATION-TYPE
			OBJECTS { extremeWingEventMnemonic, extremeWingEventModule, extremeWingEventSeverity, extremeWingEventMsg, extremeWingEventSourceAddr, 
				extremeWingEventSourceHostname }
			STATUS current
			DESCRIPTION 
				"Generic WiNG Trap"
			::= { extremeWingNotifications 1 }


--AAA/Radius module
		--1.3.6.1.4.1.1916.2.131.50.0.2
		extremeWingTrapsAaa OBJECT IDENTIFIER ::= { extremeWingNotifications 2 }


		--1.3.6.1.4.1.1916.2.131.50.0.2.0
		extremeWingTrapsAaaPrefix OBJECT IDENTIFIER ::= { extremeWingTrapsAaa 0 }


		-- 1.3.6.1.4.1.1916.2.131.50.0.2.0.1
		extremeWingTrapAaaRadiusDisconMsg NOTIFICATION-TYPE
			OBJECTS { extremeWingEventMnemonic, extremeWingEventModule, extremeWingEventSeverity, extremeWingEventMsg, extremeWingEventSourceAddr,
				extremeWingEventSourceHostname }
			STATUS current
			DESCRIPTION
				"Received radius disconnect request"
				::= { extremeWingTrapsAaaPrefix 1}


		-- 1.3.6.1.4.1.1916.2.131.50.0.2.0.2
		extremeWingTrapAaaRadiusVlanUpdate NOTIFICATION-TYPE
			OBJECTS { extremeWingEventMnemonic, extremeWingEventModule, extremeWingEventSeverity, extremeWingEventMsg, extremeWingEventSourceAddr,
				extremeWingEventSourceHostname }
			STATUS current
			DESCRIPTION
				"Client vlan updated by radius"
				::= { extremeWingTrapsAaaPrefix 2}


		-- 1.3.6.1.4.1.1916.2.131.50.0.2.0.3
		extremeWingTrapAaaRadiusSessionNotStarted NOTIFICATION-TYPE
			OBJECTS { extremeWingEventMnemonic, extremeWingEventModule, extremeWingEventSeverity, extremeWingEventMsg, extremeWingEventSourceAddr,
				extremeWingEventSourceHostname }
			STATUS current
			DESCRIPTION
				"Start-time from Radius not yet valid"
				::= { extremeWingTrapsAaaPrefix 3}


		-- 1.3.6.1.4.1.1916.2.131.50.0.2.0.4
		extremeWingTrapAaaRadiusSessionExpired NOTIFICATION-TYPE
			OBJECTS { extremeWingEventMnemonic, extremeWingEventModule, extremeWingEventSeverity, extremeWingEventMsg, extremeWingEventSourceAddr,
				extremeWingEventSourceHostname }
			STATUS current
			DESCRIPTION
				"Session-time from Radius already expired"
				::= { extremeWingTrapsAaaPrefix 4}


--adv-wips module
		--1.3.6.1.4.1.1916.2.131.50.0.3
		extremeWingTrapsAdvWips OBJECT IDENTIFIER ::= { extremeWingNotifications 3 }


		--1.3.6.1.4.1.1916.2.131.50.0.3.0
		extremeWingTrapsAdvWipsPrefix OBJECT IDENTIFIER ::= { extremeWingTrapsAdvWips 0 }


		-- 1.3.6.1.4.1.1916.2.131.50.0.3.0.1
		extremeWingTrapAdvWipsAdvWipsEvent1 NOTIFICATION-TYPE
			OBJECTS { extremeWingEventMnemonic, extremeWingEventModule, extremeWingEventSeverity, extremeWingEventMsg, extremeWingEventSourceAddr,
				extremeWingEventSourceHostname }
			STATUS current
			DESCRIPTION
				"DoS Deauthentication attack "
				::= { extremeWingTrapsAdvWipsPrefix 1}


		-- 1.3.6.1.4.1.1916.2.131.50.0.3.0.2
		extremeWingTrapAdvWipsAdvWipsEvent2 NOTIFICATION-TYPE
			OBJECTS { extremeWingEventMnemonic, extremeWingEventModule, extremeWingEventSeverity, extremeWingEventMsg, extremeWingEventSourceAddr,
				extremeWingEventSourceHostname }
			STATUS current
			DESCRIPTION
				"DoS Disassociation attack "
				::= { extremeWingTrapsAdvWipsPrefix 2}


		-- 1.3.6.1.4.1.1916.2.131.50.0.3.0.3
		extremeWingTrapAdvWipsAdvWipsEvent3 NOTIFICATION-TYPE
			OBJECTS { extremeWingEventMnemonic, extremeWingEventModule, extremeWingEventSeverity, extremeWingEventMsg, extremeWingEventSourceAddr,
				extremeWingEventSourceHostname }
			STATUS current
			DESCRIPTION
				"EAP failure spoof attack "
				::= { extremeWingTrapsAdvWipsPrefix 3}


		-- 1.3.6.1.4.1.1916.2.131.50.0.3.0.4
		extremeWingTrapAdvWipsAdvWipsEvent10 NOTIFICATION-TYPE
			OBJECTS { extremeWingEventMnemonic, extremeWingEventModule, extremeWingEventSeverity, extremeWingEventMsg, extremeWingEventSourceAddr,
				extremeWingEventSourceHostname }
			STATUS current
			DESCRIPTION
				"ID-Theft out of sequence attack "
				::= { extremeWingTrapsAdvWipsPrefix 4}


		-- 1.3.6.1.4.1.1916.2.131.50.0.3.0.5
		extremeWingTrapAdvWipsAdvWipsEvent11 NOTIFICATION-TYPE
			OBJECTS { extremeWingEventMnemonic, extremeWingEventModule, extremeWingEventSeverity, extremeWingEventMsg, extremeWingEventSourceAddr,
				extremeWingEventSourceHostname }
			STATUS current
			DESCRIPTION
				"Possible ID-Theft EAPoL Success spoof attack "
				::= { extremeWingTrapsAdvWipsPrefix 5}


		-- 1.3.6.1.4.1.1916.2.131.50.0.3.0.6
		extremeWingTrapAdvWipsAdvWipsEvent12 NOTIFICATION-TYPE
			OBJECTS { extremeWingEventMnemonic, extremeWingEventModule, extremeWingEventSeverity, extremeWingEventMsg, extremeWingEventSourceAddr,
				extremeWingEventSourceHostname }
			STATUS current
			DESCRIPTION
				"Possible WLAN-Jack attack "
				::= { extremeWingTrapsAdvWipsPrefix 6}


		-- 1.3.6.1.4.1.1916.2.131.50.0.3.0.7
		extremeWingTrapAdvWipsAdvWipsEvent13 NOTIFICATION-TYPE
			OBJECTS { extremeWingEventMnemonic, extremeWingEventModule, extremeWingEventSeverity, extremeWingEventMsg, extremeWingEventSourceAddr,
				extremeWingEventSourceHostname }
			STATUS current
			DESCRIPTION
				"Possible ESSID-Jack attack "
				::= { extremeWingTrapsAdvWipsPrefix 7}


		-- 1.3.6.1.4.1.1916.2.131.50.0.3.0.8
		extremeWingTrapAdvWipsAdvWipsEvent14 NOTIFICATION-TYPE
			OBJECTS { extremeWingEventMnemonic, extremeWingEventModule, extremeWingEventSeverity, extremeWingEventMsg, extremeWingEventSourceAddr,
				extremeWingEventSourceHostname }
			STATUS current
			DESCRIPTION
				"Possible Monkey-Jack attack "
				::= { extremeWingTrapsAdvWipsPrefix 8}


		-- 1.3.6.1.4.1.1916.2.131.50.0.3.0.9
		extremeWingTrapAdvWipsAdvWipsEvent16 NOTIFICATION-TYPE
			OBJECTS { extremeWingEventMnemonic, extremeWingEventModule, extremeWingEventSeverity, extremeWingEventMsg, extremeWingEventSourceAddr,
				extremeWingEventSourceHostname }
			STATUS current
			DESCRIPTION
				"Possible NULL Probe Response attack "
				::= { extremeWingTrapsAdvWipsPrefix 9}


		-- 1.3.6.1.4.1.1916.2.131.50.0.3.0.10
		extremeWingTrapAdvWipsAdvWipsEvent19 NOTIFICATION-TYPE
			OBJECTS { extremeWingEventMnemonic, extremeWingEventModule, extremeWingEventSeverity, extremeWingEventMsg, extremeWingEventSourceAddr,
				extremeWingEventSourceHostname }
			STATUS current
			DESCRIPTION
				"DoS EAPoL Logoff storm attack "
				::= { extremeWingTrapsAdvWipsPrefix 10}


		-- 1.3.6.1.4.1.1916.2.131.50.0.3.0.11
		extremeWingTrapAdvWipsAdvWipsEvent21 NOTIFICATION-TYPE
			OBJECTS { extremeWingEventMnemonic, extremeWingEventModule, extremeWingEventSeverity, extremeWingEventMsg, extremeWingEventSourceAddr,
				extremeWingEventSourceHostname }
			STATUS current
			DESCRIPTION
				"DoS CTS flood attack "
				::= { extremeWingTrapsAdvWipsPrefix 11}


		-- 1.3.6.1.4.1.1916.2.131.50.0.3.0.12
		extremeWingTrapAdvWipsAdvWipsEvent25 NOTIFICATION-TYPE
			OBJECTS { extremeWingEventMnemonic, extremeWingEventModule, extremeWingEventSeverity, extremeWingEventMsg, extremeWingEventSourceAddr,
				extremeWingEventSourceHostname }
			STATUS current
			DESCRIPTION
				"Possible FATA-Jack attack "
				::= { extremeWingTrapsAdvWipsPrefix 12}


		-- 1.3.6.1.4.1.1916.2.131.50.0.3.0.13
		extremeWingTrapAdvWipsAdvWipsEvent29 NOTIFICATION-TYPE
			OBJECTS { extremeWingEventMnemonic, extremeWingEventModule, extremeWingEventSeverity, extremeWingEventMsg, extremeWingEventSourceAddr,
				extremeWingEventSourceHostname }
			STATUS current
			DESCRIPTION
				"Possible Fake DHCP server "
				::= { extremeWingTrapsAdvWipsPrefix 13}


		-- 1.3.6.1.4.1.1916.2.131.50.0.3.0.14
		extremeWingTrapAdvWipsAdvWipsEvent47 NOTIFICATION-TYPE
			OBJECTS { extremeWingEventMnemonic, extremeWingEventModule, extremeWingEventSeverity, extremeWingEventMsg, extremeWingEventSourceAddr,
				extremeWingEventSourceHostname }
			STATUS current
			DESCRIPTION
				"Crackable WEP IV used  "
				::= { extremeWingTrapsAdvWipsPrefix 14}


		-- 1.3.6.1.4.1.1916.2.131.50.0.3.0.15
		extremeWingTrapAdvWipsAdvWipsEvent87 NOTIFICATION-TYPE
			OBJECTS { extremeWingEventMnemonic, extremeWingEventModule, extremeWingEventSeverity, extremeWingEventMsg, extremeWingEventSourceAddr,
				extremeWingEventSourceHostname }
			STATUS current
			DESCRIPTION
				"Rogue-AP on wired network "
				::= { extremeWingTrapsAdvWipsPrefix 15}


		-- 1.3.6.1.4.1.1916.2.131.50.0.3.0.16
		extremeWingTrapAdvWipsAdvWipsEvent105 NOTIFICATION-TYPE
			OBJECTS { extremeWingEventMnemonic, extremeWingEventModule, extremeWingEventSeverity, extremeWingEventMsg, extremeWingEventSourceAddr,
				extremeWingEventSourceHostname }
			STATUS current
			DESCRIPTION
				"Sanctioned MU detected associated with unsanctioned/neighboring AP"
				::= { extremeWingTrapsAdvWipsPrefix 16}


		-- 1.3.6.1.4.1.1916.2.131.50.0.3.0.17
		extremeWingTrapAdvWipsAdvWipsEvent109 NOTIFICATION-TYPE
			OBJECTS { extremeWingEventMnemonic, extremeWingEventModule, extremeWingEventSeverity, extremeWingEventMsg, extremeWingEventSourceAddr,
				extremeWingEventSourceHostname }
			STATUS current
			DESCRIPTION
				"Multicast all systems traffic"
				::= { extremeWingTrapsAdvWipsPrefix 17}


		-- 1.3.6.1.4.1.1916.2.131.50.0.3.0.18
		extremeWingTrapAdvWipsAdvWipsEvent110 NOTIFICATION-TYPE
			OBJECTS { extremeWingEventMnemonic, extremeWingEventModule, extremeWingEventSeverity, extremeWingEventMsg, extremeWingEventSourceAddr,
				extremeWingEventSourceHostname }
			STATUS current
			DESCRIPTION
				"Multicast all routers traffic "
				::= { extremeWingTrapsAdvWipsPrefix 18}


		-- 1.3.6.1.4.1.1916.2.131.50.0.3.0.19
		extremeWingTrapAdvWipsAdvWipsEvent111 NOTIFICATION-TYPE
			OBJECTS { extremeWingEventMnemonic, extremeWingEventModule, extremeWingEventSeverity, extremeWingEventMsg, extremeWingEventSourceAddr,
				extremeWingEventSourceHostname }
			STATUS current
			DESCRIPTION
				"Multicast OSPF all traffic "
				::= { extremeWingTrapsAdvWipsPrefix 19}


		-- 1.3.6.1.4.1.1916.2.131.50.0.3.0.20
		extremeWingTrapAdvWipsAdvWipsEvent112 NOTIFICATION-TYPE
			OBJECTS { extremeWingEventMnemonic, extremeWingEventModule, extremeWingEventSeverity, extremeWingEventMsg, extremeWingEventSourceAddr,
				extremeWingEventSourceHostname }
			STATUS current
			DESCRIPTION
				"Multicast OSPF Deisgnated Routers traffic "
				::= { extremeWingTrapsAdvWipsPrefix 20}


		-- 1.3.6.1.4.1.1916.2.131.50.0.3.0.21
		extremeWingTrapAdvWipsAdvWipsEvent113 NOTIFICATION-TYPE
			OBJECTS { extremeWingEventMnemonic, extremeWingEventModule, extremeWingEventSeverity, extremeWingEventMsg, extremeWingEventSourceAddr,
				extremeWingEventSourceHostname }
			STATUS current
			DESCRIPTION
				"Multicast RIP-2 Routers traffic "
				::= { extremeWingTrapsAdvWipsPrefix 21}


		-- 1.3.6.1.4.1.1916.2.131.50.0.3.0.22
		extremeWingTrapAdvWipsAdvWipsEvent114 NOTIFICATION-TYPE
			OBJECTS { extremeWingEventMnemonic, extremeWingEventModule, extremeWingEventSeverity, extremeWingEventMsg, extremeWingEventSourceAddr,
				extremeWingEventSourceHostname }
			STATUS current
			DESCRIPTION
				"Multicast IGRP Routers traffic "
				::= { extremeWingTrapsAdvWipsPrefix 22}


		-- 1.3.6.1.4.1.1916.2.131.50.0.3.0.23
		extremeWingTrapAdvWipsAdvWipsEvent115 NOTIFICATION-TYPE
			OBJECTS { extremeWingEventMnemonic, extremeWingEventModule, extremeWingEventSeverity, extremeWingEventMsg, extremeWingEventSourceAddr,
				extremeWingEventSourceHostname }
			STATUS current
			DESCRIPTION
				"Multicast DHCP Server Relay Agent traffic "
				::= { extremeWingTrapsAdvWipsPrefix 23}


		-- 1.3.6.1.4.1.1916.2.131.50.0.3.0.24
		extremeWingTrapAdvWipsAdvWipsEvent116 NOTIFICATION-TYPE
			OBJECTS { extremeWingEventMnemonic, extremeWingEventModule, extremeWingEventSeverity, extremeWingEventMsg, extremeWingEventSourceAddr,
				extremeWingEventSourceHostname }
			STATUS current
			DESCRIPTION
				"Multicast VRRP Agent traffic "
				::= { extremeWingTrapsAdvWipsPrefix 24}


		-- 1.3.6.1.4.1.1916.2.131.50.0.3.0.25
		extremeWingTrapAdvWipsAdvWipsEvent117 NOTIFICATION-TYPE
			OBJECTS { extremeWingEventMnemonic, extremeWingEventModule, extremeWingEventSeverity, extremeWingEventMsg, extremeWingEventSourceAddr,
				extremeWingEventSourceHostname }
			STATUS current
			DESCRIPTION
				"Multicast HSRP Agent traffic "
				::= { extremeWingTrapsAdvWipsPrefix 25}


		-- 1.3.6.1.4.1.1916.2.131.50.0.3.0.26
		extremeWingTrapAdvWipsAdvWipsEvent118 NOTIFICATION-TYPE
			OBJECTS { extremeWingEventMnemonic, extremeWingEventModule, extremeWingEventSeverity, extremeWingEventMsg, extremeWingEventSourceAddr,
				extremeWingEventSourceHostname }
			STATUS current
			DESCRIPTION
				"Multicast IGMP traffic "
				::= { extremeWingTrapsAdvWipsPrefix 26}


		-- 1.3.6.1.4.1.1916.2.131.50.0.3.0.27
		extremeWingTrapAdvWipsAdvWipsEvent119 NOTIFICATION-TYPE
			OBJECTS { extremeWingEventMnemonic, extremeWingEventModule, extremeWingEventSeverity, extremeWingEventMsg, extremeWingEventSourceAddr,
				extremeWingEventSourceHostname }
			STATUS current
			DESCRIPTION
				"Detected NETBIOS traffic "
				::= { extremeWingTrapsAdvWipsPrefix 27}


		-- 1.3.6.1.4.1.1916.2.131.50.0.3.0.28
		extremeWingTrapAdvWipsAdvWipsEvent120 NOTIFICATION-TYPE
			OBJECTS { extremeWingEventMnemonic, extremeWingEventModule, extremeWingEventSeverity, extremeWingEventMsg, extremeWingEventSourceAddr,
				extremeWingEventSourceHostname }
			STATUS current
			DESCRIPTION
				"Detected STP traffic "
				::= { extremeWingTrapsAdvWipsPrefix 28}


		-- 1.3.6.1.4.1.1916.2.131.50.0.3.0.29
		extremeWingTrapAdvWipsAdvWipsEvent121 NOTIFICATION-TYPE
			OBJECTS { extremeWingEventMnemonic, extremeWingEventModule, extremeWingEventSeverity, extremeWingEventMsg, extremeWingEventSourceAddr,
				extremeWingEventSourceHostname }
			STATUS current
			DESCRIPTION
				"Detected IPX traffic "
				::= { extremeWingTrapsAdvWipsPrefix 29}


		-- 1.3.6.1.4.1.1916.2.131.50.0.3.0.30
		extremeWingTrapAdvWipsAdvWipsEvent142 NOTIFICATION-TYPE
			OBJECTS { extremeWingEventMnemonic, extremeWingEventModule, extremeWingEventSeverity, extremeWingEventMsg, extremeWingEventSourceAddr,
				extremeWingEventSourceHostname }
			STATUS current
			DESCRIPTION
				"Possible Probe Response attack "
				::= { extremeWingTrapsAdvWipsPrefix 30}


		-- 1.3.6.1.4.1.1916.2.131.50.0.3.0.31
		extremeWingTrapAdvWipsAdvWipsEvent221 NOTIFICATION-TYPE
			OBJECTS { extremeWingEventMnemonic, extremeWingEventModule, extremeWingEventSeverity, extremeWingEventMsg, extremeWingEventSourceAddr,
				extremeWingEventSourceHostname }
			STATUS current
			DESCRIPTION
				"Invalid Management Frames "
				::= { extremeWingTrapsAdvWipsPrefix 31}


		-- 1.3.6.1.4.1.1916.2.131.50.0.3.0.32
		extremeWingTrapAdvWipsAdvWipsEvent222 NOTIFICATION-TYPE
			OBJECTS { extremeWingEventMnemonic, extremeWingEventModule, extremeWingEventSeverity, extremeWingEventMsg, extremeWingEventSourceAddr,
				extremeWingEventSourceHostname }
			STATUS current
			DESCRIPTION
				"Invalid Channel Advertisement "
				::= { extremeWingTrapsAdvWipsPrefix 32}


		-- 1.3.6.1.4.1.1916.2.131.50.0.3.0.33
		extremeWingTrapAdvWipsAdvWipsEvent63 NOTIFICATION-TYPE
			OBJECTS { extremeWingEventMnemonic, extremeWingEventModule, extremeWingEventSeverity, extremeWingEventMsg, extremeWingEventSourceAddr,
				extremeWingEventSourceHostname }
			STATUS current
			DESCRIPTION
				"Windows ZERO Configuration Memory Leak "
				::= { extremeWingTrapsAdvWipsPrefix 33}


		-- 1.3.6.1.4.1.1916.2.131.50.0.3.0.34
		extremeWingTrapAdvWipsAdvWipsEvent26 NOTIFICATION-TYPE
			OBJECTS { extremeWingEventMnemonic, extremeWingEventModule, extremeWingEventSeverity, extremeWingEventMsg, extremeWingEventSourceAddr,
				extremeWingEventSourceHostname }
			STATUS current
			DESCRIPTION
				"DoS RTS flood attack "
				::= { extremeWingTrapsAdvWipsPrefix 34}


		-- 1.3.6.1.4.1.1916.2.131.50.0.3.0.35
		extremeWingTrapAdvWipsAdvWipsEvent220 NOTIFICATION-TYPE
			OBJECTS { extremeWingEventMnemonic, extremeWingEventModule, extremeWingEventSeverity, extremeWingEventMsg, extremeWingEventSourceAddr,
				extremeWingEventSourceHostname }
			STATUS current
			DESCRIPTION
				"Unauthorized Bridge "
				::= { extremeWingTrapsAdvWipsPrefix 35}


--Access point module
		--1.3.6.1.4.1.1916.2.131.50.0.4
		extremeWingTrapsAp OBJECT IDENTIFIER ::= { extremeWingNotifications 4 }


		--1.3.6.1.4.1.1916.2.131.50.0.4.0
		extremeWingTrapsApPrefix OBJECT IDENTIFIER ::= { extremeWingTrapsAp 0 }


		-- 1.3.6.1.4.1.1916.2.131.50.0.4.0.1
		extremeWingTrapApAdopted NOTIFICATION-TYPE
			OBJECTS { extremeWingEventMnemonic, extremeWingEventModule, extremeWingEventSeverity, extremeWingEventMsg, extremeWingEventSourceAddr,
				extremeWingEventSourceHostname }
			STATUS current
			DESCRIPTION
				"Access point adopted"
				::= { extremeWingTrapsApPrefix 1}


		-- 1.3.6.1.4.1.1916.2.131.50.0.4.0.2
		extremeWingTrapApUnadopted NOTIFICATION-TYPE
			OBJECTS { extremeWingEventMnemonic, extremeWingEventModule, extremeWingEventSeverity, extremeWingEventMsg, extremeWingEventSourceAddr,
				extremeWingEventSourceHostname }
			STATUS current
			DESCRIPTION
				"Access point unadopted"
				::= { extremeWingTrapsApPrefix 2}


		-- 1.3.6.1.4.1.1916.2.131.50.0.4.0.3
		extremeWingTrapApAdoptedToController NOTIFICATION-TYPE
			OBJECTS { extremeWingEventMnemonic, extremeWingEventModule, extremeWingEventSeverity, extremeWingEventMsg, extremeWingEventSourceAddr,
				extremeWingEventSourceHostname }
			STATUS current
			DESCRIPTION
				"Access point adopted to controller"
				::= { extremeWingTrapsApPrefix 3}


		-- 1.3.6.1.4.1.1916.2.131.50.0.4.0.4
		extremeWingTrapApOnline NOTIFICATION-TYPE
			OBJECTS { extremeWingEventMnemonic, extremeWingEventModule, extremeWingEventSeverity, extremeWingEventMsg, extremeWingEventSourceAddr,
				extremeWingEventSourceHostname }
			STATUS current
			DESCRIPTION
				"Event online"
				::= { extremeWingTrapsApPrefix 4}


		-- 1.3.6.1.4.1.1916.2.131.50.0.4.0.5
		extremeWingTrapApOffline NOTIFICATION-TYPE
			OBJECTS { extremeWingEventMnemonic, extremeWingEventModule, extremeWingEventSeverity, extremeWingEventMsg, extremeWingEventSourceAddr,
				extremeWingEventSourceHostname }
			STATUS current
			DESCRIPTION
				"Adopted device is offline"
				::= { extremeWingTrapsApPrefix 5}


		-- 1.3.6.1.4.1.1916.2.131.50.0.4.0.6
		extremeWingTrapApReset NOTIFICATION-TYPE
			OBJECTS { extremeWingEventMnemonic, extremeWingEventModule, extremeWingEventSeverity, extremeWingEventMsg, extremeWingEventSourceAddr,
				extremeWingEventSourceHostname }
			STATUS current
			DESCRIPTION
				"Access point reset"
				::= { extremeWingTrapsApPrefix 6}


		-- 1.3.6.1.4.1.1916.2.131.50.0.4.0.7
		extremeWingTrapApAdoptionRedirected NOTIFICATION-TYPE
			OBJECTS { extremeWingEventMnemonic, extremeWingEventModule, extremeWingEventSeverity, extremeWingEventMsg, extremeWingEventSourceAddr,
				extremeWingEventSourceHostname }
			STATUS current
			DESCRIPTION
				"Access point redirected"
				::= { extremeWingTrapsApPrefix 7}


		-- 1.3.6.1.4.1.1916.2.131.50.0.4.0.8
		extremeWingTrapApSwConnLost NOTIFICATION-TYPE
			OBJECTS { extremeWingEventMnemonic, extremeWingEventModule, extremeWingEventSeverity, extremeWingEventMsg, extremeWingEventSourceAddr,
				extremeWingEventSourceHostname }
			STATUS current
			DESCRIPTION
				"controller connectivity lost"
				::= { extremeWingTrapsApPrefix 8}


		-- 1.3.6.1.4.1.1916.2.131.50.0.4.0.9
		extremeWingTrapApApAutoupTimeout NOTIFICATION-TYPE
			OBJECTS { extremeWingEventMnemonic, extremeWingEventModule, extremeWingEventSeverity, extremeWingEventMsg, extremeWingEventSourceAddr,
				extremeWingEventSourceHostname }
			STATUS current
			DESCRIPTION
				"Time out while trying to auto upgrade an AP"
				::= { extremeWingTrapsApPrefix 9}


		-- 1.3.6.1.4.1.1916.2.131.50.0.4.0.10
		extremeWingTrapApApAutoupReboot NOTIFICATION-TYPE
			OBJECTS { extremeWingEventMnemonic, extremeWingEventModule, extremeWingEventSeverity, extremeWingEventMsg, extremeWingEventSourceAddr,
				extremeWingEventSourceHostname }
			STATUS current
			DESCRIPTION
				"Rebooting AP after upgrade"
				::= { extremeWingTrapsApPrefix 10}


		-- 1.3.6.1.4.1.1916.2.131.50.0.4.0.11
		extremeWingTrapApApAutoupNoNeed NOTIFICATION-TYPE
			OBJECTS { extremeWingEventMnemonic, extremeWingEventModule, extremeWingEventSeverity, extremeWingEventMsg, extremeWingEventSourceAddr,
				extremeWingEventSourceHostname }
			STATUS current
			DESCRIPTION
				"Auto upgrade is not initiated"
				::= { extremeWingTrapsApPrefix 11}


		-- 1.3.6.1.4.1.1916.2.131.50.0.4.0.12
		extremeWingTrapApApAutoupNeeded NOTIFICATION-TYPE
			OBJECTS { extremeWingEventMnemonic, extremeWingEventModule, extremeWingEventSeverity, extremeWingEventMsg, extremeWingEventSourceAddr,
				extremeWingEventSourceHostname }
			STATUS current
			DESCRIPTION
				"Auto upgrade is initiated on the AP"
				::= { extremeWingTrapsApPrefix 12}


		-- 1.3.6.1.4.1.1916.2.131.50.0.4.0.13
		extremeWingTrapApApAutoupDone NOTIFICATION-TYPE
			OBJECTS { extremeWingEventMnemonic, extremeWingEventModule, extremeWingEventSeverity, extremeWingEventMsg, extremeWingEventSourceAddr,
				extremeWingEventSourceHostname }
			STATUS current
			DESCRIPTION
				"Autoupgrade successful"
				::= { extremeWingTrapsApPrefix 13}


		-- 1.3.6.1.4.1.1916.2.131.50.0.4.0.14
		extremeWingTrapApApAutoupFail NOTIFICATION-TYPE
			OBJECTS { extremeWingEventMnemonic, extremeWingEventModule, extremeWingEventSeverity, extremeWingEventMsg, extremeWingEventSourceAddr,
				extremeWingEventSourceHostname }
			STATUS current
			DESCRIPTION
				"Failed auto upgrade attempt "
				::= { extremeWingTrapsApPrefix 14}


		-- 1.3.6.1.4.1.1916.2.131.50.0.4.0.15
		extremeWingTrapApApAutoupVer NOTIFICATION-TYPE
			OBJECTS { extremeWingEventMnemonic, extremeWingEventModule, extremeWingEventSeverity, extremeWingEventMsg, extremeWingEventSourceAddr,
				extremeWingEventSourceHostname }
			STATUS current
			DESCRIPTION
				"Available AP firmware versions for auto upgrade"
				::= { extremeWingTrapsApPrefix 15}


		-- 1.3.6.1.4.1.1916.2.131.50.0.4.0.16
		extremeWingTrapApNoImageFile NOTIFICATION-TYPE
			OBJECTS { extremeWingEventMnemonic, extremeWingEventModule, extremeWingEventSeverity, extremeWingEventMsg, extremeWingEventSourceAddr,
				extremeWingEventSourceHostname }
			STATUS current
			DESCRIPTION
				"AP firmware not on controller"
				::= { extremeWingTrapsApPrefix 16}


		-- 1.3.6.1.4.1.1916.2.131.50.0.4.0.17
		extremeWingTrapApImageParseFailure NOTIFICATION-TYPE
			OBJECTS { extremeWingEventMnemonic, extremeWingEventModule, extremeWingEventSeverity, extremeWingEventMsg, extremeWingEventSourceAddr,
				extremeWingEventSourceHostname }
			STATUS current
			DESCRIPTION
				"Invalid AP firmware file"
				::= { extremeWingTrapsApPrefix 17}


		-- 1.3.6.1.4.1.1916.2.131.50.0.4.0.18
		extremeWingTrapApLegacyAutoUpdate NOTIFICATION-TYPE
			OBJECTS { extremeWingEventMnemonic, extremeWingEventModule, extremeWingEventSeverity, extremeWingEventMsg, extremeWingEventSourceAddr,
				extremeWingEventSourceHostname }
			STATUS current
			DESCRIPTION
				"Legacy AP updated"
				::= { extremeWingTrapsApPrefix 18}


		-- 1.3.6.1.4.1.1916.2.131.50.0.4.0.19
		extremeWingTrapApApAdopted NOTIFICATION-TYPE
			OBJECTS { extremeWingEventMnemonic, extremeWingEventModule, extremeWingEventSeverity, extremeWingEventMsg, extremeWingEventSourceAddr,
				extremeWingEventSourceHostname }
			STATUS current
			DESCRIPTION
				"Access port adopted"
				::= { extremeWingTrapsApPrefix 19}


		-- 1.3.6.1.4.1.1916.2.131.50.0.4.0.20
		extremeWingTrapApApUnadopted NOTIFICATION-TYPE
			OBJECTS { extremeWingEventMnemonic, extremeWingEventModule, extremeWingEventSeverity, extremeWingEventMsg, extremeWingEventSourceAddr,
				extremeWingEventSourceHostname }
			STATUS current
			DESCRIPTION
				"Access port unadopted"
				::= { extremeWingTrapsApPrefix 20}


		-- 1.3.6.1.4.1.1916.2.131.50.0.4.0.21
		extremeWingTrapApApResetDetected NOTIFICATION-TYPE
			OBJECTS { extremeWingEventMnemonic, extremeWingEventModule, extremeWingEventSeverity, extremeWingEventMsg, extremeWingEventSourceAddr,
				extremeWingEventSourceHostname }
			STATUS current
			DESCRIPTION
				"Access port reset detected"
				::= { extremeWingTrapsApPrefix 21}


		-- 1.3.6.1.4.1.1916.2.131.50.0.4.0.22
		extremeWingTrapApApResetRequest NOTIFICATION-TYPE
			OBJECTS { extremeWingEventMnemonic, extremeWingEventModule, extremeWingEventSeverity, extremeWingEventMsg, extremeWingEventSourceAddr,
				extremeWingEventSourceHostname }
			STATUS current
			DESCRIPTION
				"Access port user requested reset"
				::= { extremeWingTrapsApPrefix 22}


		-- 1.3.6.1.4.1.1916.2.131.50.0.4.0.23
		extremeWingTrapApApTimeout NOTIFICATION-TYPE
			OBJECTS { extremeWingEventMnemonic, extremeWingEventModule, extremeWingEventSeverity, extremeWingEventMsg, extremeWingEventSourceAddr,
				extremeWingEventSourceHostname }
			STATUS current
			DESCRIPTION
				"Access port timed out"
				::= { extremeWingTrapsApPrefix 23}


--Captive Portal
		--1.3.6.1.4.1.1916.2.131.50.0.5
		extremeWingTrapsCaptivePortal OBJECT IDENTIFIER ::= { extremeWingNotifications 5 }


		--1.3.6.1.4.1.1916.2.131.50.0.5.0
		extremeWingTrapsCaptivePortalPrefix OBJECT IDENTIFIER ::= { extremeWingTrapsCaptivePortal 0 }


		-- 1.3.6.1.4.1.1916.2.131.50.0.5.0.1
		extremeWingTrapCaptivePortalAuthSuccess NOTIFICATION-TYPE
			OBJECTS { extremeWingEventMnemonic, extremeWingEventModule, extremeWingEventSeverity, extremeWingEventMsg, extremeWingEventSourceAddr,
				extremeWingEventSourceHostname }
			STATUS current
			DESCRIPTION
				"Authentication sucess"
				::= { extremeWingTrapsCaptivePortalPrefix 1}


		-- 1.3.6.1.4.1.1916.2.131.50.0.5.0.2
		extremeWingTrapCaptivePortalAuthFailed NOTIFICATION-TYPE
			OBJECTS { extremeWingEventMnemonic, extremeWingEventModule, extremeWingEventSeverity, extremeWingEventMsg, extremeWingEventSourceAddr,
				extremeWingEventSourceHostname }
			STATUS current
			DESCRIPTION
				"Authentication failed"
				::= { extremeWingTrapsCaptivePortalPrefix 2}


		-- 1.3.6.1.4.1.1916.2.131.50.0.5.0.3
		extremeWingTrapCaptivePortalSessionTimeout NOTIFICATION-TYPE
			OBJECTS { extremeWingEventMnemonic, extremeWingEventModule, extremeWingEventSeverity, extremeWingEventMsg, extremeWingEventSourceAddr,
				extremeWingEventSourceHostname }
			STATUS current
			DESCRIPTION
				"Session timed out"
				::= { extremeWingTrapsCaptivePortalPrefix 3}


		-- 1.3.6.1.4.1.1916.2.131.50.0.5.0.4
		extremeWingTrapCaptivePortalClientDisconnect NOTIFICATION-TYPE
			OBJECTS { extremeWingEventMnemonic, extremeWingEventModule, extremeWingEventSeverity, extremeWingEventMsg, extremeWingEventSourceAddr,
				extremeWingEventSourceHostname }
			STATUS current
			DESCRIPTION
				"Client disconnected"
				::= { extremeWingTrapsCaptivePortalPrefix 4}


		-- 1.3.6.1.4.1.1916.2.131.50.0.5.0.5
		extremeWingTrapCaptivePortalPurgeClient NOTIFICATION-TYPE
			OBJECTS { extremeWingEventMnemonic, extremeWingEventModule, extremeWingEventSeverity, extremeWingEventMsg, extremeWingEventSourceAddr,
				extremeWingEventSourceHostname }
			STATUS current
			DESCRIPTION
				"Client purged"
				::= { extremeWingTrapsCaptivePortalPrefix 5}


		-- 1.3.6.1.4.1.1916.2.131.50.0.5.0.6
		extremeWingTrapCaptivePortalFlexLogAccess NOTIFICATION-TYPE
			OBJECTS { extremeWingEventMnemonic, extremeWingEventModule, extremeWingEventSeverity, extremeWingEventMsg, extremeWingEventSourceAddr,
				extremeWingEventSourceHostname }
			STATUS current
			DESCRIPTION
				"Flex-log access granted to client"
				::= { extremeWingTrapsCaptivePortalPrefix 6}


		-- 1.3.6.1.4.1.1916.2.131.50.0.5.0.7
		extremeWingTrapCaptivePortalInactivityTimeout NOTIFICATION-TYPE
			OBJECTS { extremeWingEventMnemonic, extremeWingEventModule, extremeWingEventSeverity, extremeWingEventMsg, extremeWingEventSourceAddr,
				extremeWingEventSourceHostname }
			STATUS current
			DESCRIPTION
				"Client timed out due to inactivity"
				::= { extremeWingTrapsCaptivePortalPrefix 7}


		-- 1.3.6.1.4.1.1916.2.131.50.0.5.0.8
		extremeWingTrapCaptivePortalAllowAccess NOTIFICATION-TYPE
			OBJECTS { extremeWingEventMnemonic, extremeWingEventModule, extremeWingEventSeverity, extremeWingEventMsg, extremeWingEventSourceAddr,
				extremeWingEventSourceHostname }
			STATUS current
			DESCRIPTION
				"Client allowed access"
				::= { extremeWingTrapsCaptivePortalPrefix 8}


		-- 1.3.6.1.4.1.1916.2.131.50.0.5.0.9
		extremeWingTrapCaptivePortalClientRemoved NOTIFICATION-TYPE
			OBJECTS { extremeWingEventMnemonic, extremeWingEventModule, extremeWingEventSeverity, extremeWingEventMsg, extremeWingEventSourceAddr,
				extremeWingEventSourceHostname }
			STATUS current
			DESCRIPTION
				"Client removed due to admin changes"
				::= { extremeWingTrapsCaptivePortalPrefix 9}


		-- 1.3.6.1.4.1.1916.2.131.50.0.5.0.10
		extremeWingTrapCaptivePortalPageCreFailed NOTIFICATION-TYPE
			OBJECTS { extremeWingEventMnemonic, extremeWingEventModule, extremeWingEventSeverity, extremeWingEventMsg, extremeWingEventSourceAddr,
				extremeWingEventSourceHostname }
			STATUS current
			DESCRIPTION
				"Page Creation failure"
				::= { extremeWingTrapsCaptivePortalPrefix 10}


		-- 1.3.6.1.4.1.1916.2.131.50.0.5.0.11
		extremeWingTrapCaptivePortalDataLimitExceed NOTIFICATION-TYPE
			OBJECTS { extremeWingEventMnemonic, extremeWingEventModule, extremeWingEventSeverity, extremeWingEventMsg, extremeWingEventSourceAddr,
				extremeWingEventSourceHostname }
			STATUS current
			DESCRIPTION
				"Client data limit exceed      "
				::= { extremeWingTrapsCaptivePortalPrefix 11}


		-- 1.3.6.1.4.1.1916.2.131.50.0.5.0.12
		extremeWingTrapCaptivePortalVlanSwitch NOTIFICATION-TYPE
			OBJECTS { extremeWingEventMnemonic, extremeWingEventModule, extremeWingEventSeverity, extremeWingEventMsg, extremeWingEventSourceAddr,
				extremeWingEventSourceHostname }
			STATUS current
			DESCRIPTION
				"Client vlan switch "
				::= { extremeWingTrapsCaptivePortalPrefix 12}


		-- 1.3.6.1.4.1.1916.2.131.50.0.5.0.13
		extremeWingTrapCaptivePortalServerMonitorStateChange NOTIFICATION-TYPE
			OBJECTS { extremeWingEventMnemonic, extremeWingEventModule, extremeWingEventSeverity, extremeWingEventMsg, extremeWingEventSourceAddr,
				extremeWingEventSourceHostname }
			STATUS current
			DESCRIPTION
				" CP server monitor state changes"
				::= { extremeWingTrapsCaptivePortalPrefix 13}


		-- 1.3.6.1.4.1.1916.2.131.50.0.5.0.14
		extremeWingTrapCaptivePortalNoServicePageSent NOTIFICATION-TYPE
			OBJECTS { extremeWingEventMnemonic, extremeWingEventModule, extremeWingEventSeverity, extremeWingEventMsg, extremeWingEventSourceAddr,
				extremeWingEventSourceHostname }
			STATUS current
			DESCRIPTION
				"no service page sent to the client"
				::= { extremeWingTrapsCaptivePortalPrefix 14}


--Certificate Manager (Not valid for NCAP/MCN)
		--1.3.6.1.4.1.1916.2.131.50.0.6
		extremeWingTrapsCertmgr OBJECT IDENTIFIER ::= { extremeWingNotifications 6 }


		--1.3.6.1.4.1.1916.2.131.50.0.6.0
		extremeWingTrapsCertmgrPrefix OBJECT IDENTIFIER ::= { extremeWingTrapsCertmgr 0 }


		-- 1.3.6.1.4.1.1916.2.131.50.0.6.0.1
		extremeWingTrapCertmgrRsaKeyActionsSuccess NOTIFICATION-TYPE
			OBJECTS { extremeWingEventMnemonic, extremeWingEventModule, extremeWingEventSeverity, extremeWingEventMsg, extremeWingEventSourceAddr,
				extremeWingEventSourceHostname }
			STATUS current
			DESCRIPTION
				"Successful completion of RSA key related actions (import, export, etc)"
				::= { extremeWingTrapsCertmgrPrefix 1}


		-- 1.3.6.1.4.1.1916.2.131.50.0.6.0.2
		extremeWingTrapCertmgrRsaKeyActionsFailure NOTIFICATION-TYPE
			OBJECTS { extremeWingEventMnemonic, extremeWingEventModule, extremeWingEventSeverity, extremeWingEventMsg, extremeWingEventSourceAddr,
				extremeWingEventSourceHostname }
			STATUS current
			DESCRIPTION
				"Failure of RSA key related actions (import, export, etc)"
				::= { extremeWingTrapsCertmgrPrefix 2}


		-- 1.3.6.1.4.1.1916.2.131.50.0.6.0.3
		extremeWingTrapCertmgrCaCertActionsSuccess NOTIFICATION-TYPE
			OBJECTS { extremeWingEventMnemonic, extremeWingEventModule, extremeWingEventSeverity, extremeWingEventMsg, extremeWingEventSourceAddr,
				extremeWingEventSourceHostname }
			STATUS current
			DESCRIPTION
				"Successful completion of CA certificate related actions (import, export, etc)"
				::= { extremeWingTrapsCertmgrPrefix 3}


		-- 1.3.6.1.4.1.1916.2.131.50.0.6.0.4
		extremeWingTrapCertmgrCaCertActionsFailure NOTIFICATION-TYPE
			OBJECTS { extremeWingEventMnemonic, extremeWingEventModule, extremeWingEventSeverity, extremeWingEventMsg, extremeWingEventSourceAddr,
				extremeWingEventSourceHostname }
			STATUS current
			DESCRIPTION
				"Failure of CA certificate actions (import, export, etc)"
				::= { extremeWingTrapsCertmgrPrefix 4}


		-- 1.3.6.1.4.1.1916.2.131.50.0.6.0.5
		extremeWingTrapCertmgrSrvCertActionsSuccess NOTIFICATION-TYPE
			OBJECTS { extremeWingEventMnemonic, extremeWingEventModule, extremeWingEventSeverity, extremeWingEventMsg, extremeWingEventSourceAddr,
				extremeWingEventSourceHostname }
			STATUS current
			DESCRIPTION
				"Successful completion of Server certificate actions (import, export, etc)"
				::= { extremeWingTrapsCertmgrPrefix 5}


		-- 1.3.6.1.4.1.1916.2.131.50.0.6.0.6
		extremeWingTrapCertmgrSvrCertActionsFailure NOTIFICATION-TYPE
			OBJECTS { extremeWingEventMnemonic, extremeWingEventModule, extremeWingEventSeverity, extremeWingEventMsg, extremeWingEventSourceAddr,
				extremeWingEventSourceHostname }
			STATUS current
			DESCRIPTION
				"Failure of Server certificate actions (import, export, etc)"
				::= { extremeWingTrapsCertmgrPrefix 6}


		-- 1.3.6.1.4.1.1916.2.131.50.0.6.0.7
		extremeWingTrapCertmgrCsrExportSuccess NOTIFICATION-TYPE
			OBJECTS { extremeWingEventMnemonic, extremeWingEventModule, extremeWingEventSeverity, extremeWingEventMsg, extremeWingEventSourceAddr,
				extremeWingEventSourceHostname }
			STATUS current
			DESCRIPTION
				"Successful export of Certificate Signing Request"
				::= { extremeWingTrapsCertmgrPrefix 7}


		-- 1.3.6.1.4.1.1916.2.131.50.0.6.0.8
		extremeWingTrapCertmgrCsrExportFailure NOTIFICATION-TYPE
			OBJECTS { extremeWingEventMnemonic, extremeWingEventModule, extremeWingEventSeverity, extremeWingEventMsg, extremeWingEventSourceAddr,
				extremeWingEventSourceHostname }
			STATUS current
			DESCRIPTION
				"Failed to export Certificate Signing Request"
				::= { extremeWingTrapsCertmgrPrefix 8}


		-- 1.3.6.1.4.1.1916.2.131.50.0.6.0.9
		extremeWingTrapCertmgrCrlActionsSuccess NOTIFICATION-TYPE
			OBJECTS { extremeWingEventMnemonic, extremeWingEventModule, extremeWingEventSeverity, extremeWingEventMsg, extremeWingEventSourceAddr,
				extremeWingEventSourceHostname }
			STATUS current
			DESCRIPTION
				"Successful completion of Certificate Revocation List actions"
				::= { extremeWingTrapsCertmgrPrefix 9}


		-- 1.3.6.1.4.1.1916.2.131.50.0.6.0.10
		extremeWingTrapCertmgrCrlActionsFailure NOTIFICATION-TYPE
			OBJECTS { extremeWingEventMnemonic, extremeWingEventModule, extremeWingEventSeverity, extremeWingEventMsg, extremeWingEventSourceAddr,
				extremeWingEventSourceHostname }
			STATUS current
			DESCRIPTION
				"Failure of Certificate Revocation List actions"
				::= { extremeWingTrapsCertmgrPrefix 10}


		-- 1.3.6.1.4.1.1916.2.131.50.0.6.0.11
		extremeWingTrapCertmgrDeleteTrustpointAction NOTIFICATION-TYPE
			OBJECTS { extremeWingEventMnemonic, extremeWingEventModule, extremeWingEventSeverity, extremeWingEventMsg, extremeWingEventSourceAddr,
				extremeWingEventSourceHostname }
			STATUS current
			DESCRIPTION
				"Deletion of Trustpoint"
				::= { extremeWingTrapsCertmgrPrefix 11}


		-- 1.3.6.1.4.1.1916.2.131.50.0.6.0.12
		extremeWingTrapCertmgrImportTrustpoint NOTIFICATION-TYPE
			OBJECTS { extremeWingEventMnemonic, extremeWingEventModule, extremeWingEventSeverity, extremeWingEventMsg, extremeWingEventSourceAddr,
				extremeWingEventSourceHostname }
			STATUS current
			DESCRIPTION
				"Import of Trustpoint"
				::= { extremeWingTrapsCertmgrPrefix 12}


		-- 1.3.6.1.4.1.1916.2.131.50.0.6.0.13
		extremeWingTrapCertmgrExportTrustpoint NOTIFICATION-TYPE
			OBJECTS { extremeWingEventMnemonic, extremeWingEventModule, extremeWingEventSeverity, extremeWingEventMsg, extremeWingEventSourceAddr,
				extremeWingEventSourceHostname }
			STATUS current
			DESCRIPTION
				"Export of Trustpoint"
				::= { extremeWingTrapsCertmgrPrefix 13}


		-- 1.3.6.1.4.1.1916.2.131.50.0.6.0.14
		extremeWingTrapCertmgrCertExpiry NOTIFICATION-TYPE
			OBJECTS { extremeWingEventMnemonic, extremeWingEventModule, extremeWingEventSeverity, extremeWingEventMsg, extremeWingEventSourceAddr,
				extremeWingEventSourceHostname }
			STATUS current
			DESCRIPTION
				"Certificate expiry"
				::= { extremeWingTrapsCertmgrPrefix 14}


		-- 1.3.6.1.4.1.1916.2.131.50.0.6.0.15
		extremeWingTrapCertmgrCaKeyActionsSuccess NOTIFICATION-TYPE
			OBJECTS { extremeWingEventMnemonic, extremeWingEventModule, extremeWingEventSeverity, extremeWingEventMsg, extremeWingEventSourceAddr,
				extremeWingEventSourceHostname }
			STATUS current
			DESCRIPTION
				"Successful completion of CA private key actions"
				::= { extremeWingTrapsCertmgrPrefix 15}


		-- 1.3.6.1.4.1.1916.2.131.50.0.6.0.16
		extremeWingTrapCertmgrCaKeyActionsFailure NOTIFICATION-TYPE
			OBJECTS { extremeWingEventMnemonic, extremeWingEventModule, extremeWingEventSeverity, extremeWingEventMsg, extremeWingEventSourceAddr,
				extremeWingEventSourceHostname }
			STATUS current
			DESCRIPTION
				"Failure of CA private key actions"
				::= { extremeWingTrapsCertmgrPrefix 16}


		-- 1.3.6.1.4.1.1916.2.131.50.0.6.0.17
		extremeWingTrapCertmgrTrustpointInvalidKeyLength NOTIFICATION-TYPE
			OBJECTS { extremeWingEventMnemonic, extremeWingEventModule, extremeWingEventSeverity, extremeWingEventMsg, extremeWingEventSourceAddr,
				extremeWingEventSourceHostname }
			STATUS current
			DESCRIPTION
				"Trustpoint using invalid key length"
				::= { extremeWingTrapsCertmgrPrefix 17}


--cfgd module
		--1.3.6.1.4.1.1916.2.131.50.0.7
		extremeWingTrapsCfgd OBJECT IDENTIFIER ::= { extremeWingNotifications 7 }


		--1.3.6.1.4.1.1916.2.131.50.0.7.0
		extremeWingTrapsCfgdPrefix OBJECT IDENTIFIER ::= { extremeWingTrapsCfgd 0 }


		-- 1.3.6.1.4.1.1916.2.131.50.0.7.0.1
		extremeWingTrapCfgdAclRuleAltered NOTIFICATION-TYPE
			OBJECTS { extremeWingEventMnemonic, extremeWingEventModule, extremeWingEventSeverity, extremeWingEventMsg, extremeWingEventSourceAddr,
				extremeWingEventSourceHostname }
			STATUS current
			DESCRIPTION
				"ACL rule altered"
				::= { extremeWingTrapsCfgdPrefix 1}


		-- 1.3.6.1.4.1.1916.2.131.50.0.7.0.2
		extremeWingTrapCfgdAclAttachedAltered NOTIFICATION-TYPE
			OBJECTS { extremeWingEventMnemonic, extremeWingEventModule, extremeWingEventSeverity, extremeWingEventMsg, extremeWingEventSourceAddr,
				extremeWingEventSourceHostname }
			STATUS current
			DESCRIPTION
				"ACL altered"
				::= { extremeWingTrapsCfgdPrefix 2}


--cluster module
		--1.3.6.1.4.1.1916.2.131.50.0.8
		extremeWingTrapsCluster OBJECT IDENTIFIER ::= { extremeWingNotifications 8 }


		--1.3.6.1.4.1.1916.2.131.50.0.8.0
		extremeWingTrapsClusterPrefix OBJECT IDENTIFIER ::= { extremeWingTrapsCluster 0 }


		-- 1.3.6.1.4.1.1916.2.131.50.0.8.0.1
		extremeWingTrapClusterCmasterCfgUpdateFail NOTIFICATION-TYPE
			OBJECTS { extremeWingEventMnemonic, extremeWingEventModule, extremeWingEventSeverity, extremeWingEventMsg, extremeWingEventSourceAddr,
				extremeWingEventSourceHostname }
			STATUS current
			DESCRIPTION
				"Cluster master config update failed"
				::= { extremeWingTrapsClusterPrefix 1}


		-- 1.3.6.1.4.1.1916.2.131.50.0.8.0.2
		extremeWingTrapClusterMaxExceeded NOTIFICATION-TYPE
			OBJECTS { extremeWingEventMnemonic, extremeWingEventModule, extremeWingEventSeverity, extremeWingEventMsg, extremeWingEventSourceAddr,
				extremeWingEventSourceHostname }
			STATUS current
			DESCRIPTION
				"Max cluster count exceeded"
				::= { extremeWingTrapsClusterPrefix 2}


		-- 1.3.6.1.4.1.1916.2.131.50.0.8.0.3
		extremeWingTrapClusterStateChange NOTIFICATION-TYPE
			OBJECTS { extremeWingEventMnemonic, extremeWingEventModule, extremeWingEventSeverity, extremeWingEventMsg, extremeWingEventSourceAddr,
				extremeWingEventSourceHostname }
			STATUS current
			DESCRIPTION
				"Event state-change"
				::= { extremeWingTrapsClusterPrefix 3}


--DHCP Configuration Daemon
		--1.3.6.1.4.1.1916.2.131.50.0.9
		extremeWingTrapsDhcpsvr OBJECT IDENTIFIER ::= { extremeWingNotifications 9 }


		--1.3.6.1.4.1.1916.2.131.50.0.9.0
		extremeWingTrapsDhcpsvrPrefix OBJECT IDENTIFIER ::= { extremeWingTrapsDhcpsvr 0 }


		-- 1.3.6.1.4.1.1916.2.131.50.0.9.0.1
		extremeWingTrapDhcpsvrRelayNoIface NOTIFICATION-TYPE
			OBJECTS { extremeWingEventMnemonic, extremeWingEventModule, extremeWingEventSeverity, extremeWingEventMsg, extremeWingEventSourceAddr,
				extremeWingEventSourceHostname }
			STATUS current
			DESCRIPTION
				"No interface for DHCP relay"
				::= { extremeWingTrapsDhcpsvrPrefix 1}


		-- 1.3.6.1.4.1.1916.2.131.50.0.9.0.2
		extremeWingTrapDhcpsvrRelayIfaceNoIp NOTIFICATION-TYPE
			OBJECTS { extremeWingEventMnemonic, extremeWingEventModule, extremeWingEventSeverity, extremeWingEventMsg, extremeWingEventSourceAddr,
				extremeWingEventSourceHostname }
			STATUS current
			DESCRIPTION
				"No IP address on DHCP relay interface"
				::= { extremeWingTrapsDhcpsvrPrefix 2}


		-- 1.3.6.1.4.1.1916.2.131.50.0.9.0.3
		extremeWingTrapDhcpsvrRelayStart NOTIFICATION-TYPE
			OBJECTS { extremeWingEventMnemonic, extremeWingEventModule, extremeWingEventSeverity, extremeWingEventMsg, extremeWingEventSourceAddr,
				extremeWingEventSourceHostname }
			STATUS current
			DESCRIPTION
				"DHCP relay agent started"
				::= { extremeWingTrapsDhcpsvrPrefix 3}


		-- 1.3.6.1.4.1.1916.2.131.50.0.9.0.4
		extremeWingTrapDhcpsvrRelayStop NOTIFICATION-TYPE
			OBJECTS { extremeWingEventMnemonic, extremeWingEventModule, extremeWingEventSeverity, extremeWingEventMsg, extremeWingEventSourceAddr,
				extremeWingEventSourceHostname }
			STATUS current
			DESCRIPTION
				"DHCP relay agent stopped"
				::= { extremeWingTrapsDhcpsvrPrefix 4}


		-- 1.3.6.1.4.1.1916.2.131.50.0.9.0.5
		extremeWingTrapDhcpsvrDhcpsvrStart NOTIFICATION-TYPE
			OBJECTS { extremeWingEventMnemonic, extremeWingEventModule, extremeWingEventSeverity, extremeWingEventMsg, extremeWingEventSourceAddr,
				extremeWingEventSourceHostname }
			STATUS current
			DESCRIPTION
				"DHCP server started"
				::= { extremeWingTrapsDhcpsvrPrefix 5}


		-- 1.3.6.1.4.1.1916.2.131.50.0.9.0.6
		extremeWingTrapDhcpsvrDhcpsvrStop NOTIFICATION-TYPE
			OBJECTS { extremeWingEventMnemonic, extremeWingEventModule, extremeWingEventSeverity, extremeWingEventMsg, extremeWingEventSourceAddr,
				extremeWingEventSourceHostname }
			STATUS current
			DESCRIPTION
				"DHCP server stopped"
				::= { extremeWingTrapsDhcpsvrPrefix 6}


--diag module
		--1.3.6.1.4.1.1916.2.131.50.0.10
		extremeWingTrapsDiag OBJECT IDENTIFIER ::= { extremeWingNotifications 10 }


		--1.3.6.1.4.1.1916.2.131.50.0.10.0
		extremeWingTrapsDiagPrefix OBJECT IDENTIFIER ::= { extremeWingTrapsDiag 0 }


		-- 1.3.6.1.4.1.1916.2.131.50.0.10.0.1
		extremeWingTrapDiagFanUnderspeed NOTIFICATION-TYPE
			OBJECTS { extremeWingEventMnemonic, extremeWingEventModule, extremeWingEventSeverity, extremeWingEventMsg, extremeWingEventSourceAddr,
				extremeWingEventSourceHostname }
			STATUS current
			DESCRIPTION
				"Event fan-underspeed"
				::= { extremeWingTrapsDiagPrefix 1}


		-- 1.3.6.1.4.1.1916.2.131.50.0.10.0.2
		extremeWingTrapDiagUnderVoltage NOTIFICATION-TYPE
			OBJECTS { extremeWingEventMnemonic, extremeWingEventModule, extremeWingEventSeverity, extremeWingEventMsg, extremeWingEventSourceAddr,
				extremeWingEventSourceHostname }
			STATUS current
			DESCRIPTION
				"Event under-voltage"
				::= { extremeWingTrapsDiagPrefix 2}


		-- 1.3.6.1.4.1.1916.2.131.50.0.10.0.3
		extremeWingTrapDiagOverVoltage NOTIFICATION-TYPE
			OBJECTS { extremeWingEventMnemonic, extremeWingEventModule, extremeWingEventSeverity, extremeWingEventMsg, extremeWingEventSourceAddr,
				extremeWingEventSourceHostname }
			STATUS current
			DESCRIPTION
				"Event over-voltage"
				::= { extremeWingTrapsDiagPrefix 3}


		-- 1.3.6.1.4.1.1916.2.131.50.0.10.0.4
		extremeWingTrapDiagLowTemp NOTIFICATION-TYPE
			OBJECTS { extremeWingEventMnemonic, extremeWingEventModule, extremeWingEventSeverity, extremeWingEventMsg, extremeWingEventSourceAddr,
				extremeWingEventSourceHostname }
			STATUS current
			DESCRIPTION
				"Event low-temp"
				::= { extremeWingTrapsDiagPrefix 4}


		-- 1.3.6.1.4.1.1916.2.131.50.0.10.0.5
		extremeWingTrapDiagHighTemp NOTIFICATION-TYPE
			OBJECTS { extremeWingEventMnemonic, extremeWingEventModule, extremeWingEventSeverity, extremeWingEventMsg, extremeWingEventSourceAddr,
				extremeWingEventSourceHostname }
			STATUS current
			DESCRIPTION
				"Event high-temp"
				::= { extremeWingTrapsDiagPrefix 5}


		-- 1.3.6.1.4.1.1916.2.131.50.0.10.0.6
		extremeWingTrapDiagOverTemp NOTIFICATION-TYPE
			OBJECTS { extremeWingEventMnemonic, extremeWingEventModule, extremeWingEventSeverity, extremeWingEventMsg, extremeWingEventSourceAddr,
				extremeWingEventSourceHostname }
			STATUS current
			DESCRIPTION
				"Event over-temp"
				::= { extremeWingTrapsDiagPrefix 6}


		-- 1.3.6.1.4.1.1916.2.131.50.0.10.0.7
		extremeWingTrapDiagWdStateChange NOTIFICATION-TYPE
			OBJECTS { extremeWingEventMnemonic, extremeWingEventModule, extremeWingEventSeverity, extremeWingEventMsg, extremeWingEventSourceAddr,
				extremeWingEventSourceHostname }
			STATUS current
			DESCRIPTION
				"Event wd-state-change"
				::= { extremeWingTrapsDiagPrefix 7}


		-- 1.3.6.1.4.1.1916.2.131.50.0.10.0.8
		extremeWingTrapDiagElapsedTime NOTIFICATION-TYPE
			OBJECTS { extremeWingEventMnemonic, extremeWingEventModule, extremeWingEventSeverity, extremeWingEventMsg, extremeWingEventSourceAddr,
				extremeWingEventSourceHostname }
			STATUS current
			DESCRIPTION
				"Event elapsed-time"
				::= { extremeWingTrapsDiagPrefix 8}


		-- 1.3.6.1.4.1.1916.2.131.50.0.10.0.9
		extremeWingTrapDiagAutogenTechSprt NOTIFICATION-TYPE
			OBJECTS { extremeWingEventMnemonic, extremeWingEventModule, extremeWingEventSeverity, extremeWingEventMsg, extremeWingEventSourceAddr,
				extremeWingEventSourceHostname }
			STATUS current
			DESCRIPTION
				"Event autogen-tech-sprt"
				::= { extremeWingTrapsDiagPrefix 9}


		-- 1.3.6.1.4.1.1916.2.131.50.0.10.0.10
		extremeWingTrapDiagPoeInitFail NOTIFICATION-TYPE
			OBJECTS { extremeWingEventMnemonic, extremeWingEventModule, extremeWingEventSeverity, extremeWingEventMsg, extremeWingEventSourceAddr,
				extremeWingEventSourceHostname }
			STATUS current
			DESCRIPTION
				"Event poe-init-fail"
				::= { extremeWingTrapsDiagPrefix 10}


		-- 1.3.6.1.4.1.1916.2.131.50.0.10.0.11
		extremeWingTrapDiagPoePowerLevel NOTIFICATION-TYPE
			OBJECTS { extremeWingEventMnemonic, extremeWingEventModule, extremeWingEventSeverity, extremeWingEventMsg, extremeWingEventSourceAddr,
				extremeWingEventSourceHostname }
			STATUS current
			DESCRIPTION
				"Event poe-power-level"
				::= { extremeWingTrapsDiagPrefix 11}


		-- 1.3.6.1.4.1.1916.2.131.50.0.10.0.12
		extremeWingTrapDiagPoeReadFail NOTIFICATION-TYPE
			OBJECTS { extremeWingEventMnemonic, extremeWingEventModule, extremeWingEventSeverity, extremeWingEventMsg, extremeWingEventSourceAddr,
				extremeWingEventSourceHostname }
			STATUS current
			DESCRIPTION
				"Event poe-read-fail"
				::= { extremeWingTrapsDiagPrefix 12}


		-- 1.3.6.1.4.1.1916.2.131.50.0.10.0.13
		extremeWingTrapDiagPoeStateChange NOTIFICATION-TYPE
			OBJECTS { extremeWingEventMnemonic, extremeWingEventModule, extremeWingEventSeverity, extremeWingEventMsg, extremeWingEventSourceAddr,
				extremeWingEventSourceHostname }
			STATUS current
			DESCRIPTION
				"Event poe-state-change"
				::= { extremeWingTrapsDiagPrefix 13}


		-- 1.3.6.1.4.1.1916.2.131.50.0.10.0.14
		extremeWingTrapDiagRaidDegraded NOTIFICATION-TYPE
			OBJECTS { extremeWingEventMnemonic, extremeWingEventModule, extremeWingEventSeverity, extremeWingEventMsg, extremeWingEventSourceAddr,
				extremeWingEventSourceHostname }
			STATUS current
			DESCRIPTION
				"Event raid-degraded"
				::= { extremeWingTrapsDiagPrefix 14}


		-- 1.3.6.1.4.1.1916.2.131.50.0.10.0.15
		extremeWingTrapDiagRaidError NOTIFICATION-TYPE
			OBJECTS { extremeWingEventMnemonic, extremeWingEventModule, extremeWingEventSeverity, extremeWingEventMsg, extremeWingEventSourceAddr,
				extremeWingEventSourceHostname }
			STATUS current
			DESCRIPTION
				"Event raid-error"
				::= { extremeWingTrapsDiagPrefix 15}


		-- 1.3.6.1.4.1.1916.2.131.50.0.10.0.16
		extremeWingTrapDiagPwrsplyFail NOTIFICATION-TYPE
			OBJECTS { extremeWingEventMnemonic, extremeWingEventModule, extremeWingEventSeverity, extremeWingEventMsg, extremeWingEventSourceAddr,
				extremeWingEventSourceHostname }
			STATUS current
			DESCRIPTION
				"Event pwrsply-fail"
				::= { extremeWingTrapsDiagPrefix 16}


		-- 1.3.6.1.4.1.1916.2.131.50.0.10.0.17
		extremeWingTrapDiagHddFailing NOTIFICATION-TYPE
			OBJECTS { extremeWingEventMnemonic, extremeWingEventModule, extremeWingEventSeverity, extremeWingEventMsg, extremeWingEventSourceAddr,
				extremeWingEventSourceHostname }
			STATUS current
			DESCRIPTION
				"Event hdd-failing"
				::= { extremeWingTrapsDiagPrefix 17}


		-- 1.3.6.1.4.1.1916.2.131.50.0.10.0.18
		extremeWingTrapDiagWdResetSys NOTIFICATION-TYPE
			OBJECTS { extremeWingEventMnemonic, extremeWingEventModule, extremeWingEventSeverity, extremeWingEventMsg, extremeWingEventSourceAddr,
				extremeWingEventSourceHostname }
			STATUS current
			DESCRIPTION
				"Event wd-reset-sys"
				::= { extremeWingTrapsDiagPrefix 18}


		-- 1.3.6.1.4.1.1916.2.131.50.0.10.0.19
		extremeWingTrapDiagCpuUsageTooHigh NOTIFICATION-TYPE
			OBJECTS { extremeWingEventMnemonic, extremeWingEventModule, extremeWingEventSeverity, extremeWingEventMsg, extremeWingEventSourceAddr,
				extremeWingEventSourceHostname }
			STATUS current
			DESCRIPTION
				"Event cpu-usage-too-high"
				::= { extremeWingTrapsDiagPrefix 19}


		-- 1.3.6.1.4.1.1916.2.131.50.0.10.0.20
		extremeWingTrapDiagCpuUsageTooHighRecover NOTIFICATION-TYPE
			OBJECTS { extremeWingEventMnemonic, extremeWingEventModule, extremeWingEventSeverity, extremeWingEventMsg, extremeWingEventSourceAddr,
				extremeWingEventSourceHostname }
			STATUS current
			DESCRIPTION
				"Event cpu-usage-too-high-recover"
				::= { extremeWingTrapsDiagPrefix 20}


		-- 1.3.6.1.4.1.1916.2.131.50.0.10.0.21
		extremeWingTrapDiagCpuLoad NOTIFICATION-TYPE
			OBJECTS { extremeWingEventMnemonic, extremeWingEventModule, extremeWingEventSeverity, extremeWingEventMsg, extremeWingEventSourceAddr,
				extremeWingEventSourceHostname }
			STATUS current
			DESCRIPTION
				"Event cpu-load"
				::= { extremeWingTrapsDiagPrefix 21}


		-- 1.3.6.1.4.1.1916.2.131.50.0.10.0.22
		extremeWingTrapDiagRamUsage NOTIFICATION-TYPE
			OBJECTS { extremeWingEventMnemonic, extremeWingEventModule, extremeWingEventSeverity, extremeWingEventMsg, extremeWingEventSourceAddr,
				extremeWingEventSourceHostname }
			STATUS current
			DESCRIPTION
				"Event ram-usage"
				::= { extremeWingTrapsDiagPrefix 22}


		-- 1.3.6.1.4.1.1916.2.131.50.0.10.0.23
		extremeWingTrapDiagMemUsageTooHigh NOTIFICATION-TYPE
			OBJECTS { extremeWingEventMnemonic, extremeWingEventModule, extremeWingEventSeverity, extremeWingEventMsg, extremeWingEventSourceAddr,
				extremeWingEventSourceHostname }
			STATUS current
			DESCRIPTION
				"Event mem-usage-too-high"
				::= { extremeWingTrapsDiagPrefix 23}


		-- 1.3.6.1.4.1.1916.2.131.50.0.10.0.24
		extremeWingTrapDiagMemUsageTooHighRecover NOTIFICATION-TYPE
			OBJECTS { extremeWingEventMnemonic, extremeWingEventModule, extremeWingEventSeverity, extremeWingEventMsg, extremeWingEventSourceAddr,
				extremeWingEventSourceHostname }
			STATUS current
			DESCRIPTION
				"Event mem-usage-too-high-recover"
				::= { extremeWingTrapsDiagPrefix 24}


		-- 1.3.6.1.4.1.1916.2.131.50.0.10.0.25
		extremeWingTrapDiagBufUsage NOTIFICATION-TYPE
			OBJECTS { extremeWingEventMnemonic, extremeWingEventModule, extremeWingEventSeverity, extremeWingEventMsg, extremeWingEventSourceAddr,
				extremeWingEventSourceHostname }
			STATUS current
			DESCRIPTION
				"Event buf-usage"
				::= { extremeWingTrapsDiagPrefix 25}


		-- 1.3.6.1.4.1.1916.2.131.50.0.10.0.26
		extremeWingTrapDiagHeadCacheUsage NOTIFICATION-TYPE
			OBJECTS { extremeWingEventMnemonic, extremeWingEventModule, extremeWingEventSeverity, extremeWingEventMsg, extremeWingEventSourceAddr,
				extremeWingEventSourceHostname }
			STATUS current
			DESCRIPTION
				"Event head-cache-usage"
				::= { extremeWingTrapsDiagPrefix 26}


		-- 1.3.6.1.4.1.1916.2.131.50.0.10.0.27
		extremeWingTrapDiagIpDestUsage NOTIFICATION-TYPE
			OBJECTS { extremeWingEventMnemonic, extremeWingEventModule, extremeWingEventSeverity, extremeWingEventMsg, extremeWingEventSourceAddr,
				extremeWingEventSourceHostname }
			STATUS current
			DESCRIPTION
				"Event ip-dest-usage"
				::= { extremeWingTrapsDiagPrefix 27}


		-- 1.3.6.1.4.1.1916.2.131.50.0.10.0.28
		extremeWingTrapDiagFreeRam NOTIFICATION-TYPE
			OBJECTS { extremeWingEventMnemonic, extremeWingEventModule, extremeWingEventSeverity, extremeWingEventMsg, extremeWingEventSourceAddr,
				extremeWingEventSourceHostname }
			STATUS current
			DESCRIPTION
				"Event free-ram"
				::= { extremeWingTrapsDiagPrefix 28}


		-- 1.3.6.1.4.1.1916.2.131.50.0.10.0.29
		extremeWingTrapDiagFreeFlashDisk NOTIFICATION-TYPE
			OBJECTS { extremeWingEventMnemonic, extremeWingEventModule, extremeWingEventSeverity, extremeWingEventMsg, extremeWingEventSourceAddr,
				extremeWingEventSourceHostname }
			STATUS current
			DESCRIPTION
				"Event free-flash-disk"
				::= { extremeWingTrapsDiagPrefix 29}


		-- 1.3.6.1.4.1.1916.2.131.50.0.10.0.30
		extremeWingTrapDiagFreeFlashInodes NOTIFICATION-TYPE
			OBJECTS { extremeWingEventMnemonic, extremeWingEventModule, extremeWingEventSeverity, extremeWingEventMsg, extremeWingEventSourceAddr,
				extremeWingEventSourceHostname }
			STATUS current
			DESCRIPTION
				"Event free-flash-inodes"
				::= { extremeWingTrapsDiagPrefix 30}


		-- 1.3.6.1.4.1.1916.2.131.50.0.10.0.31
		extremeWingTrapDiagFreeNvramDisk NOTIFICATION-TYPE
			OBJECTS { extremeWingEventMnemonic, extremeWingEventModule, extremeWingEventSeverity, extremeWingEventMsg, extremeWingEventSourceAddr,
				extremeWingEventSourceHostname }
			STATUS current
			DESCRIPTION
				"Event free-nvram-disk"
				::= { extremeWingTrapsDiagPrefix 31}


		-- 1.3.6.1.4.1.1916.2.131.50.0.10.0.32
		extremeWingTrapDiagFreeNvramInodes NOTIFICATION-TYPE
			OBJECTS { extremeWingEventMnemonic, extremeWingEventModule, extremeWingEventSeverity, extremeWingEventMsg, extremeWingEventSourceAddr,
				extremeWingEventSourceHostname }
			STATUS current
			DESCRIPTION
				"Event free-nvram-inodes"
				::= { extremeWingTrapsDiagPrefix 32}


		-- 1.3.6.1.4.1.1916.2.131.50.0.10.0.33
		extremeWingTrapDiagFreeRamDisk NOTIFICATION-TYPE
			OBJECTS { extremeWingEventMnemonic, extremeWingEventModule, extremeWingEventSeverity, extremeWingEventMsg, extremeWingEventSourceAddr,
				extremeWingEventSourceHostname }
			STATUS current
			DESCRIPTION
				"Event free-ram-disk"
				::= { extremeWingTrapsDiagPrefix 33}


		-- 1.3.6.1.4.1.1916.2.131.50.0.10.0.34
		extremeWingTrapDiagFreeRamInodes NOTIFICATION-TYPE
			OBJECTS { extremeWingEventMnemonic, extremeWingEventModule, extremeWingEventSeverity, extremeWingEventMsg, extremeWingEventSourceAddr,
				extremeWingEventSourceHostname }
			STATUS current
			DESCRIPTION
				"Event free-ram-inodes"
				::= { extremeWingTrapsDiagPrefix 34}


		-- 1.3.6.1.4.1.1916.2.131.50.0.10.0.35
		extremeWingTrapDiagFdCount NOTIFICATION-TYPE
			OBJECTS { extremeWingEventMnemonic, extremeWingEventModule, extremeWingEventSeverity, extremeWingEventMsg, extremeWingEventSourceAddr,
				extremeWingEventSourceHostname }
			STATUS current
			DESCRIPTION
				"Event fd-count"
				::= { extremeWingTrapsDiagPrefix 35}


		-- 1.3.6.1.4.1.1916.2.131.50.0.10.0.36
		extremeWingTrapDiagDiskUsage NOTIFICATION-TYPE
			OBJECTS { extremeWingEventMnemonic, extremeWingEventModule, extremeWingEventSeverity, extremeWingEventMsg, extremeWingEventSourceAddr,
				extremeWingEventSourceHostname }
			STATUS current
			DESCRIPTION
				"Event disk-usage"
				::= { extremeWingTrapsDiagPrefix 36}


		-- 1.3.6.1.4.1.1916.2.131.50.0.10.0.37
		extremeWingTrapDiagNewLedState NOTIFICATION-TYPE
			OBJECTS { extremeWingEventMnemonic, extremeWingEventModule, extremeWingEventSeverity, extremeWingEventMsg, extremeWingEventSourceAddr,
				extremeWingEventSourceHostname }
			STATUS current
			DESCRIPTION
				"Event new-led-state"
				::= { extremeWingTrapsDiagPrefix 37}


		-- 1.3.6.1.4.1.1916.2.131.50.0.10.0.38
		extremeWingTrapDiagLedIdentify NOTIFICATION-TYPE
			OBJECTS { extremeWingEventMnemonic, extremeWingEventModule, extremeWingEventSeverity, extremeWingEventMsg, extremeWingEventSourceAddr,
				extremeWingEventSourceHostname }
			STATUS current
			DESCRIPTION
				"Event led-identify"
				::= { extremeWingTrapsDiagPrefix 38}


--802.11 management module
		--1.3.6.1.4.1.1916.2.131.50.0.11
		extremeWingTrapsDot11 OBJECT IDENTIFIER ::= { extremeWingNotifications 11 }


		--1.3.6.1.4.1.1916.2.131.50.0.11.0
		extremeWingTrapsDot11Prefix OBJECT IDENTIFIER ::= { extremeWingTrapsDot11 0 }


		-- 1.3.6.1.4.1.1916.2.131.50.0.11.0.1
		extremeWingTrapDot11CountryCode NOTIFICATION-TYPE
			OBJECTS { extremeWingEventMnemonic, extremeWingEventModule, extremeWingEventSeverity, extremeWingEventMsg, extremeWingEventSourceAddr,
				extremeWingEventSourceHostname }
			STATUS current
			DESCRIPTION
				"Country of operation configured"
				::= { extremeWingTrapsDot11Prefix 1}


		-- 1.3.6.1.4.1.1916.2.131.50.0.11.0.2
		extremeWingTrapDot11CountryCodeError NOTIFICATION-TYPE
			OBJECTS { extremeWingEventMnemonic, extremeWingEventModule, extremeWingEventSeverity, extremeWingEventMsg, extremeWingEventSourceAddr,
				extremeWingEventSourceHostname }
			STATUS current
			DESCRIPTION
				"Error setting country of operation"
				::= { extremeWingTrapsDot11Prefix 2}


		-- 1.3.6.1.4.1.1916.2.131.50.0.11.0.3
		extremeWingTrapDot11ClientAssociated NOTIFICATION-TYPE
			OBJECTS { extremeWingEventMnemonic, extremeWingEventModule, extremeWingEventSeverity, extremeWingEventMsg, extremeWingEventSourceAddr,
				extremeWingEventSourceHostname }
			STATUS current
			DESCRIPTION
				"Client associated event"
				::= { extremeWingTrapsDot11Prefix 3}


		-- 1.3.6.1.4.1.1916.2.131.50.0.11.0.4
		extremeWingTrapDot11ClientDisassociated NOTIFICATION-TYPE
			OBJECTS { extremeWingEventMnemonic, extremeWingEventModule, extremeWingEventSeverity, extremeWingEventMsg, extremeWingEventSourceAddr,
				extremeWingEventSourceHostname }
			STATUS current
			DESCRIPTION
				"Client disassociated"
				::= { extremeWingTrapsDot11Prefix 4}


		-- 1.3.6.1.4.1.1916.2.131.50.0.11.0.5
		extremeWingTrapDot11ClientDeniedAssoc NOTIFICATION-TYPE
			OBJECTS { extremeWingEventMnemonic, extremeWingEventModule, extremeWingEventSeverity, extremeWingEventMsg, extremeWingEventSourceAddr,
				extremeWingEventSourceHostname }
			STATUS current
			DESCRIPTION
				"Client denied association"
				::= { extremeWingTrapsDot11Prefix 5}


		-- 1.3.6.1.4.1.1916.2.131.50.0.11.0.6
		extremeWingTrapDot11ClientAssocIgnored NOTIFICATION-TYPE
			OBJECTS { extremeWingEventMnemonic, extremeWingEventModule, extremeWingEventSeverity, extremeWingEventMsg, extremeWingEventSourceAddr,
				extremeWingEventSourceHostname }
			STATUS current
			DESCRIPTION
				"Client ignored association"
				::= { extremeWingTrapsDot11Prefix 6}


		-- 1.3.6.1.4.1.1916.2.131.50.0.11.0.7
		extremeWingTrapDot11WpaWpa2Success NOTIFICATION-TYPE
			OBJECTS { extremeWingEventMnemonic, extremeWingEventModule, extremeWingEventSeverity, extremeWingEventMsg, extremeWingEventSourceAddr,
				extremeWingEventSourceHostname }
			STATUS current
			DESCRIPTION
				"Client completed WPA/WPA2 handshake"
				::= { extremeWingTrapsDot11Prefix 7}


		-- 1.3.6.1.4.1.1916.2.131.50.0.11.0.8
		extremeWingTrapDot11WpaWpa2Failed NOTIFICATION-TYPE
			OBJECTS { extremeWingEventMnemonic, extremeWingEventModule, extremeWingEventSeverity, extremeWingEventMsg, extremeWingEventSourceAddr,
				extremeWingEventSourceHostname }
			STATUS current
			DESCRIPTION
				"Client failed WPA/WPA2 handshake"
				::= { extremeWingTrapsDot11Prefix 8}


		-- 1.3.6.1.4.1.1916.2.131.50.0.11.0.9
		extremeWingTrapDot11WpaWpa2KeyRotn NOTIFICATION-TYPE
			OBJECTS { extremeWingEventMnemonic, extremeWingEventModule, extremeWingEventSeverity, extremeWingEventMsg, extremeWingEventSourceAddr,
				extremeWingEventSourceHostname }
			STATUS current
			DESCRIPTION
				"Rotating WPA/WPA2 group keys on wlan"
				::= { extremeWingTrapsDot11Prefix 9}


		-- 1.3.6.1.4.1.1916.2.131.50.0.11.0.10
		extremeWingTrapDot11TkipMicFailReport NOTIFICATION-TYPE
			OBJECTS { extremeWingEventMnemonic, extremeWingEventModule, extremeWingEventSeverity, extremeWingEventMsg, extremeWingEventSourceAddr,
				extremeWingEventSourceHostname }
			STATUS current
			DESCRIPTION
				"TKIP MIC failure report"
				::= { extremeWingTrapsDot11Prefix 10}


		-- 1.3.6.1.4.1.1916.2.131.50.0.11.0.11
		extremeWingTrapDot11TkipMicFailure NOTIFICATION-TYPE
			OBJECTS { extremeWingEventMnemonic, extremeWingEventModule, extremeWingEventSeverity, extremeWingEventMsg, extremeWingEventSourceAddr,
				extremeWingEventSourceHostname }
			STATUS current
			DESCRIPTION
				"TKIP MIC check failed"
				::= { extremeWingTrapsDot11Prefix 11}


		-- 1.3.6.1.4.1.1916.2.131.50.0.11.0.12
		extremeWingTrapDot11TkipCntrmeasStart NOTIFICATION-TYPE
			OBJECTS { extremeWingEventMnemonic, extremeWingEventModule, extremeWingEventSeverity, extremeWingEventMsg, extremeWingEventSourceAddr,
				extremeWingEventSourceHostname }
			STATUS current
			DESCRIPTION
				"TKIP countermeasures initiated"
				::= { extremeWingTrapsDot11Prefix 12}


		-- 1.3.6.1.4.1.1916.2.131.50.0.11.0.13
		extremeWingTrapDot11TkipCntrmeasEnd NOTIFICATION-TYPE
			OBJECTS { extremeWingEventMnemonic, extremeWingEventModule, extremeWingEventSeverity, extremeWingEventMsg, extremeWingEventSourceAddr,
				extremeWingEventSourceHostname }
			STATUS current
			DESCRIPTION
				"TKIP countermeasures ended"
				::= { extremeWingTrapsDot11Prefix 13}


		-- 1.3.6.1.4.1.1916.2.131.50.0.11.0.14
		extremeWingTrapDot11EapSuccess NOTIFICATION-TYPE
			OBJECTS { extremeWingEventMnemonic, extremeWingEventModule, extremeWingEventSeverity, extremeWingEventMsg, extremeWingEventSourceAddr,
				extremeWingEventSourceHostname }
			STATUS current
			DESCRIPTION
				"EAP authentication success"
				::= { extremeWingTrapsDot11Prefix 14}


		-- 1.3.6.1.4.1.1916.2.131.50.0.11.0.15
		extremeWingTrapDot11EapFailed NOTIFICATION-TYPE
			OBJECTS { extremeWingEventMnemonic, extremeWingEventModule, extremeWingEventSeverity, extremeWingEventMsg, extremeWingEventSourceAddr,
				extremeWingEventSourceHostname }
			STATUS current
			DESCRIPTION
				"EAP authentication failure"
				::= { extremeWingTrapsDot11Prefix 15}


		-- 1.3.6.1.4.1.1916.2.131.50.0.11.0.16
		extremeWingTrapDot11EapClientTimeout NOTIFICATION-TYPE
			OBJECTS { extremeWingEventMnemonic, extremeWingEventModule, extremeWingEventSeverity, extremeWingEventMsg, extremeWingEventSourceAddr,
				extremeWingEventSourceHostname }
			STATUS current
			DESCRIPTION
				"EAP authentication timed out"
				::= { extremeWingTrapsDot11Prefix 16}


		-- 1.3.6.1.4.1.1916.2.131.50.0.11.0.17
		extremeWingTrapDot11EapServerTimeout NOTIFICATION-TYPE
			OBJECTS { extremeWingEventMnemonic, extremeWingEventModule, extremeWingEventSeverity, extremeWingEventMsg, extremeWingEventSourceAddr,
				extremeWingEventSourceHostname }
			STATUS current
			DESCRIPTION
				"Radius server timed out"
				::= { extremeWingTrapsDot11Prefix 17}


		-- 1.3.6.1.4.1.1916.2.131.50.0.11.0.18
		extremeWingTrapDot11EapCachedKeys NOTIFICATION-TYPE
			OBJECTS { extremeWingEventMnemonic, extremeWingEventModule, extremeWingEventSeverity, extremeWingEventMsg, extremeWingEventSourceAddr,
				extremeWingEventSourceHostname }
			STATUS current
			DESCRIPTION
				"Key cache used for authentication"
				::= { extremeWingTrapsDot11Prefix 18}


		-- 1.3.6.1.4.1.1916.2.131.50.0.11.0.19
		extremeWingTrapDot11EapOppCachedKeys NOTIFICATION-TYPE
			OBJECTS { extremeWingEventMnemonic, extremeWingEventModule, extremeWingEventSeverity, extremeWingEventMsg, extremeWingEventSourceAddr,
				extremeWingEventSourceHostname }
			STATUS current
			DESCRIPTION
				"Opportunistic key cached used for authentication"
				::= { extremeWingTrapsDot11Prefix 19}


		-- 1.3.6.1.4.1.1916.2.131.50.0.11.0.20
		extremeWingTrapDot11EapPreauthSuccess NOTIFICATION-TYPE
			OBJECTS { extremeWingEventMnemonic, extremeWingEventModule, extremeWingEventSeverity, extremeWingEventMsg, extremeWingEventSourceAddr,
				extremeWingEventSourceHostname }
			STATUS current
			DESCRIPTION
				"EAP pre-authentication success"
				::= { extremeWingTrapsDot11Prefix 20}


		-- 1.3.6.1.4.1.1916.2.131.50.0.11.0.21
		extremeWingTrapDot11EapPreauthFailed NOTIFICATION-TYPE
			OBJECTS { extremeWingEventMnemonic, extremeWingEventModule, extremeWingEventSeverity, extremeWingEventMsg, extremeWingEventSourceAddr,
				extremeWingEventSourceHostname }
			STATUS current
			DESCRIPTION
				"EAP pre-authentication failed"
				::= { extremeWingTrapsDot11Prefix 21}


		-- 1.3.6.1.4.1.1916.2.131.50.0.11.0.22
		extremeWingTrapDot11EapPreauthClientTimeout NOTIFICATION-TYPE
			OBJECTS { extremeWingEventMnemonic, extremeWingEventModule, extremeWingEventSeverity, extremeWingEventMsg, extremeWingEventSourceAddr,
				extremeWingEventSourceHostname }
			STATUS current
			DESCRIPTION
				"EAP pre-authentication client timeout"
				::= { extremeWingTrapsDot11Prefix 22}


		-- 1.3.6.1.4.1.1916.2.131.50.0.11.0.23
		extremeWingTrapDot11EapPreauthServerTimeout NOTIFICATION-TYPE
			OBJECTS { extremeWingEventMnemonic, extremeWingEventModule, extremeWingEventSeverity, extremeWingEventMsg, extremeWingEventSourceAddr,
				extremeWingEventSourceHostname }
			STATUS current
			DESCRIPTION
				"EAP pre-authentication server timeout"
				::= { extremeWingTrapsDot11Prefix 23}


		-- 1.3.6.1.4.1.1916.2.131.50.0.11.0.24
		extremeWingTrapDot11KerberosWlanSuccess NOTIFICATION-TYPE
			OBJECTS { extremeWingEventMnemonic, extremeWingEventModule, extremeWingEventSeverity, extremeWingEventMsg, extremeWingEventSourceAddr,
				extremeWingEventSourceHostname }
			STATUS current
			DESCRIPTION
				"Kerberos authentication success"
				::= { extremeWingTrapsDot11Prefix 24}


		-- 1.3.6.1.4.1.1916.2.131.50.0.11.0.25
		extremeWingTrapDot11KerberosWlanTimeout NOTIFICATION-TYPE
			OBJECTS { extremeWingEventMnemonic, extremeWingEventModule, extremeWingEventSeverity, extremeWingEventMsg, extremeWingEventSourceAddr,
				extremeWingEventSourceHostname }
			STATUS current
			DESCRIPTION
				"Kerberos authentication timed out"
				::= { extremeWingTrapsDot11Prefix 25}


		-- 1.3.6.1.4.1.1916.2.131.50.0.11.0.26
		extremeWingTrapDot11KerberosWlanFailed NOTIFICATION-TYPE
			OBJECTS { extremeWingEventMnemonic, extremeWingEventModule, extremeWingEventSeverity, extremeWingEventMsg, extremeWingEventSourceAddr,
				extremeWingEventSourceHostname }
			STATUS current
			DESCRIPTION
				"Wlan kerberos authentication failed"
				::= { extremeWingTrapsDot11Prefix 26}


		-- 1.3.6.1.4.1.1916.2.131.50.0.11.0.27
		extremeWingTrapDot11KerberosClientSuccess NOTIFICATION-TYPE
			OBJECTS { extremeWingEventMnemonic, extremeWingEventModule, extremeWingEventSeverity, extremeWingEventMsg, extremeWingEventSourceAddr,
				extremeWingEventSourceHostname }
			STATUS current
			DESCRIPTION
				"Client kerberos authentication success"
				::= { extremeWingTrapsDot11Prefix 27}


		-- 1.3.6.1.4.1.1916.2.131.50.0.11.0.28
		extremeWingTrapDot11KerberosClientFailed NOTIFICATION-TYPE
			OBJECTS { extremeWingEventMnemonic, extremeWingEventModule, extremeWingEventSeverity, extremeWingEventMsg, extremeWingEventSourceAddr,
				extremeWingEventSourceHostname }
			STATUS current
			DESCRIPTION
				"Client kerberos authentication failed"
				::= { extremeWingTrapsDot11Prefix 28}


		-- 1.3.6.1.4.1.1916.2.131.50.0.11.0.29
		extremeWingTrapDot11VoiceCallFailed NOTIFICATION-TYPE
			OBJECTS { extremeWingEventMnemonic, extremeWingEventModule, extremeWingEventSeverity, extremeWingEventMsg, extremeWingEventSourceAddr,
				extremeWingEventSourceHostname }
			STATUS current
			DESCRIPTION
				"Voice call failed"
				::= { extremeWingTrapsDot11Prefix 29}


		-- 1.3.6.1.4.1.1916.2.131.50.0.11.0.30
		extremeWingTrapDot11VoiceCallEstablished NOTIFICATION-TYPE
			OBJECTS { extremeWingEventMnemonic, extremeWingEventModule, extremeWingEventSeverity, extremeWingEventMsg, extremeWingEventSourceAddr,
				extremeWingEventSourceHostname }
			STATUS current
			DESCRIPTION
				"Voice call established"
				::= { extremeWingTrapsDot11Prefix 30}


		-- 1.3.6.1.4.1.1916.2.131.50.0.11.0.31
		extremeWingTrapDot11VoiceCallCompleted NOTIFICATION-TYPE
			OBJECTS { extremeWingEventMnemonic, extremeWingEventModule, extremeWingEventSeverity, extremeWingEventMsg, extremeWingEventSourceAddr,
				extremeWingEventSourceHostname }
			STATUS current
			DESCRIPTION
				"Voice call completed"
				::= { extremeWingTrapsDot11Prefix 31}


		-- 1.3.6.1.4.1.1916.2.131.50.0.11.0.32
		extremeWingTrapDot11UnsanctionedApActive NOTIFICATION-TYPE
			OBJECTS { extremeWingEventMnemonic, extremeWingEventModule, extremeWingEventSeverity, extremeWingEventMsg, extremeWingEventSourceAddr,
				extremeWingEventSourceHostname }
			STATUS current
			DESCRIPTION
				"Unsanctioned AP active"
				::= { extremeWingTrapsDot11Prefix 32}


		-- 1.3.6.1.4.1.1916.2.131.50.0.11.0.33
		extremeWingTrapDot11UnsanctionedApInactive NOTIFICATION-TYPE
			OBJECTS { extremeWingEventMnemonic, extremeWingEventModule, extremeWingEventSeverity, extremeWingEventMsg, extremeWingEventSourceAddr,
				extremeWingEventSourceHostname }
			STATUS current
			DESCRIPTION
				"Unsanctioned AP inactive"
				::= { extremeWingTrapsDot11Prefix 33}


		-- 1.3.6.1.4.1.1916.2.131.50.0.11.0.34
		extremeWingTrapDot11UnsanctionedApStatusChange NOTIFICATION-TYPE
			OBJECTS { extremeWingEventMnemonic, extremeWingEventModule, extremeWingEventSeverity, extremeWingEventMsg, extremeWingEventSourceAddr,
				extremeWingEventSourceHostname }
			STATUS current
			DESCRIPTION
				"Unsanctioned AP changed state"
				::= { extremeWingTrapsDot11Prefix 34}


		-- 1.3.6.1.4.1.1916.2.131.50.0.11.0.35
		extremeWingTrapDot11NeighborDeniedAssoc NOTIFICATION-TYPE
			OBJECTS { extremeWingEventMnemonic, extremeWingEventModule, extremeWingEventSeverity, extremeWingEventMsg, extremeWingEventSourceAddr,
				extremeWingEventSourceHostname }
			STATUS current
			DESCRIPTION
				"Neighbor denied association"
				::= { extremeWingTrapsDot11Prefix 35}


		-- 1.3.6.1.4.1.1916.2.131.50.0.11.0.36
		extremeWingTrapDot11WlanTimeAccessDisable NOTIFICATION-TYPE
			OBJECTS { extremeWingEventMnemonic, extremeWingEventModule, extremeWingEventSeverity, extremeWingEventMsg, extremeWingEventSourceAddr,
				extremeWingEventSourceHostname }
			STATUS current
			DESCRIPTION
				"Wlan disabled by time-based-access"
				::= { extremeWingTrapsDot11Prefix 36}


		-- 1.3.6.1.4.1.1916.2.131.50.0.11.0.37
		extremeWingTrapDot11WlanTimeAccessEnable NOTIFICATION-TYPE
			OBJECTS { extremeWingEventMnemonic, extremeWingEventModule, extremeWingEventSeverity, extremeWingEventMsg, extremeWingEventSourceAddr,
				extremeWingEventSourceHostname }
			STATUS current
			DESCRIPTION
				"Wlan re-enabled by time-based-access"
				::= { extremeWingTrapsDot11Prefix 37}


		-- 1.3.6.1.4.1.1916.2.131.50.0.11.0.38
		extremeWingTrapDot11MoveOperationSuccess NOTIFICATION-TYPE
			OBJECTS { extremeWingEventMnemonic, extremeWingEventModule, extremeWingEventSeverity, extremeWingEventMsg, extremeWingEventSourceAddr,
				extremeWingEventSourceHostname }
			STATUS current
			DESCRIPTION
				"Move operation success"
				::= { extremeWingTrapsDot11Prefix 38}


		-- 1.3.6.1.4.1.1916.2.131.50.0.11.0.39
		extremeWingTrapDot11FtRoamSuccess NOTIFICATION-TYPE
			OBJECTS { extremeWingEventMnemonic, extremeWingEventModule, extremeWingEventSeverity, extremeWingEventMsg, extremeWingEventSourceAddr,
				extremeWingEventSourceHostname }
			STATUS current
			DESCRIPTION
				"Client fast bss transition"
				::= { extremeWingTrapsDot11Prefix 39}


		-- 1.3.6.1.4.1.1916.2.131.50.0.11.0.40
		extremeWingTrapDot11GalRxRequest NOTIFICATION-TYPE
			OBJECTS { extremeWingEventMnemonic, extremeWingEventModule, extremeWingEventSeverity, extremeWingEventMsg, extremeWingEventSourceAddr,
				extremeWingEventSourceHostname }
			STATUS current
			DESCRIPTION
				"Event gal-rx-request"
				::= { extremeWingTrapsDot11Prefix 40}


		-- 1.3.6.1.4.1.1916.2.131.50.0.11.0.41
		extremeWingTrapDot11GalTxResponse NOTIFICATION-TYPE
			OBJECTS { extremeWingEventMnemonic, extremeWingEventModule, extremeWingEventSeverity, extremeWingEventMsg, extremeWingEventSourceAddr,
				extremeWingEventSourceHostname }
			STATUS current
			DESCRIPTION
				"Event gal-tx-response"
				::= { extremeWingTrapsDot11Prefix 41}


		-- 1.3.6.1.4.1.1916.2.131.50.0.11.0.42
		extremeWingTrapDot11GalValidateReq NOTIFICATION-TYPE
			OBJECTS { extremeWingEventMnemonic, extremeWingEventModule, extremeWingEventSeverity, extremeWingEventMsg, extremeWingEventSourceAddr,
				extremeWingEventSourceHostname }
			STATUS current
			DESCRIPTION
				"Event gal-validate-req"
				::= { extremeWingTrapsDot11Prefix 42}


		-- 1.3.6.1.4.1.1916.2.131.50.0.11.0.43
		extremeWingTrapDot11GalValidateFailed NOTIFICATION-TYPE
			OBJECTS { extremeWingEventMnemonic, extremeWingEventModule, extremeWingEventSeverity, extremeWingEventMsg, extremeWingEventSourceAddr,
				extremeWingEventSourceHostname }
			STATUS current
			DESCRIPTION
				"Event gal-validate-failed"
				::= { extremeWingTrapsDot11Prefix 43}


		-- 1.3.6.1.4.1.1916.2.131.50.0.11.0.44
		extremeWingTrapDot11GalValidateSuccess NOTIFICATION-TYPE
			OBJECTS { extremeWingEventMnemonic, extremeWingEventModule, extremeWingEventSeverity, extremeWingEventMsg, extremeWingEventSourceAddr,
				extremeWingEventSourceHostname }
			STATUS current
			DESCRIPTION
				"Event gal-validate-success"
				::= { extremeWingTrapsDot11Prefix 44}


--Firmware update module
		--1.3.6.1.4.1.1916.2.131.50.0.13
		extremeWingTrapsFwu OBJECT IDENTIFIER ::= { extremeWingNotifications 13 }


		--1.3.6.1.4.1.1916.2.131.50.0.13.0
		extremeWingTrapsFwuPrefix OBJECT IDENTIFIER ::= { extremeWingTrapsFwu 0 }


		-- 1.3.6.1.4.1.1916.2.131.50.0.13.0.1
		extremeWingTrapFwuFwudone NOTIFICATION-TYPE
			OBJECTS { extremeWingEventMnemonic, extremeWingEventModule, extremeWingEventSeverity, extremeWingEventMsg, extremeWingEventSourceAddr,
				extremeWingEventSourceHostname }
			STATUS current
			DESCRIPTION
				"Update successfully completed"
				::= { extremeWingTrapsFwuPrefix 1}


		-- 1.3.6.1.4.1.1916.2.131.50.0.13.0.2
		extremeWingTrapFwuFwuaborted NOTIFICATION-TYPE
			OBJECTS { extremeWingEventMnemonic, extremeWingEventModule, extremeWingEventSeverity, extremeWingEventMsg, extremeWingEventSourceAddr,
				extremeWingEventSourceHostname }
			STATUS current
			DESCRIPTION
				"Update aborted"
				::= { extremeWingTrapsFwuPrefix 2}


		-- 1.3.6.1.4.1.1916.2.131.50.0.13.0.3
		extremeWingTrapFwuFwunoneed NOTIFICATION-TYPE
			OBJECTS { extremeWingEventMnemonic, extremeWingEventModule, extremeWingEventSeverity, extremeWingEventMsg, extremeWingEventSourceAddr,
				extremeWingEventSourceHostname }
			STATUS current
			DESCRIPTION
				"Update not required, running and update version are the same"
				::= { extremeWingTrapsFwuPrefix 3}


		-- 1.3.6.1.4.1.1916.2.131.50.0.13.0.4
		extremeWingTrapFwuFwusyserr NOTIFICATION-TYPE
			OBJECTS { extremeWingEventMnemonic, extremeWingEventModule, extremeWingEventSeverity, extremeWingEventMsg, extremeWingEventSourceAddr,
				extremeWingEventSourceHostname }
			STATUS current
			DESCRIPTION
				"Update unsuccessful, system cmd failed"
				::= { extremeWingTrapsFwuPrefix 4}


		-- 1.3.6.1.4.1.1916.2.131.50.0.13.0.5
		extremeWingTrapFwuFwubadconfig NOTIFICATION-TYPE
			OBJECTS { extremeWingEventMnemonic, extremeWingEventModule, extremeWingEventSeverity, extremeWingEventMsg, extremeWingEventSourceAddr,
				extremeWingEventSourceHostname }
			STATUS current
			DESCRIPTION
				"Update unsuccessful, unable to read config file"
				::= { extremeWingTrapsFwuPrefix 5}


		-- 1.3.6.1.4.1.1916.2.131.50.0.13.0.6
		extremeWingTrapFwuFwuserverundef NOTIFICATION-TYPE
			OBJECTS { extremeWingEventMnemonic, extremeWingEventModule, extremeWingEventSeverity, extremeWingEventMsg, extremeWingEventSourceAddr,
				extremeWingEventSourceHostname }
			STATUS current
			DESCRIPTION
				"Update unsuccessful, server undefined"
				::= { extremeWingTrapsFwuPrefix 6}


		-- 1.3.6.1.4.1.1916.2.131.50.0.13.0.7
		extremeWingTrapFwuFwufileundef NOTIFICATION-TYPE
			OBJECTS { extremeWingEventMnemonic, extremeWingEventModule, extremeWingEventSeverity, extremeWingEventMsg, extremeWingEventSourceAddr,
				extremeWingEventSourceHostname }
			STATUS current
			DESCRIPTION
				"Update unsuccessful, update file undefined"
				::= { extremeWingTrapsFwuPrefix 7}


		-- 1.3.6.1.4.1.1916.2.131.50.0.13.0.8
		extremeWingTrapFwuFwuserverunreachable NOTIFICATION-TYPE
			OBJECTS { extremeWingEventMnemonic, extremeWingEventModule, extremeWingEventSeverity, extremeWingEventMsg, extremeWingEventSourceAddr,
				extremeWingEventSourceHostname }
			STATUS current
			DESCRIPTION
				"Update unsuccessful, server unreachable"
				::= { extremeWingTrapsFwuPrefix 8}


		-- 1.3.6.1.4.1.1916.2.131.50.0.13.0.9
		extremeWingTrapFwuFwucouldntgetfile NOTIFICATION-TYPE
			OBJECTS { extremeWingEventMnemonic, extremeWingEventModule, extremeWingEventSeverity, extremeWingEventMsg, extremeWingEventSourceAddr,
				extremeWingEventSourceHostname }
			STATUS current
			DESCRIPTION
				"Update unsuccessful, could not get file"
				::= { extremeWingTrapsFwuPrefix 9}


		-- 1.3.6.1.4.1.1916.2.131.50.0.13.0.10
		extremeWingTrapFwuFwuvermismatch NOTIFICATION-TYPE
			OBJECTS { extremeWingEventMnemonic, extremeWingEventModule, extremeWingEventSeverity, extremeWingEventMsg, extremeWingEventSourceAddr,
				extremeWingEventSourceHostname }
			STATUS current
			DESCRIPTION
				"Update unsuccessful, version mismatch"
				::= { extremeWingTrapsFwuPrefix 10}


		-- 1.3.6.1.4.1.1916.2.131.50.0.13.0.11
		extremeWingTrapFwuFwuprodmismatch NOTIFICATION-TYPE
			OBJECTS { extremeWingEventMnemonic, extremeWingEventModule, extremeWingEventSeverity, extremeWingEventMsg, extremeWingEventSourceAddr,
				extremeWingEventSourceHostname }
			STATUS current
			DESCRIPTION
				"Update unsuccessful, product mismatch"
				::= { extremeWingTrapsFwuPrefix 11}


		-- 1.3.6.1.4.1.1916.2.131.50.0.13.0.12
		extremeWingTrapFwuFwucorruptedfile NOTIFICATION-TYPE
			OBJECTS { extremeWingEventMnemonic, extremeWingEventModule, extremeWingEventSeverity, extremeWingEventMsg, extremeWingEventSourceAddr,
				extremeWingEventSourceHostname }
			STATUS current
			DESCRIPTION
				"Update unsuccessful, corrupted file"
				::= { extremeWingTrapsFwuPrefix 12}


		-- 1.3.6.1.4.1.1916.2.131.50.0.13.0.13
		extremeWingTrapFwuFwusignmismatch NOTIFICATION-TYPE
			OBJECTS { extremeWingEventMnemonic, extremeWingEventModule, extremeWingEventSeverity, extremeWingEventMsg, extremeWingEventSourceAddr,
				extremeWingEventSourceHostname }
			STATUS current
			DESCRIPTION
				"Update unsuccessful, signature mismatch"
				::= { extremeWingTrapsFwuPrefix 13}


		-- 1.3.6.1.4.1.1916.2.131.50.0.13.0.14
		extremeWingTrapFwuFwuunsupportedhw NOTIFICATION-TYPE
			OBJECTS { extremeWingEventMnemonic, extremeWingEventModule, extremeWingEventSeverity, extremeWingEventMsg, extremeWingEventSourceAddr,
				extremeWingEventSourceHostname }
			STATUS current
			DESCRIPTION
				"Update unsuccessful, unsupported hardware"
				::= { extremeWingTrapsFwuPrefix 14}


		-- 1.3.6.1.4.1.1916.2.131.50.0.13.0.15
		extremeWingTrapFwuFwuunsupportedmodelnum NOTIFICATION-TYPE
			OBJECTS { extremeWingEventMnemonic, extremeWingEventModule, extremeWingEventSeverity, extremeWingEventMsg, extremeWingEventSourceAddr,
				extremeWingEventSourceHostname }
			STATUS current
			DESCRIPTION
				"Update unsuccessful, unsupported FIPS model number"
				::= { extremeWingTrapsFwuPrefix 15}


--License module
		--1.3.6.1.4.1.1916.2.131.50.0.14
		extremeWingTrapsLicmgr OBJECT IDENTIFIER ::= { extremeWingNotifications 14 }


		--1.3.6.1.4.1.1916.2.131.50.0.14.0
		extremeWingTrapsLicmgrPrefix OBJECT IDENTIFIER ::= { extremeWingTrapsLicmgr 0 }


		-- 1.3.6.1.4.1.1916.2.131.50.0.14.0.1
		extremeWingTrapLicmgrLicInstalled NOTIFICATION-TYPE
			OBJECTS { extremeWingEventMnemonic, extremeWingEventModule, extremeWingEventSeverity, extremeWingEventMsg, extremeWingEventSourceAddr,
				extremeWingEventSourceHostname }
			STATUS current
			DESCRIPTION
				"License Installation "
				::= { extremeWingTrapsLicmgrPrefix 1}


		-- 1.3.6.1.4.1.1916.2.131.50.0.14.0.2
		extremeWingTrapLicmgrLicInstallDefault NOTIFICATION-TYPE
			OBJECTS { extremeWingEventMnemonic, extremeWingEventModule, extremeWingEventSeverity, extremeWingEventMsg, extremeWingEventSourceAddr,
				extremeWingEventSourceHostname }
			STATUS current
			DESCRIPTION
				"Default License Installation "
				::= { extremeWingTrapsLicmgrPrefix 2}


		-- 1.3.6.1.4.1.1916.2.131.50.0.14.0.3
		extremeWingTrapLicmgrLicInstallCount NOTIFICATION-TYPE
			OBJECTS { extremeWingEventMnemonic, extremeWingEventModule, extremeWingEventSeverity, extremeWingEventMsg, extremeWingEventSourceAddr,
				extremeWingEventSourceHostname }
			STATUS current
			DESCRIPTION
				"License Count"
				::= { extremeWingTrapsLicmgrPrefix 3}


		-- 1.3.6.1.4.1.1916.2.131.50.0.14.0.4
		extremeWingTrapLicmgrLicRemoved NOTIFICATION-TYPE
			OBJECTS { extremeWingEventMnemonic, extremeWingEventModule, extremeWingEventSeverity, extremeWingEventMsg, extremeWingEventSourceAddr,
				extremeWingEventSourceHostname }
			STATUS current
			DESCRIPTION
				"License Removed"
				::= { extremeWingTrapsLicmgrPrefix 4}


		-- 1.3.6.1.4.1.1916.2.131.50.0.14.0.5
		extremeWingTrapLicmgrLicInvalid NOTIFICATION-TYPE
			OBJECTS { extremeWingEventMnemonic, extremeWingEventModule, extremeWingEventSeverity, extremeWingEventMsg, extremeWingEventSourceAddr,
				extremeWingEventSourceHostname }
			STATUS current
			DESCRIPTION
				"License Installation Failed"
				::= { extremeWingTrapsLicmgrPrefix 5}


--Mesh module
		--1.3.6.1.4.1.1916.2.131.50.0.15
		extremeWingTrapsMesh OBJECT IDENTIFIER ::= { extremeWingNotifications 15 }


		--1.3.6.1.4.1.1916.2.131.50.0.15.0
		extremeWingTrapsMeshPrefix OBJECT IDENTIFIER ::= { extremeWingTrapsMesh 0 }


		-- 1.3.6.1.4.1.1916.2.131.50.0.15.0.1
		extremeWingTrapMeshMeshLinkUp NOTIFICATION-TYPE
			OBJECTS { extremeWingEventMnemonic, extremeWingEventModule, extremeWingEventSeverity, extremeWingEventMsg, extremeWingEventSourceAddr,
				extremeWingEventSourceHostname }
			STATUS current
			DESCRIPTION
				"Mesh link up"
				::= { extremeWingTrapsMeshPrefix 1}


		-- 1.3.6.1.4.1.1916.2.131.50.0.15.0.2
		extremeWingTrapMeshMeshLinkDown NOTIFICATION-TYPE
			OBJECTS { extremeWingEventMnemonic, extremeWingEventModule, extremeWingEventSeverity, extremeWingEventMsg, extremeWingEventSourceAddr,
				extremeWingEventSourceHostname }
			STATUS current
			DESCRIPTION
				"Mesh link down"
				::= { extremeWingTrapsMeshPrefix 2}


		-- 1.3.6.1.4.1.1916.2.131.50.0.15.0.3
		extremeWingTrapMeshMeshpointUp NOTIFICATION-TYPE
			OBJECTS { extremeWingEventMnemonic, extremeWingEventModule, extremeWingEventSeverity, extremeWingEventMsg, extremeWingEventSourceAddr,
				extremeWingEventSourceHostname }
			STATUS current
			DESCRIPTION
				"Event meshpoint-up"
				::= { extremeWingTrapsMeshPrefix 3}


		-- 1.3.6.1.4.1.1916.2.131.50.0.15.0.4
		extremeWingTrapMeshMeshpointDown NOTIFICATION-TYPE
			OBJECTS { extremeWingEventMnemonic, extremeWingEventModule, extremeWingEventSeverity, extremeWingEventMsg, extremeWingEventSourceAddr,
				extremeWingEventSourceHostname }
			STATUS current
			DESCRIPTION
				"Event meshpoint-down"
				::= { extremeWingTrapsMeshPrefix 4}


		-- 1.3.6.1.4.1.1916.2.131.50.0.15.0.5
		extremeWingTrapMeshMeshpointLoopPreventOn NOTIFICATION-TYPE
			OBJECTS { extremeWingEventMnemonic, extremeWingEventModule, extremeWingEventSeverity, extremeWingEventMsg, extremeWingEventSourceAddr,
				extremeWingEventSourceHostname }
			STATUS current
			DESCRIPTION
				"Event meshpoint-loop-prevent-on"
				::= { extremeWingTrapsMeshPrefix 5}


		-- 1.3.6.1.4.1.1916.2.131.50.0.15.0.6
		extremeWingTrapMeshMeshpointLoopPreventOff NOTIFICATION-TYPE
			OBJECTS { extremeWingEventMnemonic, extremeWingEventModule, extremeWingEventSeverity, extremeWingEventMsg, extremeWingEventSourceAddr,
				extremeWingEventSourceHostname }
			STATUS current
			DESCRIPTION
				"Event meshpoint-loop-prevent-off"
				::= { extremeWingTrapsMeshPrefix 6}


		-- 1.3.6.1.4.1.1916.2.131.50.0.15.0.7
		extremeWingTrapMeshMeshpointRootChange NOTIFICATION-TYPE
			OBJECTS { extremeWingEventMnemonic, extremeWingEventModule, extremeWingEventSeverity, extremeWingEventMsg, extremeWingEventSourceAddr,
				extremeWingEventSourceHostname }
			STATUS current
			DESCRIPTION
				"Event meshpoint-root-change"
				::= { extremeWingTrapsMeshPrefix 7}


		-- 1.3.6.1.4.1.1916.2.131.50.0.15.0.8
		extremeWingTrapMeshMeshpointPathChange NOTIFICATION-TYPE
			OBJECTS { extremeWingEventMnemonic, extremeWingEventModule, extremeWingEventSeverity, extremeWingEventMsg, extremeWingEventSourceAddr,
				extremeWingEventSourceHostname }
			STATUS current
			DESCRIPTION
				"Event meshpoint-path-change"
				::= { extremeWingTrapsMeshPrefix 8}


--Network Services Module
		--1.3.6.1.4.1.1916.2.131.50.0.16
		extremeWingTrapsNsm OBJECT IDENTIFIER ::= { extremeWingNotifications 16 }


		--1.3.6.1.4.1.1916.2.131.50.0.16.0
		extremeWingTrapsNsmPrefix OBJECT IDENTIFIER ::= { extremeWingTrapsNsm 0 }


		-- 1.3.6.1.4.1.1916.2.131.50.0.16.0.1
		extremeWingTrapNsmIfup NOTIFICATION-TYPE
			OBJECTS { extremeWingEventMnemonic, extremeWingEventModule, extremeWingEventSeverity, extremeWingEventMsg, extremeWingEventSourceAddr,
				extremeWingEventSourceHostname }
			STATUS current
			DESCRIPTION
				"Interface up"
				::= { extremeWingTrapsNsmPrefix 1}


		-- 1.3.6.1.4.1.1916.2.131.50.0.16.0.2
		extremeWingTrapNsmIfdown NOTIFICATION-TYPE
			OBJECTS { extremeWingEventMnemonic, extremeWingEventModule, extremeWingEventSeverity, extremeWingEventMsg, extremeWingEventSourceAddr,
				extremeWingEventSourceHostname }
			STATUS current
			DESCRIPTION
				"Interface down"
				::= { extremeWingTrapsNsmPrefix 2}


		-- 1.3.6.1.4.1.1916.2.131.50.0.16.0.3
		extremeWingTrapNsmDhcpip NOTIFICATION-TYPE
			OBJECTS { extremeWingEventMnemonic, extremeWingEventModule, extremeWingEventSeverity, extremeWingEventMsg, extremeWingEventSourceAddr,
				extremeWingEventSourceHostname }
			STATUS current
			DESCRIPTION
				"Interface assigned DHCP IP address"
				::= { extremeWingTrapsNsmPrefix 3}


		-- 1.3.6.1.4.1.1916.2.131.50.0.16.0.4
		extremeWingTrapNsmDhcpdefrt NOTIFICATION-TYPE
			OBJECTS { extremeWingEventMnemonic, extremeWingEventModule, extremeWingEventSeverity, extremeWingEventMsg, extremeWingEventSourceAddr,
				extremeWingEventSourceHostname }
			STATUS current
			DESCRIPTION
				"Default route learnt via DHCP"
				::= { extremeWingTrapsNsmPrefix 4}


		-- 1.3.6.1.4.1.1916.2.131.50.0.16.0.5
		extremeWingTrapNsmDhcpipchg NOTIFICATION-TYPE
			OBJECTS { extremeWingEventMnemonic, extremeWingEventModule, extremeWingEventSeverity, extremeWingEventMsg, extremeWingEventSourceAddr,
				extremeWingEventSourceHostname }
			STATUS current
			DESCRIPTION
				"DHCP Interface IP changed"
				::= { extremeWingTrapsNsmPrefix 5}


		-- 1.3.6.1.4.1.1916.2.131.50.0.16.0.6
		extremeWingTrapNsmDhcpnodefrt NOTIFICATION-TYPE
			OBJECTS { extremeWingEventMnemonic, extremeWingEventModule, extremeWingEventSeverity, extremeWingEventMsg, extremeWingEventSourceAddr,
				extremeWingEventSourceHostname }
			STATUS current
			DESCRIPTION
				"Interface no default route"
				::= { extremeWingTrapsNsmPrefix 6}


		-- 1.3.6.1.4.1.1916.2.131.50.0.16.0.7
		extremeWingTrapNsmIfipcfg NOTIFICATION-TYPE
			OBJECTS { extremeWingEventMnemonic, extremeWingEventModule, extremeWingEventSeverity, extremeWingEventMsg, extremeWingEventSourceAddr,
				extremeWingEventSourceHostname }
			STATUS current
			DESCRIPTION
				"Interface IP address "
				::= { extremeWingTrapsNsmPrefix 7}


		-- 1.3.6.1.4.1.1916.2.131.50.0.16.0.8
		extremeWingTrapNsmDhcpcErr NOTIFICATION-TYPE
			OBJECTS { extremeWingEventMnemonic, extremeWingEventModule, extremeWingEventSeverity, extremeWingEventMsg, extremeWingEventSourceAddr,
				extremeWingEventSourceHostname }
			STATUS current
			DESCRIPTION
				"DHCP server-client config conflict"
				::= { extremeWingTrapsNsmPrefix 8}


		-- 1.3.6.1.4.1.1916.2.131.50.0.16.0.9
		extremeWingTrapNsmDhcpipnoadd NOTIFICATION-TYPE
			OBJECTS { extremeWingEventMnemonic, extremeWingEventModule, extremeWingEventSeverity, extremeWingEventMsg, extremeWingEventSourceAddr,
				extremeWingEventSourceHostname }
			STATUS current
			DESCRIPTION
				"DHCP IP overlaps static IP address"
				::= { extremeWingTrapsNsmPrefix 9}


		-- 1.3.6.1.4.1.1916.2.131.50.0.16.0.10
		extremeWingTrapNsmDhcplsexp NOTIFICATION-TYPE
			OBJECTS { extremeWingEventMnemonic, extremeWingEventModule, extremeWingEventSeverity, extremeWingEventMsg, extremeWingEventSourceAddr,
				extremeWingEventSourceHostname }
			STATUS current
			DESCRIPTION
				"Interace DHCP lease expired"
				::= { extremeWingTrapsNsmPrefix 10}


		-- 1.3.6.1.4.1.1916.2.131.50.0.16.0.11
		extremeWingTrapNsmDhcpnak NOTIFICATION-TYPE
			OBJECTS { extremeWingEventMnemonic, extremeWingEventModule, extremeWingEventSeverity, extremeWingEventMsg, extremeWingEventSourceAddr,
				extremeWingEventSourceHostname }
			STATUS current
			DESCRIPTION
				"DHCP Server returned DHCP NAK response"
				::= { extremeWingTrapsNsmPrefix 11}


		-- 1.3.6.1.4.1.1916.2.131.50.0.16.0.12
		extremeWingTrapNsmNsmNtp NOTIFICATION-TYPE
			OBJECTS { extremeWingEventMnemonic, extremeWingEventModule, extremeWingEventSeverity, extremeWingEventMsg, extremeWingEventSourceAddr,
				extremeWingEventSourceHostname }
			STATUS current
			DESCRIPTION
				"Translate host name"
				::= { extremeWingTrapsNsmPrefix 12}


		-- 1.3.6.1.4.1.1916.2.131.50.0.16.0.13
		extremeWingTrapNsmIfFailover NOTIFICATION-TYPE
			OBJECTS { extremeWingEventMnemonic, extremeWingEventModule, extremeWingEventSeverity, extremeWingEventMsg, extremeWingEventSourceAddr,
				extremeWingEventSourceHostname }
			STATUS current
			DESCRIPTION
				"Interface failover"
				::= { extremeWingTrapsNsmPrefix 13}


		-- 1.3.6.1.4.1.1916.2.131.50.0.16.0.14
		extremeWingTrapNsmIfFailback NOTIFICATION-TYPE
			OBJECTS { extremeWingEventMnemonic, extremeWingEventModule, extremeWingEventSeverity, extremeWingEventMsg, extremeWingEventSourceAddr,
				extremeWingEventSourceHostname }
			STATUS current
			DESCRIPTION
				"Interface failback"
				::= { extremeWingTrapsNsmPrefix 14}


--Process-monitor module
		--1.3.6.1.4.1.1916.2.131.50.0.17
		extremeWingTrapsPm OBJECT IDENTIFIER ::= { extremeWingNotifications 17 }


		--1.3.6.1.4.1.1916.2.131.50.0.17.0
		extremeWingTrapsPmPrefix OBJECT IDENTIFIER ::= { extremeWingTrapsPm 0 }


		-- 1.3.6.1.4.1.1916.2.131.50.0.17.0.1
		extremeWingTrapPmProcstart NOTIFICATION-TYPE
			OBJECTS { extremeWingEventMnemonic, extremeWingEventModule, extremeWingEventSeverity, extremeWingEventMsg, extremeWingEventSourceAddr,
				extremeWingEventSourceHostname }
			STATUS current
			DESCRIPTION
				"Process started"
				::= { extremeWingTrapsPmPrefix 1}


		-- 1.3.6.1.4.1.1916.2.131.50.0.17.0.2
		extremeWingTrapPmProcrstrt NOTIFICATION-TYPE
			OBJECTS { extremeWingEventMnemonic, extremeWingEventModule, extremeWingEventSeverity, extremeWingEventMsg, extremeWingEventSourceAddr,
				extremeWingEventSourceHostname }
			STATUS current
			DESCRIPTION
				"Process restarted"
				::= { extremeWingTrapsPmPrefix 2}


		-- 1.3.6.1.4.1.1916.2.131.50.0.17.0.3
		extremeWingTrapPmProcmaxrstrt NOTIFICATION-TYPE
			OBJECTS { extremeWingEventMnemonic, extremeWingEventModule, extremeWingEventSeverity, extremeWingEventMsg, extremeWingEventSourceAddr,
				extremeWingEventSourceHostname }
			STATUS current
			DESCRIPTION
				"Process reached max number of restarts"
				::= { extremeWingTrapsPmPrefix 3}


		-- 1.3.6.1.4.1.1916.2.131.50.0.17.0.4
		extremeWingTrapPmProcsysrstrt NOTIFICATION-TYPE
			OBJECTS { extremeWingEventMnemonic, extremeWingEventModule, extremeWingEventSeverity, extremeWingEventMsg, extremeWingEventSourceAddr,
				extremeWingEventSourceHostname }
			STATUS current
			DESCRIPTION
				"Process reached max restarts. Rebooting system."
				::= { extremeWingTrapsPmPrefix 4}


		-- 1.3.6.1.4.1.1916.2.131.50.0.17.0.5
		extremeWingTrapPmProcstop NOTIFICATION-TYPE
			OBJECTS { extremeWingEventMnemonic, extremeWingEventModule, extremeWingEventSeverity, extremeWingEventMsg, extremeWingEventSourceAddr,
				extremeWingEventSourceHostname }
			STATUS current
			DESCRIPTION
				"Process has been stopped"
				::= { extremeWingTrapsPmPrefix 5}


		-- 1.3.6.1.4.1.1916.2.131.50.0.17.0.6
		extremeWingTrapPmProcid NOTIFICATION-TYPE
			OBJECTS { extremeWingEventMnemonic, extremeWingEventModule, extremeWingEventSeverity, extremeWingEventMsg, extremeWingEventSourceAddr,
				extremeWingEventSourceHostname }
			STATUS current
			DESCRIPTION
				"Process changed pid"
				::= { extremeWingTrapsPmPrefix 6}


		-- 1.3.6.1.4.1.1916.2.131.50.0.17.0.7
		extremeWingTrapPmStartupcomplete NOTIFICATION-TYPE
			OBJECTS { extremeWingEventMnemonic, extremeWingEventModule, extremeWingEventSeverity, extremeWingEventMsg, extremeWingEventSourceAddr,
				extremeWingEventSourceHostname }
			STATUS current
			DESCRIPTION
				"System startup completed"
				::= { extremeWingTrapsPmPrefix 7}


		-- 1.3.6.1.4.1.1916.2.131.50.0.17.0.8
		extremeWingTrapPmProcnoresp NOTIFICATION-TYPE
			OBJECTS { extremeWingEventMnemonic, extremeWingEventModule, extremeWingEventSeverity, extremeWingEventMsg, extremeWingEventSourceAddr,
				extremeWingEventSourceHostname }
			STATUS current
			DESCRIPTION
				"Process is not responding"
				::= { extremeWingTrapsPmPrefix 8}


--Radius Configuration Daemon
		--1.3.6.1.4.1.1916.2.131.50.0.18
		extremeWingTrapsRadconf OBJECT IDENTIFIER ::= { extremeWingNotifications 18 }


		--1.3.6.1.4.1.1916.2.131.50.0.18.0
		extremeWingTrapsRadconfPrefix OBJECT IDENTIFIER ::= { extremeWingTrapsRadconf 0 }


		-- 1.3.6.1.4.1.1916.2.131.50.0.18.0.1
		extremeWingTrapRadconfRadiusdstart NOTIFICATION-TYPE
			OBJECTS { extremeWingEventMnemonic, extremeWingEventModule, extremeWingEventSeverity, extremeWingEventMsg, extremeWingEventSourceAddr,
				extremeWingEventSourceHostname }
			STATUS current
			DESCRIPTION
				"RADIUS server started"
				::= { extremeWingTrapsRadconfPrefix 1}


		-- 1.3.6.1.4.1.1916.2.131.50.0.18.0.2
		extremeWingTrapRadconfRadiusdstop NOTIFICATION-TYPE
			OBJECTS { extremeWingEventMnemonic, extremeWingEventModule, extremeWingEventSeverity, extremeWingEventMsg, extremeWingEventSourceAddr,
				extremeWingEventSourceHostname }
			STATUS current
			DESCRIPTION
				"RADIUS server stopped"
				::= { extremeWingTrapsRadconfPrefix 2}


		-- 1.3.6.1.4.1.1916.2.131.50.0.18.0.3
		extremeWingTrapRadconfCouldNotStopRadiusd NOTIFICATION-TYPE
			OBJECTS { extremeWingEventMnemonic, extremeWingEventModule, extremeWingEventSeverity, extremeWingEventMsg, extremeWingEventSourceAddr,
				extremeWingEventSourceHostname }
			STATUS current
			DESCRIPTION
				"Event could-not-stop-radiusd"
				::= { extremeWingTrapsRadconfPrefix 3}


--Radio module
		--1.3.6.1.4.1.1916.2.131.50.0.19
		extremeWingTrapsRadio OBJECT IDENTIFIER ::= { extremeWingNotifications 19 }


		--1.3.6.1.4.1.1916.2.131.50.0.19.0
		extremeWingTrapsRadioPrefix OBJECT IDENTIFIER ::= { extremeWingTrapsRadio 0 }


		-- 1.3.6.1.4.1.1916.2.131.50.0.19.0.1
		extremeWingTrapRadioChannelCountryMismatch NOTIFICATION-TYPE
			OBJECTS { extremeWingEventMnemonic, extremeWingEventModule, extremeWingEventSeverity, extremeWingEventMsg, extremeWingEventSourceAddr,
				extremeWingEventSourceHostname }
			STATUS current
			DESCRIPTION
				"Channel and country of operation mismatch"
				::= { extremeWingTrapsRadioPrefix 1}


		-- 1.3.6.1.4.1.1916.2.131.50.0.19.0.2
		extremeWingTrapRadioRadioStateChange NOTIFICATION-TYPE
			OBJECTS { extremeWingEventMnemonic, extremeWingEventModule, extremeWingEventSeverity, extremeWingEventMsg, extremeWingEventSourceAddr,
				extremeWingEventSourceHostname }
			STATUS current
			DESCRIPTION
				"Radio state changed"
				::= { extremeWingTrapsRadioPrefix 2}


		-- 1.3.6.1.4.1.1916.2.131.50.0.19.0.3
		extremeWingTrapRadioRadarScanStarted NOTIFICATION-TYPE
			OBJECTS { extremeWingEventMnemonic, extremeWingEventModule, extremeWingEventSeverity, extremeWingEventMsg, extremeWingEventSourceAddr,
				extremeWingEventSourceHostname }
			STATUS current
			DESCRIPTION
				"Radar scan started"
				::= { extremeWingTrapsRadioPrefix 3}


		-- 1.3.6.1.4.1.1916.2.131.50.0.19.0.4
		extremeWingTrapRadioRadarScanCompleted NOTIFICATION-TYPE
			OBJECTS { extremeWingEventMnemonic, extremeWingEventModule, extremeWingEventSeverity, extremeWingEventMsg, extremeWingEventSourceAddr,
				extremeWingEventSourceHostname }
			STATUS current
			DESCRIPTION
				"Radar scan completed"
				::= { extremeWingTrapsRadioPrefix 4}


		-- 1.3.6.1.4.1.1916.2.131.50.0.19.0.5
		extremeWingTrapRadioRadarDetected NOTIFICATION-TYPE
			OBJECTS { extremeWingEventMnemonic, extremeWingEventModule, extremeWingEventSeverity, extremeWingEventMsg, extremeWingEventSourceAddr,
				extremeWingEventSourceHostname }
			STATUS current
			DESCRIPTION
				"Radar detected"
				::= { extremeWingTrapsRadioPrefix 5}


		-- 1.3.6.1.4.1.1916.2.131.50.0.19.0.6
		extremeWingTrapRadioRadarDetInfo NOTIFICATION-TYPE
			OBJECTS { extremeWingEventMnemonic, extremeWingEventModule, extremeWingEventSeverity, extremeWingEventMsg, extremeWingEventSourceAddr,
				extremeWingEventSourceHostname }
			STATUS current
			DESCRIPTION
				"Radar info"
				::= { extremeWingTrapsRadioPrefix 6}


		-- 1.3.6.1.4.1.1916.2.131.50.0.19.0.7
		extremeWingTrapRadioResumeHomeChannel NOTIFICATION-TYPE
			OBJECTS { extremeWingEventMnemonic, extremeWingEventModule, extremeWingEventSeverity, extremeWingEventMsg, extremeWingEventSourceAddr,
				extremeWingEventSourceHostname }
			STATUS current
			DESCRIPTION
				"Radio resuming on home channel"
				::= { extremeWingTrapsRadioPrefix 7}


		-- 1.3.6.1.4.1.1916.2.131.50.0.19.0.8
		extremeWingTrapRadioAcsScanStarted NOTIFICATION-TYPE
			OBJECTS { extremeWingEventMnemonic, extremeWingEventModule, extremeWingEventSeverity, extremeWingEventMsg, extremeWingEventSourceAddr,
				extremeWingEventSourceHostname }
			STATUS current
			DESCRIPTION
				"ACS Scan Started"
				::= { extremeWingTrapsRadioPrefix 8}


		-- 1.3.6.1.4.1.1916.2.131.50.0.19.0.9
		extremeWingTrapRadioAcsScanComplete NOTIFICATION-TYPE
			OBJECTS { extremeWingEventMnemonic, extremeWingEventModule, extremeWingEventSeverity, extremeWingEventMsg, extremeWingEventSourceAddr,
				extremeWingEventSourceHostname }
			STATUS current
			DESCRIPTION
				"ACS Scan Complete"
				::= { extremeWingTrapsRadioPrefix 9}


		-- 1.3.6.1.4.1.1916.2.131.50.0.19.0.10
		extremeWingTrapRadioRadioAntennaError NOTIFICATION-TYPE
			OBJECTS { extremeWingEventMnemonic, extremeWingEventModule, extremeWingEventSeverity, extremeWingEventMsg, extremeWingEventSourceAddr,
				extremeWingEventSourceHostname }
			STATUS current
			DESCRIPTION
				"Invalid antenna type on this radio"
				::= { extremeWingTrapsRadioPrefix 10}


		-- 1.3.6.1.4.1.1916.2.131.50.0.19.0.11
		extremeWingTrapRadioRadioAntennaSetting NOTIFICATION-TYPE
			OBJECTS { extremeWingEventMnemonic, extremeWingEventModule, extremeWingEventSeverity, extremeWingEventMsg, extremeWingEventSourceAddr,
				extremeWingEventSourceHostname }
			STATUS current
			DESCRIPTION
				"Antenna type setting on this radio"
				::= { extremeWingTrapsRadioPrefix 11}


--Smart-rf module
		--1.3.6.1.4.1.1916.2.131.50.0.21
		extremeWingTrapsSmrt OBJECT IDENTIFIER ::= { extremeWingNotifications 21 }


		--1.3.6.1.4.1.1916.2.131.50.0.21.0
		extremeWingTrapsSmrtPrefix OBJECT IDENTIFIER ::= { extremeWingTrapsSmrt 0 }


		-- 1.3.6.1.4.1.1916.2.131.50.0.21.0.1
		extremeWingTrapSmrtCalibrationStarted NOTIFICATION-TYPE
			OBJECTS { extremeWingEventMnemonic, extremeWingEventModule, extremeWingEventSeverity, extremeWingEventMsg, extremeWingEventSourceAddr,
				extremeWingEventSourceHostname }
			STATUS current
			DESCRIPTION
				"Calibration started"
				::= { extremeWingTrapsSmrtPrefix 1}


		-- 1.3.6.1.4.1.1916.2.131.50.0.21.0.2
		extremeWingTrapSmrtCalibrationDone NOTIFICATION-TYPE
			OBJECTS { extremeWingEventMnemonic, extremeWingEventModule, extremeWingEventSeverity, extremeWingEventMsg, extremeWingEventSourceAddr,
				extremeWingEventSourceHostname }
			STATUS current
			DESCRIPTION
				"Calibration done"
				::= { extremeWingTrapsSmrtPrefix 2}


		-- 1.3.6.1.4.1.1916.2.131.50.0.21.0.3
		extremeWingTrapSmrtNeighborRecovery NOTIFICATION-TYPE
			OBJECTS { extremeWingEventMnemonic, extremeWingEventModule, extremeWingEventSeverity, extremeWingEventMsg, extremeWingEventSourceAddr,
				extremeWingEventSourceHostname }
			STATUS current
			DESCRIPTION
				"Neighbor recovery power change"
				::= { extremeWingTrapsSmrtPrefix 3}


		-- 1.3.6.1.4.1.1916.2.131.50.0.21.0.4
		extremeWingTrapSmrtPowerAdjustment NOTIFICATION-TYPE
			OBJECTS { extremeWingEventMnemonic, extremeWingEventModule, extremeWingEventSeverity, extremeWingEventMsg, extremeWingEventSourceAddr,
				extremeWingEventSourceHostname }
			STATUS current
			DESCRIPTION
				"Radio power adjustment"
				::= { extremeWingTrapsSmrtPrefix 4}


		-- 1.3.6.1.4.1.1916.2.131.50.0.21.0.5
		extremeWingTrapSmrtInterferenceRecovery NOTIFICATION-TYPE
			OBJECTS { extremeWingEventMnemonic, extremeWingEventModule, extremeWingEventSeverity, extremeWingEventMsg, extremeWingEventSourceAddr,
				extremeWingEventSourceHostname }
			STATUS current
			DESCRIPTION
				"Interference recovery"
				::= { extremeWingTrapsSmrtPrefix 5}


		-- 1.3.6.1.4.1.1916.2.131.50.0.21.0.6
		extremeWingTrapSmrtRootRecovery NOTIFICATION-TYPE
			OBJECTS { extremeWingEventMnemonic, extremeWingEventModule, extremeWingEventSeverity, extremeWingEventMsg, extremeWingEventSourceAddr,
				extremeWingEventSourceHostname }
			STATUS current
			DESCRIPTION
				"Meshpoint root  recovery"
				::= { extremeWingTrapsSmrtPrefix 6}


		-- 1.3.6.1.4.1.1916.2.131.50.0.21.0.7
		extremeWingTrapSmrtCovHoleRecovery NOTIFICATION-TYPE
			OBJECTS { extremeWingEventMnemonic, extremeWingEventModule, extremeWingEventSeverity, extremeWingEventMsg, extremeWingEventSourceAddr,
				extremeWingEventSourceHostname }
			STATUS current
			DESCRIPTION
				"Coverage hole recovery"
				::= { extremeWingTrapsSmrtPrefix 7}


		-- 1.3.6.1.4.1.1916.2.131.50.0.21.0.8
		extremeWingTrapSmrtCovHoleRecoveryDone NOTIFICATION-TYPE
			OBJECTS { extremeWingEventMnemonic, extremeWingEventModule, extremeWingEventSeverity, extremeWingEventMsg, extremeWingEventSourceAddr,
				extremeWingEventSourceHostname }
			STATUS current
			DESCRIPTION
				"Coverage hole recovery done"
				::= { extremeWingTrapsSmrtPrefix 8}


		-- 1.3.6.1.4.1.1916.2.131.50.0.21.0.9
		extremeWingTrapSmrtConfigCleared NOTIFICATION-TYPE
			OBJECTS { extremeWingEventMnemonic, extremeWingEventModule, extremeWingEventSeverity, extremeWingEventMsg, extremeWingEventSourceAddr,
				extremeWingEventSourceHostname }
			STATUS current
			DESCRIPTION
				"Smart-rf configuration cleared"
				::= { extremeWingTrapsSmrtPrefix 9}


		-- 1.3.6.1.4.1.1916.2.131.50.0.21.0.10
		extremeWingTrapSmrtChannelChange NOTIFICATION-TYPE
			OBJECTS { extremeWingEventMnemonic, extremeWingEventModule, extremeWingEventSeverity, extremeWingEventMsg, extremeWingEventSourceAddr,
				extremeWingEventSourceHostname }
			STATUS current
			DESCRIPTION
				"Channel change"
				::= { extremeWingTrapsSmrtPrefix 10}


--smtpnot module
		--1.3.6.1.4.1.1916.2.131.50.0.22
		extremeWingTrapsSmtpnot OBJECT IDENTIFIER ::= { extremeWingNotifications 22 }


		--1.3.6.1.4.1.1916.2.131.50.0.22.0
		extremeWingTrapsSmtpnotPrefix OBJECT IDENTIFIER ::= { extremeWingTrapsSmtpnot 0 }


		-- 1.3.6.1.4.1.1916.2.131.50.0.22.0.1
		extremeWingTrapSmtpnotSmtpauth NOTIFICATION-TYPE
			OBJECTS { extremeWingEventMnemonic, extremeWingEventModule, extremeWingEventSeverity, extremeWingEventMsg, extremeWingEventSourceAddr,
				extremeWingEventSourceHostname }
			STATUS current
			DESCRIPTION
				"User Authentication Failure"
				::= { extremeWingTrapsSmtpnotPrefix 1}


		-- 1.3.6.1.4.1.1916.2.131.50.0.22.0.2
		extremeWingTrapSmtpnotNet NOTIFICATION-TYPE
			OBJECTS { extremeWingEventMnemonic, extremeWingEventModule, extremeWingEventSeverity, extremeWingEventMsg, extremeWingEventSourceAddr,
				extremeWingEventSourceHostname }
			STATUS current
			DESCRIPTION
				"Can not contact server"
				::= { extremeWingTrapsSmtpnotPrefix 2}


		-- 1.3.6.1.4.1.1916.2.131.50.0.22.0.3
		extremeWingTrapSmtpnotSmtpinfo NOTIFICATION-TYPE
			OBJECTS { extremeWingEventMnemonic, extremeWingEventModule, extremeWingEventSeverity, extremeWingEventMsg, extremeWingEventSourceAddr,
				extremeWingEventSourceHostname }
			STATUS current
			DESCRIPTION
				"SMTP information notice"
				::= { extremeWingTrapsSmtpnotPrefix 3}


		-- 1.3.6.1.4.1.1916.2.131.50.0.22.0.4
		extremeWingTrapSmtpnotCfg NOTIFICATION-TYPE
			OBJECTS { extremeWingEventMnemonic, extremeWingEventModule, extremeWingEventSeverity, extremeWingEventMsg, extremeWingEventSourceAddr,
				extremeWingEventSourceHostname }
			STATUS current
			DESCRIPTION
				"Can not read configuration"
				::= { extremeWingTrapsSmtpnotPrefix 4}


		-- 1.3.6.1.4.1.1916.2.131.50.0.22.0.5
		extremeWingTrapSmtpnotCfginc NOTIFICATION-TYPE
			OBJECTS { extremeWingEventMnemonic, extremeWingEventModule, extremeWingEventSeverity, extremeWingEventMsg, extremeWingEventSourceAddr,
				extremeWingEventSourceHostname }
			STATUS current
			DESCRIPTION
				"Incomplete Configuration"
				::= { extremeWingTrapsSmtpnotPrefix 5}


		-- 1.3.6.1.4.1.1916.2.131.50.0.22.0.6
		extremeWingTrapSmtpnotSmtperr NOTIFICATION-TYPE
			OBJECTS { extremeWingEventMnemonic, extremeWingEventModule, extremeWingEventSeverity, extremeWingEventMsg, extremeWingEventSourceAddr,
				extremeWingEventSourceHostname }
			STATUS current
			DESCRIPTION
				"SMTP 5XX Errors"
				::= { extremeWingTrapsSmtpnotPrefix 6}


		-- 1.3.6.1.4.1.1916.2.131.50.0.22.0.7
		extremeWingTrapSmtpnotProto NOTIFICATION-TYPE
			OBJECTS { extremeWingEventMnemonic, extremeWingEventModule, extremeWingEventSeverity, extremeWingEventMsg, extremeWingEventSourceAddr,
				extremeWingEventSourceHostname }
			STATUS current
			DESCRIPTION
				"SMTP Protocol Errors"
				::= { extremeWingTrapsSmtpnotPrefix 7}


--System module
		--1.3.6.1.4.1.1916.2.131.50.0.23
		extremeWingTrapsSystem OBJECT IDENTIFIER ::= { extremeWingNotifications 23 }


		--1.3.6.1.4.1.1916.2.131.50.0.23.0
		extremeWingTrapsSystemPrefix OBJECT IDENTIFIER ::= { extremeWingTrapsSystem 0 }


		-- 1.3.6.1.4.1.1916.2.131.50.0.23.0.1
		extremeWingTrapSystemPanic NOTIFICATION-TYPE
			OBJECTS { extremeWingEventMnemonic, extremeWingEventModule, extremeWingEventSeverity, extremeWingEventMsg, extremeWingEventSourceAddr,
				extremeWingEventSourceHostname }
			STATUS current
			DESCRIPTION
				"Event panic"
				::= { extremeWingTrapsSystemPrefix 1}


		-- 1.3.6.1.4.1.1916.2.131.50.0.23.0.2
		extremeWingTrapSystemHttpErr NOTIFICATION-TYPE
			OBJECTS { extremeWingEventMnemonic, extremeWingEventModule, extremeWingEventSeverity, extremeWingEventMsg, extremeWingEventSourceAddr,
				extremeWingEventSourceHostname }
			STATUS current
			DESCRIPTION
				"Web server did not start"
				::= { extremeWingTrapsSystemPrefix 2}


		-- 1.3.6.1.4.1.1916.2.131.50.0.23.0.3
		extremeWingTrapSystemProcStop NOTIFICATION-TYPE
			OBJECTS { extremeWingEventMnemonic, extremeWingEventModule, extremeWingEventSeverity, extremeWingEventMsg, extremeWingEventSourceAddr,
				extremeWingEventSourceHostname }
			STATUS current
			DESCRIPTION
				"Stopping process"
				::= { extremeWingTrapsSystemPrefix 3}


		-- 1.3.6.1.4.1.1916.2.131.50.0.23.0.4
		extremeWingTrapSystemClockReset NOTIFICATION-TYPE
			OBJECTS { extremeWingEventMnemonic, extremeWingEventModule, extremeWingEventSeverity, extremeWingEventMsg, extremeWingEventSourceAddr,
				extremeWingEventSourceHostname }
			STATUS current
			DESCRIPTION
				"System clock reset"
				::= { extremeWingTrapsSystemPrefix 4}


		-- 1.3.6.1.4.1.1916.2.131.50.0.23.0.5
		extremeWingTrapSystemUiUserAuthFail NOTIFICATION-TYPE
			OBJECTS { extremeWingEventMnemonic, extremeWingEventModule, extremeWingEventSeverity, extremeWingEventMsg, extremeWingEventSourceAddr,
				extremeWingEventSourceHostname }
			STATUS current
			DESCRIPTION
				"GUI user authentication failed"
				::= { extremeWingTrapsSystemPrefix 5}


		-- 1.3.6.1.4.1.1916.2.131.50.0.23.0.6
		extremeWingTrapSystemUiUserAuthSuccess NOTIFICATION-TYPE
			OBJECTS { extremeWingEventMnemonic, extremeWingEventModule, extremeWingEventSeverity, extremeWingEventMsg, extremeWingEventSourceAddr,
				extremeWingEventSourceHostname }
			STATUS current
			DESCRIPTION
				"GUI user authentication successful"
				::= { extremeWingTrapsSystemPrefix 6}


		-- 1.3.6.1.4.1.1916.2.131.50.0.23.0.7
		extremeWingTrapSystemLogin NOTIFICATION-TYPE
			OBJECTS { extremeWingEventMnemonic, extremeWingEventModule, extremeWingEventSeverity, extremeWingEventMsg, extremeWingEventSourceAddr,
				extremeWingEventSourceHostname }
			STATUS current
			DESCRIPTION
				"Successful login"
				::= { extremeWingTrapsSystemPrefix 7}


		-- 1.3.6.1.4.1.1916.2.131.50.0.23.0.8
		extremeWingTrapSystemLoginFail NOTIFICATION-TYPE
			OBJECTS { extremeWingEventMnemonic, extremeWingEventModule, extremeWingEventSeverity, extremeWingEventMsg, extremeWingEventSourceAddr,
				extremeWingEventSourceHostname }
			STATUS current
			DESCRIPTION
				"Failed login attempt - user authentication failed"
				::= { extremeWingTrapsSystemPrefix 8}


		-- 1.3.6.1.4.1.1916.2.131.50.0.23.0.9
		extremeWingTrapSystemLoginFailAccess NOTIFICATION-TYPE
			OBJECTS { extremeWingEventMnemonic, extremeWingEventModule, extremeWingEventSeverity, extremeWingEventMsg, extremeWingEventSourceAddr,
				extremeWingEventSourceHostname }
			STATUS current
			DESCRIPTION
				"Failed login attempt - access violation"
				::= { extremeWingTrapsSystemPrefix 9}


		-- 1.3.6.1.4.1.1916.2.131.50.0.23.0.10
		extremeWingTrapSystemLoginFailBadRole NOTIFICATION-TYPE
			OBJECTS { extremeWingEventMnemonic, extremeWingEventModule, extremeWingEventSeverity, extremeWingEventMsg, extremeWingEventSourceAddr,
				extremeWingEventSourceHostname }
			STATUS current
			DESCRIPTION
				"Failed login attempt - no such user role"
				::= { extremeWingTrapsSystemPrefix 10}


		-- 1.3.6.1.4.1.1916.2.131.50.0.23.0.11
		extremeWingTrapSystemLogout NOTIFICATION-TYPE
			OBJECTS { extremeWingEventMnemonic, extremeWingEventModule, extremeWingEventSeverity, extremeWingEventMsg, extremeWingEventSourceAddr,
				extremeWingEventSourceHostname }
			STATUS current
			DESCRIPTION
				"Logout event"
				::= { extremeWingTrapsSystemPrefix 11}


		-- 1.3.6.1.4.1.1916.2.131.50.0.23.0.12
		extremeWingTrapSystemWarmStart NOTIFICATION-TYPE
			OBJECTS { extremeWingEventMnemonic, extremeWingEventModule, extremeWingEventSeverity, extremeWingEventMsg, extremeWingEventSourceAddr,
				extremeWingEventSourceHostname }
			STATUS current
			DESCRIPTION
				"Event warm-start"
				::= { extremeWingTrapsSystemPrefix 12}


		-- 1.3.6.1.4.1.1916.2.131.50.0.23.0.13
		extremeWingTrapSystemWarmStartRecover NOTIFICATION-TYPE
			OBJECTS { extremeWingEventMnemonic, extremeWingEventModule, extremeWingEventSeverity, extremeWingEventMsg, extremeWingEventSourceAddr,
				extremeWingEventSourceHostname }
			STATUS current
			DESCRIPTION
				"Event warm-start-recover"
				::= { extremeWingTrapsSystemPrefix 13}


		-- 1.3.6.1.4.1.1916.2.131.50.0.23.0.14
		extremeWingTrapSystemColdStart NOTIFICATION-TYPE
			OBJECTS { extremeWingEventMnemonic, extremeWingEventModule, extremeWingEventSeverity, extremeWingEventMsg, extremeWingEventSourceAddr,
				extremeWingEventSourceHostname }
			STATUS current
			DESCRIPTION
				"Event cold-start"
				::= { extremeWingTrapsSystemPrefix 14}


		-- 1.3.6.1.4.1.1916.2.131.50.0.23.0.15
		extremeWingTrapSystemServerUnreachable NOTIFICATION-TYPE
			OBJECTS { extremeWingEventMnemonic, extremeWingEventModule, extremeWingEventSeverity, extremeWingEventMsg, extremeWingEventSourceAddr,
				extremeWingEventSourceHostname }
			STATUS current
			DESCRIPTION
				"Event server-unreachable"
				::= { extremeWingTrapsSystemPrefix 15}


		-- 1.3.6.1.4.1.1916.2.131.50.0.23.0.16
		extremeWingTrapSystemPeriodicHeartBeat NOTIFICATION-TYPE
			OBJECTS { extremeWingEventMnemonic, extremeWingEventModule, extremeWingEventSeverity, extremeWingEventMsg, extremeWingEventSourceAddr,
				extremeWingEventSourceHostname }
			STATUS current
			DESCRIPTION
				"Event periodic-heart-beat"
				::= { extremeWingTrapsSystemPrefix 16}


		-- 1.3.6.1.4.1.1916.2.131.50.0.23.0.17
		extremeWingTrapSystemConfigCommit NOTIFICATION-TYPE
			OBJECTS { extremeWingEventMnemonic, extremeWingEventModule, extremeWingEventSeverity, extremeWingEventMsg, extremeWingEventSourceAddr,
				extremeWingEventSourceHostname }
			STATUS current
			DESCRIPTION
				"Configuration commit"
				::= { extremeWingTrapsSystemPrefix 17}


		-- 1.3.6.1.4.1.1916.2.131.50.0.23.0.18
		extremeWingTrapSystemSystemAutoupEnable NOTIFICATION-TYPE
			OBJECTS { extremeWingEventMnemonic, extremeWingEventModule, extremeWingEventSeverity, extremeWingEventMsg, extremeWingEventSourceAddr,
				extremeWingEventSourceHostname }
			STATUS current
			DESCRIPTION
				"Auto upgrade module is enabled"
				::= { extremeWingTrapsSystemPrefix 18}


		-- 1.3.6.1.4.1.1916.2.131.50.0.23.0.19
		extremeWingTrapSystemSystemAutoupDisable NOTIFICATION-TYPE
			OBJECTS { extremeWingEventMnemonic, extremeWingEventModule, extremeWingEventSeverity, extremeWingEventMsg, extremeWingEventSourceAddr,
				extremeWingEventSourceHostname }
			STATUS current
			DESCRIPTION
				"Auto upgrade module is disabled"
				::= { extremeWingTrapsSystemPrefix 19}


		-- 1.3.6.1.4.1.1916.2.131.50.0.23.0.20
		extremeWingTrapSystemMaatLight NOTIFICATION-TYPE
			OBJECTS { extremeWingEventMnemonic, extremeWingEventModule, extremeWingEventSeverity, extremeWingEventMsg, extremeWingEventSourceAddr,
				extremeWingEventSourceHostname }
			STATUS current
			DESCRIPTION
				"Notice on action on RIM radio(s) from Maat Light module"
				::= { extremeWingTrapsSystemPrefix 20}


		-- 1.3.6.1.4.1.1916.2.131.50.0.23.0.21
		extremeWingTrapSystemDevupRfdFail NOTIFICATION-TYPE
			OBJECTS { extremeWingEventMnemonic, extremeWingEventModule, extremeWingEventSeverity, extremeWingEventMsg, extremeWingEventSourceAddr,
				extremeWingEventSourceHostname }
			STATUS current
			DESCRIPTION
				"device-upgrade for device failed on rf-domain manager"
				::= { extremeWingTrapsSystemPrefix 21}


		-- 1.3.6.1.4.1.1916.2.131.50.0.23.0.22
		extremeWingTrapSystemGuestUserExp NOTIFICATION-TYPE
			OBJECTS { extremeWingEventMnemonic, extremeWingEventModule, extremeWingEventSeverity, extremeWingEventMsg, extremeWingEventSourceAddr,
				extremeWingEventSourceHostname }
			STATUS current
			DESCRIPTION
				"Guest user purging"
				::= { extremeWingTrapsSystemPrefix 22}


--Wireless IPS module
		--1.3.6.1.4.1.1916.2.131.50.0.24
		extremeWingTrapsWips OBJECT IDENTIFIER ::= { extremeWingNotifications 24 }


		--1.3.6.1.4.1.1916.2.131.50.0.24.0
		extremeWingTrapsWipsPrefix OBJECT IDENTIFIER ::= { extremeWingTrapsWips 0 }


		-- 1.3.6.1.4.1.1916.2.131.50.0.24.0.1
		extremeWingTrapWipsWipsEvent NOTIFICATION-TYPE
			OBJECTS { extremeWingEventMnemonic, extremeWingEventModule, extremeWingEventSeverity, extremeWingEventMsg, extremeWingEventSourceAddr,
				extremeWingEventSourceHostname }
			STATUS current
			DESCRIPTION
				"WIPS event triggered"
				::= { extremeWingTrapsWipsPrefix 1}


		-- 1.3.6.1.4.1.1916.2.131.50.0.24.0.2
		extremeWingTrapWipsWipsClientBlacklisted NOTIFICATION-TYPE
			OBJECTS { extremeWingEventMnemonic, extremeWingEventModule, extremeWingEventSeverity, extremeWingEventMsg, extremeWingEventSourceAddr,
				extremeWingEventSourceHostname }
			STATUS current
			DESCRIPTION
				"Client blacklisted by WIPS"
				::= { extremeWingTrapsWipsPrefix 2}


		-- 1.3.6.1.4.1.1916.2.131.50.0.24.0.3
		extremeWingTrapWipsWipsClientRemBlacklist NOTIFICATION-TYPE
			OBJECTS { extremeWingEventMnemonic, extremeWingEventModule, extremeWingEventSeverity, extremeWingEventMsg, extremeWingEventSourceAddr,
				extremeWingEventSourceHostname }
			STATUS current
			DESCRIPTION
				"Client cleared from WIPS blacklist"
				::= { extremeWingTrapsWipsPrefix 3}


--802.1X Authentication
		--1.3.6.1.4.1.1916.2.131.50.0.25
		extremeWingTrapsDot1x OBJECT IDENTIFIER ::= { extremeWingNotifications 25 }


		--1.3.6.1.4.1.1916.2.131.50.0.25.0
		extremeWingTrapsDot1xPrefix OBJECT IDENTIFIER ::= { extremeWingTrapsDot1x 0 }


		-- 1.3.6.1.4.1.1916.2.131.50.0.25.0.1
		extremeWingTrapDot1xDot1xSuccess NOTIFICATION-TYPE
			OBJECTS { extremeWingEventMnemonic, extremeWingEventModule, extremeWingEventSeverity, extremeWingEventMsg, extremeWingEventSourceAddr,
				extremeWingEventSourceHostname }
			STATUS current
			DESCRIPTION
				"802.1x authentication successful"
				::= { extremeWingTrapsDot1xPrefix 1}


		-- 1.3.6.1.4.1.1916.2.131.50.0.25.0.2
		extremeWingTrapDot1xDot1xFailed NOTIFICATION-TYPE
			OBJECTS { extremeWingEventMnemonic, extremeWingEventModule, extremeWingEventSeverity, extremeWingEventMsg, extremeWingEventSourceAddr,
				extremeWingEventSourceHostname }
			STATUS current
			DESCRIPTION
				"802.1x authentication failure"
				::= { extremeWingTrapsDot1xPrefix 2}


--Critical Resource Monitoring
		--1.3.6.1.4.1.1916.2.131.50.0.26
		extremeWingTrapsCrm OBJECT IDENTIFIER ::= { extremeWingNotifications 26 }


		--1.3.6.1.4.1.1916.2.131.50.0.26.0
		extremeWingTrapsCrmPrefix OBJECT IDENTIFIER ::= { extremeWingTrapsCrm 0 }


		-- 1.3.6.1.4.1.1916.2.131.50.0.26.0.1
		extremeWingTrapCrmCriticalResourceUp NOTIFICATION-TYPE
			OBJECTS { extremeWingEventMnemonic, extremeWingEventModule, extremeWingEventSeverity, extremeWingEventMsg, extremeWingEventSourceAddr,
				extremeWingEventSourceHostname }
			STATUS current
			DESCRIPTION
				"Critical resource is up"
				::= { extremeWingTrapsCrmPrefix 1}


		-- 1.3.6.1.4.1.1916.2.131.50.0.26.0.2
		extremeWingTrapCrmCriticalResourceDown NOTIFICATION-TYPE
			OBJECTS { extremeWingEventMnemonic, extremeWingEventModule, extremeWingEventSeverity, extremeWingEventMsg, extremeWingEventSourceAddr,
				extremeWingEventSourceHostname }
			STATUS current
			DESCRIPTION
				"Critical resource is down"
				::= { extremeWingTrapsCrmPrefix 2}


--Virtual Router Redundancy Protocol
		--1.3.6.1.4.1.1916.2.131.50.0.27
		extremeWingTrapsVrrp OBJECT IDENTIFIER ::= { extremeWingNotifications 27 }


		--1.3.6.1.4.1.1916.2.131.50.0.27.0
		extremeWingTrapsVrrpPrefix OBJECT IDENTIFIER ::= { extremeWingTrapsVrrp 0 }


		-- 1.3.6.1.4.1.1916.2.131.50.0.27.0.1
		extremeWingTrapVrrpVrrpStateChange NOTIFICATION-TYPE
			OBJECTS { extremeWingEventMnemonic, extremeWingEventModule, extremeWingEventSeverity, extremeWingEventMsg, extremeWingEventSourceAddr,
				extremeWingEventSourceHostname }
			STATUS current
			DESCRIPTION
				"VRRP State Transition "
				::= { extremeWingTrapsVrrpPrefix 1}


		-- 1.3.6.1.4.1.1916.2.131.50.0.27.0.2
		extremeWingTrapVrrpVrrpVipSubnetMismatch NOTIFICATION-TYPE
			OBJECTS { extremeWingEventMnemonic, extremeWingEventModule, extremeWingEventSeverity, extremeWingEventMsg, extremeWingEventSourceAddr,
				extremeWingEventSourceHostname }
			STATUS current
			DESCRIPTION
				"VRRP IP not overlapping with interface addresses"
				::= { extremeWingTrapsVrrpPrefix 2}


		-- 1.3.6.1.4.1.1916.2.131.50.0.27.0.3
		extremeWingTrapVrrpVrrpMonitorChange NOTIFICATION-TYPE
			OBJECTS { extremeWingEventMnemonic, extremeWingEventModule, extremeWingEventSeverity, extremeWingEventMsg, extremeWingEventSourceAddr,
				extremeWingEventSourceHostname }
			STATUS current
			DESCRIPTION
				"VRRP Monitor Link State Change"
				::= { extremeWingTrapsVrrpPrefix 3}


--Layer 2 Tunneling Protocol Version 3
		--1.3.6.1.4.1.1916.2.131.50.0.28
		extremeWingTrapsL2tpv3 OBJECT IDENTIFIER ::= { extremeWingNotifications 28 }


		--1.3.6.1.4.1.1916.2.131.50.0.28.0
		extremeWingTrapsL2tpv3Prefix OBJECT IDENTIFIER ::= { extremeWingTrapsL2tpv3 0 }


		-- 1.3.6.1.4.1.1916.2.131.50.0.28.0.1
		extremeWingTrapL2tpv3L2tpv3TunnelUp NOTIFICATION-TYPE
			OBJECTS { extremeWingEventMnemonic, extremeWingEventModule, extremeWingEventSeverity, extremeWingEventMsg, extremeWingEventSourceAddr,
				extremeWingEventSourceHostname }
			STATUS current
			DESCRIPTION
				"L2TPV3 tunnel is up"
				::= { extremeWingTrapsL2tpv3Prefix 1}


		-- 1.3.6.1.4.1.1916.2.131.50.0.28.0.2
		extremeWingTrapL2tpv3L2tpv3TunnelDown NOTIFICATION-TYPE
			OBJECTS { extremeWingEventMnemonic, extremeWingEventModule, extremeWingEventSeverity, extremeWingEventMsg, extremeWingEventSourceAddr,
				extremeWingEventSourceHostname }
			STATUS current
			DESCRIPTION
				"L2TPV3 tunnel is DOWN"
				::= { extremeWingTrapsL2tpv3Prefix 2}


--isdn module
		--1.3.6.1.4.1.1916.2.131.50.0.29
		extremeWingTrapsIsdn OBJECT IDENTIFIER ::= { extremeWingNotifications 29 }


		--1.3.6.1.4.1.1916.2.131.50.0.29.0
		extremeWingTrapsIsdnPrefix OBJECT IDENTIFIER ::= { extremeWingTrapsIsdn 0 }


		-- 1.3.6.1.4.1.1916.2.131.50.0.29.0.1
		extremeWingTrapIsdnIsdnEmerg NOTIFICATION-TYPE
			OBJECTS { extremeWingEventMnemonic, extremeWingEventModule, extremeWingEventSeverity, extremeWingEventMsg, extremeWingEventSourceAddr,
				extremeWingEventSourceHostname }
			STATUS current
			DESCRIPTION
				"Event isdn-emerg"
				::= { extremeWingTrapsIsdnPrefix 1}


		-- 1.3.6.1.4.1.1916.2.131.50.0.29.0.2
		extremeWingTrapIsdnIsdnAlert NOTIFICATION-TYPE
			OBJECTS { extremeWingEventMnemonic, extremeWingEventModule, extremeWingEventSeverity, extremeWingEventMsg, extremeWingEventSourceAddr,
				extremeWingEventSourceHostname }
			STATUS current
			DESCRIPTION
				"Event isdn-alert"
				::= { extremeWingTrapsIsdnPrefix 2}


		-- 1.3.6.1.4.1.1916.2.131.50.0.29.0.3
		extremeWingTrapIsdnIsdnCrit NOTIFICATION-TYPE
			OBJECTS { extremeWingEventMnemonic, extremeWingEventModule, extremeWingEventSeverity, extremeWingEventMsg, extremeWingEventSourceAddr,
				extremeWingEventSourceHostname }
			STATUS current
			DESCRIPTION
				"Event isdn-crit"
				::= { extremeWingTrapsIsdnPrefix 3}


		-- 1.3.6.1.4.1.1916.2.131.50.0.29.0.4
		extremeWingTrapIsdnIsdnErr NOTIFICATION-TYPE
			OBJECTS { extremeWingEventMnemonic, extremeWingEventModule, extremeWingEventSeverity, extremeWingEventMsg, extremeWingEventSourceAddr,
				extremeWingEventSourceHostname }
			STATUS current
			DESCRIPTION
				"Event isdn-err"
				::= { extremeWingTrapsIsdnPrefix 4}


		-- 1.3.6.1.4.1.1916.2.131.50.0.29.0.5
		extremeWingTrapIsdnIsdnWarning NOTIFICATION-TYPE
			OBJECTS { extremeWingEventMnemonic, extremeWingEventModule, extremeWingEventSeverity, extremeWingEventMsg, extremeWingEventSourceAddr,
				extremeWingEventSourceHostname }
			STATUS current
			DESCRIPTION
				"Event isdn-warning"
				::= { extremeWingTrapsIsdnPrefix 5}


		-- 1.3.6.1.4.1.1916.2.131.50.0.29.0.6
		extremeWingTrapIsdnIsdnNotice NOTIFICATION-TYPE
			OBJECTS { extremeWingEventMnemonic, extremeWingEventModule, extremeWingEventSeverity, extremeWingEventMsg, extremeWingEventSourceAddr,
				extremeWingEventSourceHostname }
			STATUS current
			DESCRIPTION
				"Event isdn-notice"
				::= { extremeWingTrapsIsdnPrefix 6}


		-- 1.3.6.1.4.1.1916.2.131.50.0.29.0.7
		extremeWingTrapIsdnIsdnInfo NOTIFICATION-TYPE
			OBJECTS { extremeWingEventMnemonic, extremeWingEventModule, extremeWingEventSeverity, extremeWingEventMsg, extremeWingEventSourceAddr,
				extremeWingEventSourceHostname }
			STATUS current
			DESCRIPTION
				"Event isdn-info"
				::= { extremeWingTrapsIsdnPrefix 7}


		-- 1.3.6.1.4.1.1916.2.131.50.0.29.0.8
		extremeWingTrapIsdnIsdnDebug NOTIFICATION-TYPE
			OBJECTS { extremeWingEventMnemonic, extremeWingEventModule, extremeWingEventSeverity, extremeWingEventMsg, extremeWingEventSourceAddr,
				extremeWingEventSourceHostname }
			STATUS current
			DESCRIPTION
				"Event isdn-debug"
				::= { extremeWingTrapsIsdnPrefix 8}


--Management Services
		--1.3.6.1.4.1.1916.2.131.50.0.30
		extremeWingTrapsMgmt OBJECT IDENTIFIER ::= { extremeWingNotifications 30 }


		--1.3.6.1.4.1.1916.2.131.50.0.30.0
		extremeWingTrapsMgmtPrefix OBJECT IDENTIFIER ::= { extremeWingTrapsMgmt 0 }


		-- 1.3.6.1.4.1.1916.2.131.50.0.30.0.1
		extremeWingTrapMgmtLogKeyDeleted NOTIFICATION-TYPE
			OBJECTS { extremeWingEventMnemonic, extremeWingEventModule, extremeWingEventSeverity, extremeWingEventMsg, extremeWingEventSourceAddr,
				extremeWingEventSourceHostname }
			STATUS current
			DESCRIPTION
				"Rsakey associated with ssh is deleted"
				::= { extremeWingTrapsMgmtPrefix 1}


		-- 1.3.6.1.4.1.1916.2.131.50.0.30.0.2
		extremeWingTrapMgmtLogKeyRestored NOTIFICATION-TYPE
			OBJECTS { extremeWingEventMnemonic, extremeWingEventModule, extremeWingEventSeverity, extremeWingEventMsg, extremeWingEventSourceAddr,
				extremeWingEventSourceHostname }
			STATUS current
			DESCRIPTION
				"Rsakey associated with ssh is added"
				::= { extremeWingTrapsMgmtPrefix 2}


		-- 1.3.6.1.4.1.1916.2.131.50.0.30.0.3
		extremeWingTrapMgmtLogTrustpointDeleted NOTIFICATION-TYPE
			OBJECTS { extremeWingEventMnemonic, extremeWingEventModule, extremeWingEventSeverity, extremeWingEventMsg, extremeWingEventSourceAddr,
				extremeWingEventSourceHostname }
			STATUS current
			DESCRIPTION
				"Trustpoint associated with https is deleted "
				::= { extremeWingTrapsMgmtPrefix 3}


		-- 1.3.6.1.4.1.1916.2.131.50.0.30.0.4
		extremeWingTrapMgmtLogHttpStart NOTIFICATION-TYPE
			OBJECTS { extremeWingEventMnemonic, extremeWingEventModule, extremeWingEventSeverity, extremeWingEventMsg, extremeWingEventSourceAddr,
				extremeWingEventSourceHostname }
			STATUS current
			DESCRIPTION
				"Web server started in external mode"
				::= { extremeWingTrapsMgmtPrefix 4}


		-- 1.3.6.1.4.1.1916.2.131.50.0.30.0.5
		extremeWingTrapMgmtLogHttpLocalStart NOTIFICATION-TYPE
			OBJECTS { extremeWingEventMnemonic, extremeWingEventModule, extremeWingEventSeverity, extremeWingEventMsg, extremeWingEventSourceAddr,
				extremeWingEventSourceHostname }
			STATUS current
			DESCRIPTION
				"Web server started in local mode"
				::= { extremeWingTrapsMgmtPrefix 5}


		-- 1.3.6.1.4.1.1916.2.131.50.0.30.0.6
		extremeWingTrapMgmtLogHttpsStart NOTIFICATION-TYPE
			OBJECTS { extremeWingEventMnemonic, extremeWingEventModule, extremeWingEventSeverity, extremeWingEventMsg, extremeWingEventSourceAddr,
				extremeWingEventSourceHostname }
			STATUS current
			DESCRIPTION
				"Secure Web server started"
				::= { extremeWingTrapsMgmtPrefix 6}


		-- 1.3.6.1.4.1.1916.2.131.50.0.30.0.7
		extremeWingTrapMgmtLogHttpsWait NOTIFICATION-TYPE
			OBJECTS { extremeWingEventMnemonic, extremeWingEventModule, extremeWingEventSeverity, extremeWingEventMsg, extremeWingEventSourceAddr,
				extremeWingEventSourceHostname }
			STATUS current
			DESCRIPTION
				"Waiting for web server to start"
				::= { extremeWingTrapsMgmtPrefix 7}


		-- 1.3.6.1.4.1.1916.2.131.50.0.30.0.8
		extremeWingTrapMgmtLogHttpInit NOTIFICATION-TYPE
			OBJECTS { extremeWingEventMnemonic, extremeWingEventModule, extremeWingEventSeverity, extremeWingEventMsg, extremeWingEventSourceAddr,
				extremeWingEventSourceHostname }
			STATUS current
			DESCRIPTION
				"Web server started"
				::= { extremeWingTrapsMgmtPrefix 8}



		
		-- 1.3.6.1.4.1.1916.2.131.50.1
		extremeWingObjects OBJECT IDENTIFIER ::= { extremeWingMIB 1 }

		
		-- 1.3.6.1.4.1.1916.2.131.50.1.1
		extremeWingSysoids OBJECT IDENTIFIER ::= { extremeWingObjects 1 }

		
		-- 1.3.6.1.4.1.1916.2.131.50.1.1.1
		extremeWingSysoidAp4511 OBJECT-IDENTITY
			STATUS current
			DESCRIPTION 
				"AP4511 system object identifier"
			::= { extremeWingSysoids 1 }

		
		-- 1.3.6.1.4.1.1916.2.131.50.1.1.2
		extremeWingSysoidAp4521 OBJECT-IDENTITY
			STATUS current
			DESCRIPTION 
				"AP4521 system object identifier"
			::= { extremeWingSysoids 2 }

		
		-- 1.3.6.1.4.1.1916.2.131.50.1.1.4
		extremeWingSysoidAp4532 OBJECT-IDENTITY
			STATUS current
			DESCRIPTION 
				"AP4532 system object identifier"
			::= { extremeWingSysoids 4 }

		
		-- 1.3.6.1.4.1.1916.2.131.50.1.1.8
		extremeWingSysoidAp4760 OBJECT-IDENTITY
			STATUS current
			DESCRIPTION 
				"AP4760 system object identifier"
			::= { extremeWingSysoids 8 }

		
		-- 1.3.6.1.4.1.1916.2.131.50.1.1.10
		extremeWingSysoidAp4600 OBJECT-IDENTITY
			STATUS current
			DESCRIPTION 
				"AP4600 system object identifier"
			::= { extremeWingSysoids 10 }

		
		-- 1.3.6.1.4.1.1916.2.131.50.1.1.11
		extremeWingSysoidAp4021 OBJECT-IDENTITY
			STATUS current
			DESCRIPTION 
				"AP4021 system object identifier"
			::= { extremeWingSysoids 11 }

		
		-- 1.3.6.1.4.1.1916.2.131.50.1.1.12
		extremeWingSysoidAp4022 OBJECT-IDENTITY
			STATUS current
			DESCRIPTION 
				"AP4022 system object identifier"
			::= { extremeWingSysoids 12 }

		
		-- 1.3.6.1.4.1.1916.2.131.50.1.1.13
		extremeWingSysoidAp4522 OBJECT-IDENTITY
			STATUS current
			DESCRIPTION 
				"AP4522 system object identifier"
			::= { extremeWingSysoids 13 }

		
		-- 1.3.6.1.4.1.1916.2.131.50.1.1.20
		extremeWingSysoidAp4832 OBJECT-IDENTITY
			STATUS current
			DESCRIPTION 
				"AP4832 system object identifier"
			::= { extremeWingSysoids 20 }


                -- 1.3.6.1.4.1.1916.2.131.50.1.1.21
                extremeWingSysoidWiModOD01 OBJECT-IDENTITY
                        STATUS current
                        DESCRIPTION
                                "WiModOD01 system object identifier"
                        ::= { extremeWingSysoids 21 }


               -- 1.3.6.1.4.1.1916.2.131.50.1.1.24
               extremeWingSysoid9772WiSCL OBJECT-IDENTITY
                        STATUS current
                        DESCRIPTION
                                "NX9500 9772-WiSC-L system object identifier"
                        ::= { extremeWingSysoids 24 }

		
		-- 1.3.6.1.4.1.1916.2.131.50.1.1.25
		extremeWingSysoidAp6562 OBJECT-IDENTITY
			STATUS current
			DESCRIPTION 
				"AP6562 system object identifier"
			::= { extremeWingSysoids 25 }

		
		-- 1.3.6.1.4.1.1916.2.131.50.1.1.26
		extremeWingSysoidAp8232 OBJECT-IDENTITY
			STATUS current
			DESCRIPTION 
				"AP8232 system object identifier"
			::= { extremeWingSysoids 26 }

		
		-- 1.3.6.1.4.1.1916.2.131.50.1.1.27
		extremeWingSysoidNx9510 OBJECT-IDENTITY
			STATUS current
			DESCRIPTION 
				"NX9510 system object identifier"
			::= { extremeWingSysoids 27 }

		-- 1.3.6.1.4.1.1916.2.131.50.1.1.31
		extremeWingSysoidAP5142 OBJECT-IDENTITY
			STATUS current
			DESCRIPTION 
				"AP5142 system object identifier"
			::= { extremeWingSysoids 31 }
		
		-- 1.3.6.1.4.1.1916.2.131.50.1.1.32
		extremeWingSysoidNX7510 OBJECT-IDENTITY
			STATUS current
			DESCRIPTION 
				"NX7510 system object identifier"
			::= { extremeWingSysoids 32 }

		-- 1.3.6.1.4.1.1916.2.131.50.1.1.33
		extremeWingSysoidNX7520 OBJECT-IDENTITY
			STATUS current
			DESCRIPTION 
				"NX7520 system object identifier"
			::= { extremeWingSysoids 33 }

		-- 1.3.6.1.4.1.1916.2.131.50.1.1.34
		extremeWingSysoidNX7530 OBJECT-IDENTITY
			STATUS current
			DESCRIPTION 
				"NX7530 system object identifier"
			::= { extremeWingSysoids 34 }

		-- 1.3.6.1.4.1.1916.2.131.50.1.1.35
		extremeWingSysoidWM3400 OBJECT-IDENTITY
			STATUS current
			DESCRIPTION 
				"WiNG 5.X WM3400 system object identifier"
			::= { extremeWingSysoids 35 }

		-- 1.3.6.1.4.1.1916.2.131.50.1.1.36
		extremeWingSysoidWM3600 OBJECT-IDENTITY
			STATUS current
			DESCRIPTION 
				"WiNG 5.X WM3600 system object identifier"
			::= { extremeWingSysoids 36 }

		-- 1.3.6.1.4.1.1916.2.131.50.1.1.37
		extremeWingSysoidWM3700 OBJECT-IDENTITY
			STATUS current
			DESCRIPTION 
				"WiNG 5.X WM3700 system object identifier"
			::= { extremeWingSysoids 37 }

		-- 1.3.6.1.4.1.1916.2.131.50.1.1.38
		extremeWingSysoidNX7500 OBJECT-IDENTITY
			STATUS current
			DESCRIPTION 
				"NX7500 system object identifier"
			::= { extremeWingSysoids 38 }

		-- 1.3.6.1.4.1.1916.2.131.50.1.2
		extremeWingNotificationsObjects OBJECT IDENTIFIER ::= { extremeWingObjects 2 }

		
		-- 1.3.6.1.4.1.1916.2.131.50.1.2.1
		extremeWingEvent OBJECT IDENTIFIER ::= { extremeWingNotificationsObjects 1 }

		
		-- 1.3.6.1.4.1.1916.2.131.50.1.2.1.1
		extremeWingEventMnemonic OBJECT-TYPE
			SYNTAX DisplayString
			MAX-ACCESS accessible-for-notify
			STATUS current
			DESCRIPTION
				"Event mnemonic."
			::= { extremeWingEvent 1 }

		
		-- 1.3.6.1.4.1.1916.2.131.50.1.2.1.2
		extremeWingEventModule OBJECT-TYPE
			SYNTAX DisplayString
			MAX-ACCESS accessible-for-notify
			STATUS current
			DESCRIPTION
				"The module that generated the event."
			::= { extremeWingEvent 2 }

		
		-- 1.3.6.1.4.1.1916.2.131.50.1.2.1.3
		extremeWingEventSeverity OBJECT-TYPE
			SYNTAX INTEGER
				{
				emergency(0),
				alert(1),
				critical(2),
				error(3),
				warning(4),
				notice(5),
				information(6),
				debug(7)
				}
			MAX-ACCESS accessible-for-notify
			STATUS current
			DESCRIPTION
				"Severity of the event."
			::= { extremeWingEvent 3 }

		
		-- 1.3.6.1.4.1.1916.2.131.50.1.2.1.4
		extremeWingEventMsg OBJECT-TYPE
			SYNTAX DisplayString
			MAX-ACCESS accessible-for-notify
			STATUS current
			DESCRIPTION
				"Formatted message for the event."
			::= { extremeWingEvent 4 }

		
		-- 1.3.6.1.4.1.1916.2.131.50.1.2.1.5
		extremeWingEventSourceAddr OBJECT-TYPE
			SYNTAX MacAddress
			MAX-ACCESS accessible-for-notify
			STATUS current
			DESCRIPTION
				"Address of the device that generated the event."
			::= { extremeWingEvent 5 }

		
		-- 1.3.6.1.4.1.1916.2.131.50.1.2.1.6
		extremeWingEventSourceHostname OBJECT-TYPE
			SYNTAX DisplayString
			MAX-ACCESS accessible-for-notify
			STATUS current
			DESCRIPTION
				"Hostname of the device that generated the event."
			::= { extremeWingEvent 6 }

		
		-- 1.3.6.1.4.1.1916.2.131.50.1.3
		extremeWingConfig OBJECT IDENTIFIER ::= { extremeWingObjects 3 }

		
-- Extensions to mib-2.system
		-- 1.3.6.1.4.1.1916.2.131.50.1.3.1
		extremeWingCfgSys OBJECT IDENTIFIER ::= { extremeWingConfig 1 }

		
		-- 1.3.6.1.4.1.1916.2.131.50.1.3.1.5
		extremeWingConfigSysMacAddr OBJECT-TYPE
			SYNTAX DisplayString
			MAX-ACCESS read-only
			STATUS current
			DESCRIPTION
				"MAC address of the system.
				
				XPath: /extremeWing-config/device[mac='self']/mac"
			::= { extremeWingCfgSys 5 }

		
-- System commit parameters
		-- 1.3.6.1.4.1.1916.2.131.50.1.3.1.6
		extremeWingCfgSysCommit OBJECT IDENTIFIER ::= { extremeWingCfgSys 6 }

		
		-- 1.3.6.1.4.1.1916.2.131.50.1.3.1.6.1
		extremeWingCfgSysCommitLastError OBJECT-TYPE
			SYNTAX DisplayString
			MAX-ACCESS read-only
			STATUS current
			DESCRIPTION
				"A short while after a successful SNMP set operation,
				the system does an automatic commit. The automatic commit
				may fail for reasons including invalid values.
				
				This object contains the error message from
				the last automatic commit.
				
				Be sure to check this object after a few SNMP set operations
				to make sure that the commit is successful.
				
				In case of error, clear the error by setting the object(s)
				corresponding to the failed configuration item(s) with
				the correct values."
			::= { extremeWingCfgSysCommit 1 }

		
		-- 1.3.6.1.4.1.1916.2.131.50.1.3.1.7
		extremeWingCfgSysRunningConfigChecksum OBJECT-TYPE
			SYNTAX DisplayString
			MAX-ACCESS read-only
			STATUS current
			DESCRIPTION
				"MD5 checksum of system:running-config.
				
				XPath: /extremeWing-stats/device/self/config-checksum"
			::= { extremeWingCfgSys 7 }

		
-- /extremeWing-config/version
		-- 1.3.6.1.4.1.1916.2.131.50.1.3.2
		extremeWingCfgVersion OBJECT IDENTIFIER ::= { extremeWingConfig 2 }

		
		-- 1.3.6.1.4.1.1916.2.131.50.1.3.2.1
		extremeWingCfgVersionVal OBJECT-TYPE
			SYNTAX DisplayString
			MAX-ACCESS read-only
			STATUS current
			DESCRIPTION
				"Version of configuration
				
				XPath: /extremeWing-config/version[name=default]/version"
			::= { extremeWingCfgVersion 1 }

		
-- /extremeWing-config/password_encryption
		-- 1.3.6.1.4.1.1916.2.131.50.1.3.3
		extremeWingCfgPasswordEnc OBJECT IDENTIFIER ::= { extremeWingConfig 3 }

		
		-- 1.3.6.1.4.1.1916.2.131.50.1.3.3.1
		extremeWingCfgPasswordEncVal OBJECT-TYPE
			SYNTAX OCTET STRING
			MAX-ACCESS read-only
			STATUS current
			DESCRIPTION
				"sha256 digest as a hex string of the passphrase used to
				encrypt passwords in the configuration or
				zero length string when encryption is disabled.
				
				XPath: /extremeWing-config/password_encryption[name=default]/password_encryption"
			::= { extremeWingCfgPasswordEnc 1 }

		
-- /extremeWing-config/password_encryption/_set_pe_
		-- 1.3.6.1.4.1.1916.2.131.50.1.3.3.2
		extremeWingCfgPasswordEncSet OBJECT IDENTIFIER ::= { extremeWingCfgPasswordEnc 2 }

		
		-- 1.3.6.1.4.1.1916.2.131.50.1.3.3.2.1
		extremeWingCfgPasswordEncSetOldPassphrase OBJECT-TYPE
			SYNTAX DisplayString
			MAX-ACCESS read-write
			STATUS current
			DESCRIPTION
				"This object is used to encrypt passwords in the configuration.
				To set encryption passphrase with validation this object
				must be set with the current passphrase.
				
				This object is write-only, read simply returns zero length
				string.
				
				XPath: /extremeWing-config/password_encryption[name=default]/_set_pe_/old_pwd"
			::= { extremeWingCfgPasswordEncSet 1 }

		
		-- 1.3.6.1.4.1.1916.2.131.50.1.3.3.2.2
		extremeWingCfgPasswordEncSetNewPassphrase OBJECT-TYPE
			SYNTAX DisplayString
			MAX-ACCESS read-write
			STATUS current
			DESCRIPTION
				"This object is used to encrypt passwords in the configuration.
				To set encryption passphrase with validation this object
				must be set with the new passphrase or an empty string
				to indicate no encryption.
				
				The current passphrase must be set in the previous object
				before setting object.
				
				This object is write-only, read simply returns zero length
				string.
				
				XPath: /extremeWing-config/password_encryption[name=default]/_set_pe_/new_pwd"
			::= { extremeWingCfgPasswordEncSet 2 }

		
-- /extremeWing-config/wlan
		-- 1.3.6.1.4.1.1916.2.131.50.1.3.4
		extremeWingCfgWlan OBJECT IDENTIFIER ::= { extremeWingConfig 4 }

		
		-- 1.3.6.1.4.1.1916.2.131.50.1.3.4.1
		extremeWingCfgWlanTable OBJECT-TYPE
			SYNTAX SEQUENCE OF ExtremeWingCfgWlanEntry
			MAX-ACCESS not-accessible
			STATUS current
			DESCRIPTION
				"Configuration parameters of a Wireless LAN.
				
				/extremeWing-config/wlan"
			::= { extremeWingCfgWlan 1 }

		
		-- 1.3.6.1.4.1.1916.2.131.50.1.3.4.1.1
		extremeWingCfgWlanEntry OBJECT-TYPE
			SYNTAX ExtremeWingCfgWlanEntry
			MAX-ACCESS not-accessible
			STATUS current
			DESCRIPTION
				"An entry in the table."
			INDEX { extremeWingCfgWlanName }
			::= { extremeWingCfgWlanTable 1 }

		
		ExtremeWingCfgWlanEntry ::=
			SEQUENCE { 
				extremeWingCfgWlanName
					ExtremeWingIdentifier,
				extremeWingCfgWlanShutdown
					TruthValue,
				extremeWingCfgWlanSsid
					DisplayString,
				extremeWingCfgWlanDescr
					DisplayString,
				extremeWingCfgWlanEncType
					DisplayString,
				extremeWingCfgWlanAuthType
					DisplayString,
				extremeWingCfgWlanCaptivePortalEnforcement
					DisplayString,
				extremeWingCfgWlanClientPower
					Unsigned32,
				extremeWingCfgWlanNasId
					DisplayString,
				extremeWingCfgWlanNasPortId
					DisplayString,
				extremeWingCfgWlanBroadcastSsid
					TruthValue,
				extremeWingCfgWlanAnswerBroadcastProbes
					TruthValue,
				extremeWingCfgWlanClientClientCommunication
					TruthValue,
				extremeWingCfgWlanHoldTime
					Unsigned32,
				extremeWingCfgWlanInactivityTimeout
					Unsigned32,
				extremeWingCfgWlanCredCacheAgeout
					Unsigned32,
				extremeWingCfgWlanVlanCacheAgeout
					Unsigned32,
				extremeWingCfgWlanMaxFirewallSessions
					Unsigned32,
				extremeWingCfgWlanReauth
					Unsigned32,
				extremeWingCfgWlanPmfMode
					DisplayString,
				extremeWingCfgWlanPmfSaQueryTimeout
					Unsigned32,
				extremeWingCfgWlanPmfSaQueryAttempts
					Unsigned32,
				extremeWingCfgWlanWpaWpa2Psk
					DisplayString,
				extremeWingCfgWlanWpaWpa2ExcludeWpa2Tkip
					TruthValue,
				extremeWingCfgWlanWpaWpa2KeyRotationUnicast
					Unsigned32,
				extremeWingCfgWlanWpaWpa2KeyRotationBroadcast
					Unsigned32,
				extremeWingCfgWlanWpaWpa2PmkCaching
					TruthValue,
				extremeWingCfgWlanWpaWpa2OpmkCaching
					TruthValue,
				extremeWingCfgWlanWpaWpa2Preauth
					TruthValue,
				extremeWingCfgWlanWpaWpa2TkipCntrmeasHoldTime
					Unsigned32,
				extremeWingCfgWlanWep64TransmitKey
					Unsigned32,
				extremeWingCfgWlanWep128TransmitKey
					Unsigned32,
				extremeWingCfgWlanRadiusAssignedVlans
					TruthValue,
				extremeWingCfgWlanRadiusDynamicAuthorization
					TruthValue,
				extremeWingCfgWlanAccountingRadius
					TruthValue,
				extremeWingCfgWlanMotoExtnMoveCmd
					TruthValue,
				extremeWingCfgWlanMotoExtnSmartScan
					TruthValue,
				extremeWingCfgWlanMotoExtnWmmLoadBalance
					TruthValue,
				extremeWingCfgWlanMotoExtnSymbolLoadInfo
					TruthValue,
				extremeWingCfgWlanClientLoadBal
					TruthValue,
				extremeWingCfgWlanClientLoadBalSingleBandClients5ghz
					TruthValue,
				extremeWingCfgWlanClientLoadBalSingleBandClients24ghz
					TruthValue,
				extremeWingCfgWlanClientLoadBalMaxProbeReq24ghz
					Unsigned32,
				extremeWingCfgWlanClientLoadBalMaxProbeReq5ghz
					Unsigned32,
				extremeWingCfgWlanClientLoadBalProbeReqIntvl5ghz
					Unsigned32,
				extremeWingCfgWlanClientLoadBalProbeReqIntvl24ghz
					Unsigned32,
				extremeWingCfgWlanClientLoadBalBandDiscoveryIntvl
					Unsigned32,
				extremeWingCfgWlanClientLoadBalCapabilityAgeoutTime
					Unsigned32,
				extremeWingCfgWlanQosPolicy
					ExtremeWingIdentifier,
				extremeWingCfgWlanAaaPolicy
					ExtremeWingIdentifier,
				extremeWingCfgWlanCaptivePortal
					ExtremeWingIdentifier,
				extremeWingCfgWlanAssocAcl
					ExtremeWingIdentifier,
				extremeWingCfgWlanIpInAcl
					ExtremeWingIdentifier,
				extremeWingCfgWlanMacInAcl
					ExtremeWingIdentifier,
				extremeWingCfgWlanIpOutAcl
					ExtremeWingIdentifier,
				extremeWingCfgWlanMacOutAcl
					ExtremeWingIdentifier,
				extremeWingCfgWlanArpTrust
					TruthValue,
				extremeWingCfgWlanDhcpTrust
					TruthValue,
				extremeWingCfgWlanArpHeaderMismatchValidation
					TruthValue,
				extremeWingCfgWlanServiceAllowHtOnly
					TruthValue,
				extremeWingCfgWlanEnforceDhcp
					TruthValue,
				extremeWingCfgWlanProxyArpMode
					DisplayString,
				extremeWingCfgWlanBroadcastDhcpValidateOffer
					TruthValue,
                                extremeWingCfgWlanDhcpOption82
                                        TruthValue,
				extremeWingCfgWlanServiceMonitorAaaServer
					TruthValue,
				extremeWingCfgWlanServiceMonitorCaptPrtlExtServer
 					TruthValue,
				extremeWingCfgWlanControllerAssistedMobility
 					TruthValue,
				extremeWingCfgWlanRowStatus
 					RowStatus,
				extremeWingCfgWlanBridgingMode
					DisplayString
			 }

		-- 1.3.6.1.4.1.1916.2.131.50.1.3.4.1.1.1
		extremeWingCfgWlanName OBJECT-TYPE
			SYNTAX ExtremeWingIdentifier
			MAX-ACCESS read-only
			STATUS current
			DESCRIPTION
				"
				
				XPath: /extremeWing-config/wlan[name=key1]/name"
			::= { extremeWingCfgWlanEntry 1 }

		
		-- 1.3.6.1.4.1.1916.2.131.50.1.3.4.1.1.3
		extremeWingCfgWlanShutdown OBJECT-TYPE
			SYNTAX TruthValue
			MAX-ACCESS read-write
			STATUS current
			DESCRIPTION
				"
				
				XPath: /extremeWing-config/wlan[name=key1]/shutdown"
			DEFVAL { false }
			::= { extremeWingCfgWlanEntry 3 }

		
		-- 1.3.6.1.4.1.1916.2.131.50.1.3.4.1.1.4
		extremeWingCfgWlanSsid OBJECT-TYPE
			SYNTAX DisplayString (SIZE (1..32))
			MAX-ACCESS read-write
			STATUS current
			DESCRIPTION
				"Service Set Identifier for this WLAN.
				
				XPath: /extremeWing-config/wlan[name=key1]/ssid"
			::= { extremeWingCfgWlanEntry 4 }

		
		-- 1.3.6.1.4.1.1916.2.131.50.1.3.4.1.1.5
		extremeWingCfgWlanDescr OBJECT-TYPE
			SYNTAX DisplayString (SIZE (1..64))
			MAX-ACCESS read-write
			STATUS current
			DESCRIPTION
				"Descriptive text about this WLAN.
				
				XPath: /extremeWing-config/wlan[name=key1]/description"
			::= { extremeWingCfgWlanEntry 5 }

		
		-- 1.3.6.1.4.1.1916.2.131.50.1.3.4.1.1.6
		extremeWingCfgWlanEncType OBJECT-TYPE
			SYNTAX DisplayString
			MAX-ACCESS read-write
			STATUS current
			DESCRIPTION
				"
				Values:
				none
				wep64
				wep128
				wep128-keyguard
				keyguard
				tkip
				tkip-ccmp
				ccmp
				
				XPath: /extremeWing-config/wlan[name=key1]/encryption_type"
			DEFVAL { "none" }
			::= { extremeWingCfgWlanEntry 6 }

		
		-- 1.3.6.1.4.1.1916.2.131.50.1.3.4.1.1.7
		extremeWingCfgWlanAuthType OBJECT-TYPE
			SYNTAX DisplayString
			MAX-ACCESS read-write
			STATUS current
			DESCRIPTION
				"
				Values:
				none
				eap
				kerberos
				mac
				eap-psk
				eap-mac
				
				Notes:
				eap-psk authentication-type is only supported with tkip and
				ccmp encryption types
				
				eap-mac authentication-type is only supported with open,  
				wep64, and wep128 encryption types
				
				kerberos authentication-type is only supported with wep and
				keyguard encryption types
				
				XPath: /extremeWing-config/wlan[name=key1]/authentication_type"
			DEFVAL { "none" }
			::= { extremeWingCfgWlanEntry 7 }

		
		-- 1.3.6.1.4.1.1916.2.131.50.1.3.4.1.1.8
		extremeWingCfgWlanCaptivePortalEnforcement OBJECT-TYPE
			SYNTAX DisplayString
			MAX-ACCESS read-write
			STATUS current
			DESCRIPTION
				"
				Values:
				none
				fall-back
				always
				
				XPath: /extremeWing-config/wlan[name=key1]/captive_portal_enforcement"
			DEFVAL { "none" }
			::= { extremeWingCfgWlanEntry 8 }

		
		-- 1.3.6.1.4.1.1916.2.131.50.1.3.4.1.1.9
		extremeWingCfgWlanClientPower OBJECT-TYPE
			SYNTAX Unsigned32 (0..20)
			UNITS "dBm"
			MAX-ACCESS read-write
			STATUS current
			DESCRIPTION
				"Transmit power indicated to wireless clients for transmission.
				
				XPath: /extremeWing-config/wlan[name=key1]/wireless_client_power"
			DEFVAL { 20 }
			::= { extremeWingCfgWlanEntry 9 }

		
		-- 1.3.6.1.4.1.1916.2.131.50.1.3.4.1.1.10
		extremeWingCfgWlanNasId OBJECT-TYPE
			SYNTAX DisplayString (SIZE (0..253))
			MAX-ACCESS read-write
			STATUS current
			DESCRIPTION
				"The RADIUS NAS-Identifier attribute which typically
				identifies the AP/Controller where the Radius message
				originates.
				
				XPath: /extremeWing-config/wlan[name=key1]/nas_identifier"
			DEFVAL { "" }
			::= { extremeWingCfgWlanEntry 10 }

		
		-- 1.3.6.1.4.1.1916.2.131.50.1.3.4.1.1.11
		extremeWingCfgWlanNasPortId OBJECT-TYPE
			SYNTAX DisplayString (SIZE (0..253))
			MAX-ACCESS read-write
			STATUS current
			DESCRIPTION
				"The RADIUS NAS-Port-Id attribute which typically identifiers
				the port of the device where the RADIUS messages originates.
				
				XPath: /extremeWing-config/wlan[name=key1]/nas_port_id"
			DEFVAL { "" }
			::= { extremeWingCfgWlanEntry 11 }

		
		-- 1.3.6.1.4.1.1916.2.131.50.1.3.4.1.1.12
		extremeWingCfgWlanBroadcastSsid OBJECT-TYPE
			SYNTAX TruthValue
			MAX-ACCESS read-write
			STATUS current
			DESCRIPTION
				"Do not advertise the SSID of the WLAN in the beacon.
				
				XPath: /extremeWing-config/wlan[name=key1]/broadcast_ssid"
			DEFVAL { true }
			::= { extremeWingCfgWlanEntry 12 }

		
		-- 1.3.6.1.4.1.1916.2.131.50.1.3.4.1.1.13
		extremeWingCfgWlanAnswerBroadcastProbes OBJECT-TYPE
			SYNTAX TruthValue
			MAX-ACCESS read-write
			STATUS current
			DESCRIPTION
				"Include this WLAN when responding to probe requests that
				do not specify an SSID.
				
				XPath: /extremeWing-config/wlan[name=key1]/answer_broadcast_probes"
			DEFVAL { true }
			::= { extremeWingCfgWlanEntry 13 }

		
		-- 1.3.6.1.4.1.1916.2.131.50.1.3.4.1.1.14
		extremeWingCfgWlanClientClientCommunication OBJECT-TYPE
			SYNTAX TruthValue
			MAX-ACCESS read-write
			STATUS current
			DESCRIPTION
				"Disallow switching of frames from one Wireless Client to
				another on this WLAN.
				
				XPath: /extremeWing-config/wlan[name=key1]/client_client_communication"
			DEFVAL { true }
			::= { extremeWingCfgWlanEntry 14 }

		
		-- 1.3.6.1.4.1.1916.2.131.50.1.3.4.1.1.15
		extremeWingCfgWlanHoldTime OBJECT-TYPE
			SYNTAX Unsigned32 (1..300)
			UNITS "seconds"
			MAX-ACCESS read-write
			STATUS current
			DESCRIPTION
				"User credentials and firewall flow state information
				is cached for this much time when the user roams away.
				
				XPath: /extremeWing-config/wlan[name=key1]/hold_time"
			DEFVAL { 30 }
			::= { extremeWingCfgWlanEntry 15 }

		
		-- 1.3.6.1.4.1.1916.2.131.50.1.3.4.1.1.16
		extremeWingCfgWlanInactivityTimeout OBJECT-TYPE
			SYNTAX Unsigned32 (60..86400)
			UNITS "seconds"
			MAX-ACCESS read-write
			STATUS current
			DESCRIPTION
				"If a frame is not received from a Wireless Client for this
				amount of time, the Wireless Client is disassociated.
				
				XPath: /extremeWing-config/wlan[name=key1]/inactivity_timeout"
			DEFVAL { 1800 }
			::= { extremeWingCfgWlanEntry 16 }

		
		-- 1.3.6.1.4.1.1916.2.131.50.1.3.4.1.1.17
		extremeWingCfgWlanCredCacheAgeout OBJECT-TYPE
			SYNTAX Unsigned32 (60..86400)
			UNITS "seconds"
			MAX-ACCESS read-write
			STATUS current
			DESCRIPTION
				"User keys are cached for this time interval across
				associations
				
				XPath: /extremeWing-config/wlan[name=key1]/credcache_ageout"
			DEFVAL { 86400 }
			::= { extremeWingCfgWlanEntry 17 }

		
		-- 1.3.6.1.4.1.1916.2.131.50.1.3.4.1.1.18
		extremeWingCfgWlanVlanCacheAgeout OBJECT-TYPE
			SYNTAX Unsigned32 (60..86400)
			UNITS "seconds"
			MAX-ACCESS read-write
			STATUS current
			DESCRIPTION
				"User vlan information is cached for this time interval
				across associations
				
				XPath: /extremeWing-config/wlan[name=key1]/vlancache_ageout"
			DEFVAL { 3600 }
			::= { extremeWingCfgWlanEntry 18 }

		
		-- 1.3.6.1.4.1.1916.2.131.50.1.3.4.1.1.19
		extremeWingCfgWlanMaxFirewallSessions OBJECT-TYPE
			SYNTAX Unsigned32 (10..10000)
			MAX-ACCESS read-write
			STATUS current
			DESCRIPTION
				"Maximum firewall flows per Wireless Client.
				
				XPath: /extremeWing-config/wlan[name=key1]/max_firewall_sessions"
			::= { extremeWingCfgWlanEntry 19 }

		
		-- 1.3.6.1.4.1.1916.2.131.50.1.3.4.1.1.20
		extremeWingCfgWlanReauth OBJECT-TYPE
			SYNTAX Unsigned32 (30..86400)
			MAX-ACCESS read-write
			STATUS current
			DESCRIPTION
				"
				
				XPath: /extremeWing-config/wlan[name=key1]/reauthentication"
			::= { extremeWingCfgWlanEntry 20 }

		
		-- 1.3.6.1.4.1.1916.2.131.50.1.3.4.1.1.21
		extremeWingCfgWlanPmfMode OBJECT-TYPE
			SYNTAX DisplayString
			MAX-ACCESS read-write
			STATUS current
			DESCRIPTION
				"
				Values:
				disabled
				optional
				mandatory
				
				XPath: /extremeWing-config/wlan[name=key1]/pmf_mode"
			DEFVAL { "disabled" }
			::= { extremeWingCfgWlanEntry 21 }

		
		-- 1.3.6.1.4.1.1916.2.131.50.1.3.4.1.1.22
		extremeWingCfgWlanPmfSaQueryTimeout OBJECT-TYPE
			SYNTAX Unsigned32 (100..1000)
			UNITS "milliseconds"
			MAX-ACCESS read-write
			STATUS current
			DESCRIPTION
				"Timeout when waiting for a response to a Security Association
				(SA) Query before resending it.
				
				XPath: /extremeWing-config/wlan[name=key1]/pmf_sa_query_timeout"
			DEFVAL { 201 }
			::= { extremeWingCfgWlanEntry 22 }

		
		-- 1.3.6.1.4.1.1916.2.131.50.1.3.4.1.1.23
		extremeWingCfgWlanPmfSaQueryAttempts OBJECT-TYPE
			SYNTAX Unsigned32 (1..10)
			MAX-ACCESS read-write
			STATUS current
			DESCRIPTION
				"Number of times a Security Association (SA) Query message
				is tried.
				
				XPath: /extremeWing-config/wlan[name=key1]/pmf_sa_query_attempts"
			DEFVAL { 5 }
			::= { extremeWingCfgWlanEntry 23 }

		
		-- 1.3.6.1.4.1.1916.2.131.50.1.3.4.1.1.24
		extremeWingCfgWlanWpaWpa2Psk OBJECT-TYPE
			SYNTAX DisplayString (SIZE (8..64))
			MAX-ACCESS read-write
			STATUS current
			DESCRIPTION
				"
				
				XPath: /extremeWing-config/wlan[name=key1]/wpa_wpa2_psk"
			::= { extremeWingCfgWlanEntry 24 }

		
		-- 1.3.6.1.4.1.1916.2.131.50.1.3.4.1.1.25
		extremeWingCfgWlanWpaWpa2ExcludeWpa2Tkip OBJECT-TYPE
			SYNTAX TruthValue
			MAX-ACCESS read-write
			STATUS current
			DESCRIPTION
				"Exclude the WPA2 version of TKIP and support only WPA-TKIP.
				
				XPath: /extremeWing-config/wlan[name=key1]/wpa_wpa2_exclude_wpa2_tkip"
			DEFVAL { false }
			::= { extremeWingCfgWlanEntry 25 }

		
		-- 1.3.6.1.4.1.1916.2.131.50.1.3.4.1.1.26
		extremeWingCfgWlanWpaWpa2KeyRotationUnicast OBJECT-TYPE
			SYNTAX Unsigned32 (30..86400)
			UNITS "seconds"
			MAX-ACCESS read-write
			STATUS current
			DESCRIPTION
				"
				
				XPath: /extremeWing-config/wlan[name=key1]/wpa_wpa2_key_rotation_unicast"
			::= { extremeWingCfgWlanEntry 26 }

		
		-- 1.3.6.1.4.1.1916.2.131.50.1.3.4.1.1.27
		extremeWingCfgWlanWpaWpa2KeyRotationBroadcast OBJECT-TYPE
			SYNTAX Unsigned32 (30..86400)
			UNITS "seconds"
			MAX-ACCESS read-write
			STATUS current
			DESCRIPTION
				"
				
				XPath: /extremeWing-config/wlan[name=key1]/wpa_wpa2_key_rotation_broadcast"
			::= { extremeWingCfgWlanEntry 27 }

		
		-- 1.3.6.1.4.1.1916.2.131.50.1.3.4.1.1.28
		extremeWingCfgWlanWpaWpa2PmkCaching OBJECT-TYPE
			SYNTAX TruthValue
			MAX-ACCESS read-write
			STATUS current
			DESCRIPTION
				"Enable the user of cached pairwise master keys (fast roaming
				with 802.1X EAP).
				
				XPath: /extremeWing-config/wlan[name=key1]/wpa_wpa2_pmk_caching"
			DEFVAL { true }
			::= { extremeWingCfgWlanEntry 28 }

		
		-- 1.3.6.1.4.1.1916.2.131.50.1.3.4.1.1.29
		extremeWingCfgWlanWpaWpa2OpmkCaching OBJECT-TYPE
			SYNTAX TruthValue
			MAX-ACCESS read-write
			STATUS current
			DESCRIPTION
				"Enable the use of Opportunistic Key Caching (same PMK across
				APs for fast roaming with 802.1X EAP).
				
				XPath: /extremeWing-config/wlan[name=key1]/wpa_wpa2_opmk_caching"
			DEFVAL { true }
			::= { extremeWingCfgWlanEntry 29 }

		
		-- 1.3.6.1.4.1.1916.2.131.50.1.3.4.1.1.30
		extremeWingCfgWlanWpaWpa2Preauth OBJECT-TYPE
			SYNTAX TruthValue
			MAX-ACCESS read-write
			STATUS current
			DESCRIPTION
				"Enable the use of preauthentication (802.11i fast roaming).
				
				XPath: /extremeWing-config/wlan[name=key1]/wpa_wpa2_preauthentication"
			DEFVAL { true }
			::= { extremeWingCfgWlanEntry 30 }

		
		-- 1.3.6.1.4.1.1916.2.131.50.1.3.4.1.1.31
		extremeWingCfgWlanWpaWpa2TkipCntrmeasHoldTime OBJECT-TYPE
			SYNTAX Unsigned32 (0..65535)
			UNITS "seconds"
			MAX-ACCESS read-write
			STATUS current
			DESCRIPTION
				"The amount of time for which a WLAN is disabled when
				TKIP countermeasures are invoked.
				
				XPath: /extremeWing-config/wlan[name=key1]/wpa_wpa2_tkip_cntrmeas_hold_time"
			DEFVAL { 60 }
			::= { extremeWingCfgWlanEntry 31 }

		
		-- 1.3.6.1.4.1.1916.2.131.50.1.3.4.1.1.32
		extremeWingCfgWlanWep64TransmitKey OBJECT-TYPE
			SYNTAX Unsigned32 (1..4)
			MAX-ACCESS read-write
			STATUS current
			DESCRIPTION
				"
				
				XPath: /extremeWing-config/wlan[name=key1]/wep64_transmit_key"
			DEFVAL { 1 }
			::= { extremeWingCfgWlanEntry 32 }

		
		-- 1.3.6.1.4.1.1916.2.131.50.1.3.4.1.1.37
		extremeWingCfgWlanWep128TransmitKey OBJECT-TYPE
			SYNTAX Unsigned32 (1..4)
			MAX-ACCESS read-write
			STATUS current
			DESCRIPTION
				"
				
				XPath: /extremeWing-config/wlan[name=key1]/wep128_transmit_key"
			DEFVAL { 1 }
			::= { extremeWingCfgWlanEntry 37 }

		
		-- 1.3.6.1.4.1.1916.2.131.50.1.3.4.1.1.42
		extremeWingCfgWlanRadiusAssignedVlans OBJECT-TYPE
			SYNTAX TruthValue
			MAX-ACCESS read-write
			STATUS current
			DESCRIPTION
				"Allow users to be assigned to RADIUS server-specified VLANs.
				
				XPath: /extremeWing-config/wlan[name=key1]/radius_assigned_vlans"
			DEFVAL { false }
			::= { extremeWingCfgWlanEntry 42 }

		
		-- 1.3.6.1.4.1.1916.2.131.50.1.3.4.1.1.43
		extremeWingCfgWlanRadiusDynamicAuthorization OBJECT-TYPE
			SYNTAX TruthValue
			MAX-ACCESS read-write
			STATUS current
			DESCRIPTION
				"Enable support for Disconnect and Change of Authorization
				(CoA) messages (RFC5176).
				
				XPath: /extremeWing-config/wlan[name=key1]/radius_dynamic_authorization"
			DEFVAL { false }
			::= { extremeWingCfgWlanEntry 43 }

		
		-- 1.3.6.1.4.1.1916.2.131.50.1.3.4.1.1.44
		extremeWingCfgWlanAccountingRadius OBJECT-TYPE
			SYNTAX TruthValue
			MAX-ACCESS read-write
			STATUS current
			DESCRIPTION
				"802.11 rates supported on the radio for this wlan when
				it is mapped to a 2.4GHz mode radio.
				
				XPath: /extremeWing-config/wlan[name=key1]/accounting_radius"
			DEFVAL { false }
			::= { extremeWingCfgWlanEntry 44 }

		
		-- 1.3.6.1.4.1.1916.2.131.50.1.3.4.1.1.45
		extremeWingCfgWlanMotoExtnMoveCmd OBJECT-TYPE
			SYNTAX TruthValue
			MAX-ACCESS read-write
			STATUS current
			DESCRIPTION
				"
				
				XPath: /extremeWing-config/wlan[name=key1]/moto_extn_move_cmd"
			DEFVAL { false }
			::= { extremeWingCfgWlanEntry 45 }

		
		-- 1.3.6.1.4.1.1916.2.131.50.1.3.4.1.1.46
		extremeWingCfgWlanMotoExtnSmartScan OBJECT-TYPE
			SYNTAX TruthValue
			MAX-ACCESS read-write
			STATUS current
			DESCRIPTION
				"
				
				XPath: /extremeWing-config/wlan[name=key1]/moto_extn_smart_scan"
			DEFVAL { false }
			::= { extremeWingCfgWlanEntry 46 }

		
		-- 1.3.6.1.4.1.1916.2.131.50.1.3.4.1.1.47
		extremeWingCfgWlanMotoExtnWmmLoadBalance OBJECT-TYPE
			SYNTAX TruthValue
			MAX-ACCESS read-write
			STATUS current
			DESCRIPTION
				"
				
				XPath: /extremeWing-config/wlan[name=key1]/moto_extn_wmm_load_balance"
			DEFVAL { false }
			::= { extremeWingCfgWlanEntry 47 }

		
		-- 1.3.6.1.4.1.1916.2.131.50.1.3.4.1.1.48
		extremeWingCfgWlanMotoExtnSymbolLoadInfo OBJECT-TYPE
			SYNTAX TruthValue
			MAX-ACCESS read-write
			STATUS current
			DESCRIPTION
				"
				
				XPath: /extremeWing-config/wlan[name=key1]/moto_extn_symbol_load_info"
			DEFVAL { true }
			::= { extremeWingCfgWlanEntry 48 }

		
		-- 1.3.6.1.4.1.1916.2.131.50.1.3.4.1.1.49
		extremeWingCfgWlanClientLoadBal OBJECT-TYPE
			SYNTAX TruthValue
			MAX-ACCESS read-write
			STATUS current
			DESCRIPTION
				"
				
				XPath: /extremeWing-config/wlan[name=key1]/client_load_balancing"
			DEFVAL { true }
			::= { extremeWingCfgWlanEntry 49 }

		
		-- 1.3.6.1.4.1.1916.2.131.50.1.3.4.1.1.50
		extremeWingCfgWlanClientLoadBalSingleBandClients5ghz OBJECT-TYPE
			SYNTAX TruthValue
			MAX-ACCESS read-write
			STATUS current
			DESCRIPTION
				"
				
				XPath: /extremeWing-config/wlan[name=key1]/client_load_balancing_single_band_clients_5ghz"
			DEFVAL { true }
			::= { extremeWingCfgWlanEntry 50 }

		
		-- 1.3.6.1.4.1.1916.2.131.50.1.3.4.1.1.51
		extremeWingCfgWlanClientLoadBalSingleBandClients24ghz OBJECT-TYPE
			SYNTAX TruthValue
			MAX-ACCESS read-write
			STATUS current
			DESCRIPTION
				"
				
				XPath: /extremeWing-config/wlan[name=key1]/client_load_balancing_single_band_clients_2_4ghz"
			DEFVAL { true }
			::= { extremeWingCfgWlanEntry 51 }

		
		-- 1.3.6.1.4.1.1916.2.131.50.1.3.4.1.1.52
		extremeWingCfgWlanClientLoadBalMaxProbeReq24ghz OBJECT-TYPE
			SYNTAX Unsigned32 (0..10000)
			MAX-ACCESS read-write
			STATUS current
			DESCRIPTION
				"Number of persistent probe requests beyond which the client
				is allowed to associate
				
				XPath: /extremeWing-config/wlan[name=key1]/client_load_balancing_max_probe_req_2_4ghz"
			DEFVAL { 48 }
			::= { extremeWingCfgWlanEntry 52 }

		
		-- 1.3.6.1.4.1.1916.2.131.50.1.3.4.1.1.53
		extremeWingCfgWlanClientLoadBalMaxProbeReq5ghz OBJECT-TYPE
			SYNTAX Unsigned32 (0..10000)
			MAX-ACCESS read-write
			STATUS current
			DESCRIPTION
				"Number of persistent probe requests beyond which the client
				is allowed to associate
				
				XPath: /extremeWing-config/wlan[name=key1]/client_load_balancing_max_probe_req_5ghz"
			DEFVAL { 24 }
			::= { extremeWingCfgWlanEntry 53 }

		
		-- 1.3.6.1.4.1.1916.2.131.50.1.3.4.1.1.54
		extremeWingCfgWlanClientLoadBalProbeReqIntvl5ghz OBJECT-TYPE
			SYNTAX Unsigned32 (0..10000)
			UNITS "seconds"
			MAX-ACCESS read-write
			STATUS current
			DESCRIPTION
				"Interval within which we should receive a minimum number of
				probe requests to allow client association.
				
				XPath: /extremeWing-config/wlan[name=key1]/client_load_balancing_probe_req_intvl_5ghz"
			DEFVAL { 24 }
			::= { extremeWingCfgWlanEntry 54 }

		
		-- 1.3.6.1.4.1.1916.2.131.50.1.3.4.1.1.55
		extremeWingCfgWlanClientLoadBalProbeReqIntvl24ghz OBJECT-TYPE
			SYNTAX Unsigned32 (0..10000)
			UNITS "seconds"
			MAX-ACCESS read-write
			STATUS current
			DESCRIPTION
				"Interval within which we should receive a minimum number of
				probe requests to allow client association.
				
				XPath: /extremeWing-config/wlan[name=key1]/client_load_balancing_probe_req_intvl_2_4ghz"
			DEFVAL { 24 }
			::= { extremeWingCfgWlanEntry 55 }

		
		-- 1.3.6.1.4.1.1916.2.131.50.1.3.4.1.1.56
		extremeWingCfgWlanClientLoadBalBandDiscoveryIntvl OBJECT-TYPE
			SYNTAX Unsigned32 (0..10000)
			UNITS "seconds"
			MAX-ACCESS read-write
			STATUS current
			DESCRIPTION
				"Time to discover client's band capabilties.
				
				XPath: /extremeWing-config/wlan[name=key1]/client_load_balancing_band_discovery_intvl"
			DEFVAL { 24 }
			::= { extremeWingCfgWlanEntry 56 }

		
		-- 1.3.6.1.4.1.1916.2.131.50.1.3.4.1.1.57
		extremeWingCfgWlanClientLoadBalCapabilityAgeoutTime OBJECT-TYPE
			SYNTAX Unsigned32 (0..10000)
			UNITS "seconds"
			MAX-ACCESS read-write
			STATUS current
			DESCRIPTION
				"Time to ageout a client's capabilties from internal tables.
				
				XPath: /extremeWing-config/wlan[name=key1]/client_load_balancing_capability_ageout_time"
			DEFVAL { 24 }
			::= { extremeWingCfgWlanEntry 57 }

		
		-- 1.3.6.1.4.1.1916.2.131.50.1.3.4.1.1.58
		extremeWingCfgWlanQosPolicy OBJECT-TYPE
			SYNTAX ExtremeWingIdentifier
			MAX-ACCESS read-write
			STATUS current
			DESCRIPTION
				"
				
				XPath: /extremeWing-config/wlan[name=key1]/qos_policy"
			::= { extremeWingCfgWlanEntry 58 }

		
		-- 1.3.6.1.4.1.1916.2.131.50.1.3.4.1.1.59
		extremeWingCfgWlanAaaPolicy OBJECT-TYPE
			SYNTAX ExtremeWingIdentifier
			MAX-ACCESS read-write
			STATUS current
			DESCRIPTION
				"
				
				XPath: /extremeWing-config/wlan[name=key1]/aaa_policy"
			::= { extremeWingCfgWlanEntry 59 }

		
		-- 1.3.6.1.4.1.1916.2.131.50.1.3.4.1.1.60
		extremeWingCfgWlanCaptivePortal OBJECT-TYPE
			SYNTAX ExtremeWingIdentifier
			MAX-ACCESS read-write
			STATUS current
			DESCRIPTION
				"
				
				XPath: /extremeWing-config/wlan[name=key1]/captive_portal"
			::= { extremeWingCfgWlanEntry 60 }

		
		-- 1.3.6.1.4.1.1916.2.131.50.1.3.4.1.1.61
		extremeWingCfgWlanAssocAcl OBJECT-TYPE
			SYNTAX ExtremeWingIdentifier
			MAX-ACCESS read-write
			STATUS current
			DESCRIPTION
				"
				
				XPath: /extremeWing-config/wlan[name=key1]/assoc_acl"
			::= { extremeWingCfgWlanEntry 61 }

		
		-- 1.3.6.1.4.1.1916.2.131.50.1.3.4.1.1.62
		extremeWingCfgWlanIpInAcl OBJECT-TYPE
			SYNTAX ExtremeWingIdentifier
			MAX-ACCESS read-write
			STATUS current
			DESCRIPTION
				"
				
				XPath: /extremeWing-config/wlan[name=key1]/ip_in_acl"
			::= { extremeWingCfgWlanEntry 62 }

		
		-- 1.3.6.1.4.1.1916.2.131.50.1.3.4.1.1.63
		extremeWingCfgWlanMacInAcl OBJECT-TYPE
			SYNTAX ExtremeWingIdentifier
			MAX-ACCESS read-write
			STATUS current
			DESCRIPTION
				"
				
				XPath: /extremeWing-config/wlan[name=key1]/mac_in_acl"
			::= { extremeWingCfgWlanEntry 63 }

		
		-- 1.3.6.1.4.1.1916.2.131.50.1.3.4.1.1.64
		extremeWingCfgWlanIpOutAcl OBJECT-TYPE
			SYNTAX ExtremeWingIdentifier
			MAX-ACCESS read-write
			STATUS current
			DESCRIPTION
				"
				
				XPath: /extremeWing-config/wlan[name=key1]/ip_out_acl"
			::= { extremeWingCfgWlanEntry 64 }

		
		-- 1.3.6.1.4.1.1916.2.131.50.1.3.4.1.1.65
		extremeWingCfgWlanMacOutAcl OBJECT-TYPE
			SYNTAX ExtremeWingIdentifier
			MAX-ACCESS read-write
			STATUS current
			DESCRIPTION
				"
				
				XPath: /extremeWing-config/wlan[name=key1]/mac_out_acl"
			::= { extremeWingCfgWlanEntry 65 }

		
		-- 1.3.6.1.4.1.1916.2.131.50.1.3.4.1.1.66
		extremeWingCfgWlanArpTrust OBJECT-TYPE
			SYNTAX TruthValue
			MAX-ACCESS read-write
			STATUS current
			DESCRIPTION
				"Trust ARP requests on WLANs.
				
				XPath: /extremeWing-config/wlan[name=key1]/arp_trust"
			DEFVAL { false }
			::= { extremeWingCfgWlanEntry 66 }

		
		-- 1.3.6.1.4.1.1916.2.131.50.1.3.4.1.1.67
		extremeWingCfgWlanDhcpTrust OBJECT-TYPE
			SYNTAX TruthValue
			MAX-ACCESS read-write
			STATUS current
			DESCRIPTION
				"Trust DHCP responses on WLANs.
				
				XPath: /extremeWing-config/wlan[name=key1]/dhcp_trust"
			DEFVAL { false }
			::= { extremeWingCfgWlanEntry 67 }

		
		-- 1.3.6.1.4.1.1916.2.131.50.1.3.4.1.1.68
		extremeWingCfgWlanArpHeaderMismatchValidation OBJECT-TYPE
			SYNTAX TruthValue
			MAX-ACCESS read-write
			STATUS current
			DESCRIPTION
				"Check mismatch for source MAC in ARP header and ethernet header.
				
				XPath: /extremeWing-config/wlan[name=key1]/arp_header_mismatch_validation"
			DEFVAL { true }
			::= { extremeWingCfgWlanEntry 68 }

		
		-- 1.3.6.1.4.1.1916.2.131.50.1.3.4.1.1.69
		extremeWingCfgWlanServiceAllowHtOnly OBJECT-TYPE
			SYNTAX TruthValue
			MAX-ACCESS read-write
			STATUS current
			DESCRIPTION
				"
				
				XPath: /extremeWing-config/wlan[name=key1]/service_allow_ht_only"
			DEFVAL { false }
			::= { extremeWingCfgWlanEntry 69 }

		
		-- 1.3.6.1.4.1.1916.2.131.50.1.3.4.1.1.70
		extremeWingCfgWlanEnforceDhcp OBJECT-TYPE
			SYNTAX TruthValue
			MAX-ACCESS read-write
			STATUS current
			DESCRIPTION
				"
				
				XPath: /extremeWing-config/wlan[name=key1]/enforce_dhcp"
			DEFVAL { false }
			::= { extremeWingCfgWlanEntry 70 }

		
		-- 1.3.6.1.4.1.1916.2.131.50.1.3.4.1.1.71
		extremeWingCfgWlanProxyArpMode OBJECT-TYPE
			SYNTAX DisplayString
			MAX-ACCESS read-write
			STATUS current
			DESCRIPTION
				"
				Values:
				strict
				dynamic
				
				XPath: /extremeWing-config/wlan[name=key1]/proxy_arp_mode"
			DEFVAL { "dynamic" }
			::= { extremeWingCfgWlanEntry 71 }

		
		-- 1.3.6.1.4.1.1916.2.131.50.1.3.4.1.1.72
		extremeWingCfgWlanBroadcastDhcpValidateOffer OBJECT-TYPE
			SYNTAX TruthValue
			MAX-ACCESS read-write
			STATUS current
			DESCRIPTION
				"
				
				XPath: /extremeWing-config/wlan[name=key1]/broadcast_dhcp_validate_offer"
			DEFVAL { false }
			::= { extremeWingCfgWlanEntry 72 }


                -- 1.3.6.1.4.1.1916.2.131.50.1.3.4.1.1.73
                extremeWingCfgWlanDhcpOption82 OBJECT-TYPE
                        SYNTAX TruthValue
                        MAX-ACCESS read-write
                        STATUS current
                        DESCRIPTION
                                "To activate/deactivate dhcp option82 feature

                                XPath: /extremeWing-config/wlan[name=key1]/dhcp_option_82"
                        DEFVAL { false }
                        ::= { extremeWingCfgWlanEntry 73 }


		-- 1.3.6.1.4.1.1916.2.131.50.1.3.4.1.1.74
		extremeWingCfgWlanServiceMonitorAaaServer OBJECT-TYPE
			SYNTAX TruthValue
			MAX-ACCESS read-write
			STATUS current
			DESCRIPTION
				"XPath: /extremeWing-config/wlan[name=key1]/service_monitor_aaa_server"
			DEFVAL { false }
			::= { extremeWingCfgWlanEntry 74 }

		
		-- 1.3.6.1.4.1.1916.2.131.50.1.3.4.1.1.75
		extremeWingCfgWlanServiceMonitorCaptPrtlExtServer OBJECT-TYPE
			SYNTAX TruthValue
			MAX-ACCESS read-write
			STATUS current
			DESCRIPTION
				"XPath: /extremeWing-config/wlan[name=key1]/service_monitor_captive_portal_external_server"
			DEFVAL { false }
			::= { extremeWingCfgWlanEntry 75 }


		-- 1.3.6.1.4.1.1916.2.131.50.1.3.4.1.1.76
		extremeWingCfgWlanControllerAssistedMobility OBJECT-TYPE
			SYNTAX TruthValue
			MAX-ACCESS read-write
			STATUS current
			DESCRIPTION
				"XPath: /extremeWing-config/wlan[name=key1]/controller_assisted_mobility"
			DEFVAL { false }
			::= { extremeWingCfgWlanEntry 76 }


		-- 1.3.6.1.4.1.1916.2.131.50.1.3.4.1.1.2
		extremeWingCfgWlanRowStatus OBJECT-TYPE
			SYNTAX RowStatus
				{
				active(1),
				createAndGo(4),
				destroy(6)
				}
			MAX-ACCESS read-write
			STATUS current
			DESCRIPTION
				"The status of this conceptual row.
				XPath: /extremeWing-config/wlan[name=key1]/row_status"
			::= { extremeWingCfgWlanEntry 2 }


		-- 1.3.6.1.4.1.1916.2.131.50.1.3.4.1.1.77
		extremeWingCfgWlanBridgingMode OBJECT-TYPE
			SYNTAX DisplayString
			MAX-ACCESS read-write
			STATUS current
			DESCRIPTION
				"Values:
				local
				tunnel
				
				The default value for qs1,qs2,qs5 and bob is tunnel and 
				for other targets default is local
				
				XPath: /extremeWing-config/wlan[name=key1]/bridging_mode"
			::= { extremeWingCfgWlanEntry 77 }


		-- 1.3.6.1.4.1.1916.2.131.50.1.3.4.2
		extremeWingCfgWlanVlanTable OBJECT-TYPE
			SYNTAX SEQUENCE OF ExtremeWingCfgWlanVlanEntry
			MAX-ACCESS not-accessible
			STATUS current
			DESCRIPTION
				"Configure the VLAN where traffic from this WLAN is mapped.
				
				/extremeWing-config/wlan/vlans"
			::= { extremeWingCfgWlan 2 }

		
		-- 1.3.6.1.4.1.1916.2.131.50.1.3.4.2.1
		extremeWingCfgWlanVlanEntry OBJECT-TYPE
			SYNTAX ExtremeWingCfgWlanVlanEntry
			MAX-ACCESS not-accessible
			STATUS current
			DESCRIPTION
				"An entry in the table."
			INDEX { extremeWingCfgWlanName, extremeWingCfgWlanVlanId }
			::= { extremeWingCfgWlanVlanTable 1 }

		
		ExtremeWingCfgWlanVlanEntry ::=
			SEQUENCE { 
				extremeWingCfgWlanVlanId
					Unsigned32,
				extremeWingCfgWlanVlanLimit
					Unsigned32,
				extremeWingCfgWlanVlanRowStatus
					RowStatus
			 }

		-- 1.3.6.1.4.1.1916.2.131.50.1.3.4.2.1.1
		extremeWingCfgWlanVlanId OBJECT-TYPE
			SYNTAX Unsigned32 (1..4094)
			MAX-ACCESS read-only
			STATUS current
			DESCRIPTION
				"The vlan-id.
				
				XPath: /extremeWing-config/wlan[name=key1]/vlans[vlan=key2]/vlan"
			::= { extremeWingCfgWlanVlanEntry 1 }

		
		-- 1.3.6.1.4.1.1916.2.131.50.1.3.4.2.1.3
		extremeWingCfgWlanVlanLimit OBJECT-TYPE
			SYNTAX Unsigned32 (0..8192)
			MAX-ACCESS read-write
			STATUS current
			DESCRIPTION
				"Limit the number of users on this VLAN.
				
				XPath: /extremeWing-config/wlan[name=key1]/vlans[vlan=key2]/limit"
			::= { extremeWingCfgWlanVlanEntry 3 }

		-- 1.3.6.1.4.1.1916.2.131.50.1.3.4.2.1.2
		extremeWingCfgWlanVlanRowStatus OBJECT-TYPE
			SYNTAX RowStatus
				{
				active(1),
				createAndGo(4),
				destroy(6)
				}
			MAX-ACCESS read-write
			STATUS current
			DESCRIPTION
				"The status of this conceptual row.
				XPath: /extremeWing-config/wlan[name=key1]/vlans[vlan=key2]/row_status"
			::= { extremeWingCfgWlanVlanEntry 2 }

		
		-- 1.3.6.1.4.1.1916.2.131.50.1.3.4.3
		extremeWingCfgWlanKerberosTable OBJECT-TYPE
			SYNTAX SEQUENCE OF ExtremeWingCfgWlanKerberosEntry
			MAX-ACCESS not-accessible
			STATUS current
			DESCRIPTION
				"
				
				/extremeWing-config/wlan/kerberos"
			::= { extremeWingCfgWlan 3 }

		
		-- 1.3.6.1.4.1.1916.2.131.50.1.3.4.3.1
		extremeWingCfgWlanKerberosEntry OBJECT-TYPE
			SYNTAX ExtremeWingCfgWlanKerberosEntry
			MAX-ACCESS not-accessible
			STATUS current
			DESCRIPTION
				"An entry in the table."
			INDEX { extremeWingCfgWlanName }
			::= { extremeWingCfgWlanKerberosTable 1 }

		
		ExtremeWingCfgWlanKerberosEntry ::=
			SEQUENCE { 
				extremeWingCfgWlanKerberosRealm
					DisplayString,
				extremeWingCfgWlanKerberosTimeout
					Unsigned32,
				extremeWingCfgWlanKerberosPassword
					DisplayString,
				extremeWingCfgWlanKerberosPrimaryServer
					DisplayString,
				extremeWingCfgWlanKerberosPrimaryServerPort
					Unsigned32,
				extremeWingCfgWlanKerberosSecondaryServer
					DisplayString,
				extremeWingCfgWlanKerberosSecondaryServerPort
					Unsigned32
			 }

		-- 1.3.6.1.4.1.1916.2.131.50.1.3.4.3.1.1
		extremeWingCfgWlanKerberosRealm OBJECT-TYPE
			SYNTAX DisplayString (SIZE (0..127))
			MAX-ACCESS read-write
			STATUS current
			DESCRIPTION
				"
				
				XPath: /extremeWing-config/wlan[name=key1]/kerberos/realm"
			::= { extremeWingCfgWlanKerberosEntry 1 }

		
		-- 1.3.6.1.4.1.1916.2.131.50.1.3.4.3.1.2
		extremeWingCfgWlanKerberosTimeout OBJECT-TYPE
			SYNTAX Unsigned32 (1..10)
			UNITS "seconds"
			MAX-ACCESS read-write
			STATUS current
			DESCRIPTION
				"
				
				XPath: /extremeWing-config/wlan[name=key1]/kerberos/timeout"
			DEFVAL { 5 }
			::= { extremeWingCfgWlanKerberosEntry 2 }

		
		-- 1.3.6.1.4.1.1916.2.131.50.1.3.4.3.1.3
		extremeWingCfgWlanKerberosPassword OBJECT-TYPE
			SYNTAX DisplayString (SIZE (0..127))
			MAX-ACCESS read-write
			STATUS current
			DESCRIPTION
				"
				
				XPath: /extremeWing-config/wlan[name=key1]/kerberos/password"
			::= { extremeWingCfgWlanKerberosEntry 3 }

		
		-- 1.3.6.1.4.1.1916.2.131.50.1.3.4.3.1.4
		extremeWingCfgWlanKerberosPrimaryServer OBJECT-TYPE
			SYNTAX DisplayString
			MAX-ACCESS read-write
			STATUS current
			DESCRIPTION
				"
				
				XPath: /extremeWing-config/wlan[name=key1]/kerberos/primary_server"
			::= { extremeWingCfgWlanKerberosEntry 4 }

		
		-- 1.3.6.1.4.1.1916.2.131.50.1.3.4.3.1.5
		extremeWingCfgWlanKerberosPrimaryServerPort OBJECT-TYPE
			SYNTAX Unsigned32 (1..65535)
			MAX-ACCESS read-write
			STATUS current
			DESCRIPTION
				"
				
				XPath: /extremeWing-config/wlan[name=key1]/kerberos/primary_server_port"
			DEFVAL { 88 }
			::= { extremeWingCfgWlanKerberosEntry 5 }

		
		-- 1.3.6.1.4.1.1916.2.131.50.1.3.4.3.1.6
		extremeWingCfgWlanKerberosSecondaryServer OBJECT-TYPE
			SYNTAX DisplayString
			MAX-ACCESS read-write
			STATUS current
			DESCRIPTION
				"
				
				XPath: /extremeWing-config/wlan[name=key1]/kerberos/secondary_server"
			::= { extremeWingCfgWlanKerberosEntry 6 }

		
		-- 1.3.6.1.4.1.1916.2.131.50.1.3.4.3.1.7
		extremeWingCfgWlanKerberosSecondaryServerPort OBJECT-TYPE
			SYNTAX Unsigned32 (1..65535)
			MAX-ACCESS read-write
			STATUS current
			DESCRIPTION
				"
				
				XPath: /extremeWing-config/wlan[name=key1]/kerberos/secondary_server_port"
			DEFVAL { 88 }
			::= { extremeWingCfgWlanKerberosEntry 7 }

		
		-- 1.3.6.1.4.1.1916.2.131.50.1.3.4.4
		extremeWingCfgWlanAcctSyslogTable OBJECT-TYPE
			SYNTAX SEQUENCE OF ExtremeWingCfgWlanAcctSyslogEntry
			MAX-ACCESS not-accessible
			STATUS current
			DESCRIPTION
				"
				
				/extremeWing-config/wlan/accounting_syslog"
			::= { extremeWingCfgWlan 4 }

		
		-- 1.3.6.1.4.1.1916.2.131.50.1.3.4.4.1
		extremeWingCfgWlanAcctSyslogEntry OBJECT-TYPE
			SYNTAX ExtremeWingCfgWlanAcctSyslogEntry
			MAX-ACCESS not-accessible
			STATUS current
			DESCRIPTION
				"An entry in the table."
			INDEX { extremeWingCfgWlanName }
			::= { extremeWingCfgWlanAcctSyslogTable 1 }

		
		ExtremeWingCfgWlanAcctSyslogEntry ::=
			SEQUENCE { 
				extremeWingCfgWlanAcctSyslogEnable
					TruthValue,
				extremeWingCfgWlanAcctSyslogHost
					DisplayString,
				extremeWingCfgWlanAcctSyslogPort
					Unsigned32
			 }

		-- 1.3.6.1.4.1.1916.2.131.50.1.3.4.4.1.1
		extremeWingCfgWlanAcctSyslogEnable OBJECT-TYPE
			SYNTAX TruthValue
			MAX-ACCESS read-write
			STATUS current
			DESCRIPTION
				"
				
				XPath: /extremeWing-config/wlan[name=key1]/accounting_syslog/enable"
			DEFVAL { false }
			::= { extremeWingCfgWlanAcctSyslogEntry 1 }

		
		-- 1.3.6.1.4.1.1916.2.131.50.1.3.4.4.1.2
		extremeWingCfgWlanAcctSyslogHost OBJECT-TYPE
			SYNTAX DisplayString
			MAX-ACCESS read-write
			STATUS current
			DESCRIPTION
				"
				
				XPath: /extremeWing-config/wlan[name=key1]/accounting_syslog/host"
			::= { extremeWingCfgWlanAcctSyslogEntry 2 }

		
		-- 1.3.6.1.4.1.1916.2.131.50.1.3.4.4.1.3
		extremeWingCfgWlanAcctSyslogPort OBJECT-TYPE
			SYNTAX Unsigned32 (1..65535)
			MAX-ACCESS read-write
			STATUS current
			DESCRIPTION
				"
				
				XPath: /extremeWing-config/wlan[name=key1]/accounting_syslog/port"
			DEFVAL { 514 }
			::= { extremeWingCfgWlanAcctSyslogEntry 3 }

		
		-- 1.3.6.1.4.1.1916.2.131.50.1.3.4.5
		extremeWingCfgWlanClientDenyLimitTable OBJECT-TYPE
			SYNTAX SEQUENCE OF ExtremeWingCfgWlanClientDenyLimitEntry
			MAX-ACCESS not-accessible
			STATUS current
			DESCRIPTION
				"
				
				/extremeWing-config/wlan/mu_deny_limit"
			::= { extremeWingCfgWlan 5 }

		
		-- 1.3.6.1.4.1.1916.2.131.50.1.3.4.5.1
		extremeWingCfgWlanClientDenyLimitEntry OBJECT-TYPE
			SYNTAX ExtremeWingCfgWlanClientDenyLimitEntry
			MAX-ACCESS not-accessible
			STATUS current
			DESCRIPTION
				"An entry in the table."
			INDEX { extremeWingCfgWlanName }
			::= { extremeWingCfgWlanClientDenyLimitTable 1 }

		
		ExtremeWingCfgWlanClientDenyLimitEntry ::=
			SEQUENCE { 
				extremeWingCfgWlanClientDenyLimitThresholdRate
					Unsigned32,
				extremeWingCfgWlanClientDenyLimitAction
					DisplayString,
				extremeWingCfgWlanClientDenyLimitBlacklistAgeout
					Unsigned32
			 }

		-- 1.3.6.1.4.1.1916.2.131.50.1.3.4.5.1.1
		extremeWingCfgWlanClientDenyLimitThresholdRate OBJECT-TYPE
			SYNTAX Unsigned32 (1..1000000)
			UNITS "packets"
			MAX-ACCESS read-write
			STATUS current
			DESCRIPTION
				"
				
				XPath: /extremeWing-config/wlan[name=key1]/mu_deny_limit/threshold_rate"
			::= { extremeWingCfgWlanClientDenyLimitEntry 1 }

		
		-- 1.3.6.1.4.1.1916.2.131.50.1.3.4.5.1.2
		extremeWingCfgWlanClientDenyLimitAction OBJECT-TYPE
			SYNTAX DisplayString
			MAX-ACCESS read-write
			STATUS current
			DESCRIPTION
				"
				Values:
				disassociate
				blacklist
				none
				
				XPath: /extremeWing-config/wlan[name=key1]/mu_deny_limit/action"
			DEFVAL { "none" }
			::= { extremeWingCfgWlanClientDenyLimitEntry 2 }

		
		-- 1.3.6.1.4.1.1916.2.131.50.1.3.4.5.1.3
		extremeWingCfgWlanClientDenyLimitBlacklistAgeout OBJECT-TYPE
			SYNTAX Unsigned32 (0..86400)
			UNITS "seconds"
			MAX-ACCESS read-write
			STATUS current
			DESCRIPTION
				"Specifies the duration for which the mobile unit causing
				this event is black listed.
				
				XPath: /extremeWing-config/wlan[name=key1]/mu_deny_limit/blacklist_ageout"
			::= { extremeWingCfgWlanClientDenyLimitEntry 3 }

-- Mac Registraion Feature.
                -- 1.3.6.1.4.1.1916.2.131.50.1.3.4.6
                extremeWingCfgWlanMacRegistration OBJECT IDENTIFIER ::= { extremeWingCfgWlan 6 }


-- Mac Registration Table.
                -- 1.3.6.1.4.1.1916.2.131.50.1.3.4.6.1
                extremeWingCfgWlanMacRegistrationTable OBJECT-TYPE
                        SYNTAX SEQUENCE OF ExtremeWingCfgWlanMacRegistrationEntry
                        MAX-ACCESS not-accessible
                        STATUS current
                        DESCRIPTION
                                "/extremeWing-config/wlan/mac_registration"
                        ::= { extremeWingCfgWlanMacRegistration 1 }


                -- 1.3.6.1.4.1.1916.2.131.50.1.3.4.6.1.1
                extremeWingCfgWlanMacRegistrationEntry OBJECT-TYPE
                        SYNTAX ExtremeWingCfgWlanMacRegistrationEntry
                        MAX-ACCESS not-accessible
                        STATUS current
                        DESCRIPTION
                                "An entry in the table."
                        INDEX { extremeWingCfgWlanName }
                        ::= { extremeWingCfgWlanMacRegistrationTable 1 }


                ExtremeWingCfgWlanMacRegistrationEntry ::=
                        SEQUENCE {
                                extremeWingCfgWlanMacRegistrationEnable
                                        TruthValue,
                                extremeWingCfgWlanMacRegistrationGroupName
                                        DisplayString,
                                extremeWingCfgWlanMacRegistrationExpiryTime
                                        Unsigned32
                         }

                -- 1.3.6.1.4.1.1916.2.131.50.1.3.4.6.1.1.1
                extremeWingCfgWlanMacRegistrationEnable OBJECT-TYPE
                        SYNTAX TruthValue
                        MAX-ACCESS read-write
                        STATUS current
                        DESCRIPTION
                                "/extremeWing-config/wlan[name=key1]/mac_registration/enable

                                Mac Registration Status."
                        DEFVAL { false }
                        ::= { extremeWingCfgWlanMacRegistrationEntry 1 }


                -- 1.3.6.1.4.1.1916.2.131.50.1.3.4.6.1.1.2
                extremeWingCfgWlanMacRegistrationGroupName OBJECT-TYPE
                        SYNTAX DisplayString (SIZE (0..64))
                        MAX-ACCESS read-write
                        STATUS current
                        DESCRIPTION
                                "/extremeWing-config/wlan[name=key1]/mac_registration/group_name

                                Group to which the MAC registering user needs to be associated with."
                        ::= { extremeWingCfgWlanMacRegistrationEntry 2 }


                -- 1.3.6.1.4.1.1916.2.131.50.1.3.4.6.1.1.3
                extremeWingCfgWlanMacRegistrationExpiryTime OBJECT-TYPE
                        SYNTAX Unsigned32 (1..1500)
                        UNITS "days"
                        MAX-ACCESS read-write
                        STATUS current
                        DESCRIPTION
                                "/extremeWing-config/wlan[name=key1]/mac_registration/expiry_time

                                MAC registered user expiry time (in number of days)."
                        DEFVAL { 1500 }
                        ::= { extremeWingCfgWlanMacRegistrationEntry 3 }


                -- 1.3.6.1.4.1.1916.2.131.50.1.3.4.6.2
                extremeWingCfgWlanMacRegistrationExternalTable OBJECT-TYPE
                        SYNTAX SEQUENCE OF ExtremeWingCfgWlanMacRegistrationExternalEntry
                        MAX-ACCESS not-accessible
                        STATUS current
                        DESCRIPTION
                                "/extremeWing-config/wlan/mac_registration_external"
                        ::= { extremeWingCfgWlanMacRegistration 2 }


                -- 1.3.6.1.4.1.1916.2.131.50.1.3.4.6.2.1
                extremeWingCfgWlanMacRegistrationExternalEntry OBJECT-TYPE
                        SYNTAX ExtremeWingCfgWlanMacRegistrationExternalEntry
                        MAX-ACCESS not-accessible
                        STATUS current
                        DESCRIPTION
                                "An entry in the table."
                        INDEX { extremeWingCfgWlanName }
                        ::= { extremeWingCfgWlanMacRegistrationExternalTable 1 }


                ExtremeWingCfgWlanMacRegistrationExternalEntry ::=
                        SEQUENCE {
                                extremeWingCfgWlanMacRegistrationExternalEnable
                                        TruthValue,
                                extremeWingCfgWlanMacRegistrationExternalHost
                                        DisplayString,
                                extremeWingCfgWlanMacRegistrationExternalProxyMode
                                        DisplayString
                         }

                -- 1.3.6.1.4.1.1916.2.131.50.1.3.4.6.2.1.1
                extremeWingCfgWlanMacRegistrationExternalEnable OBJECT-TYPE
                        SYNTAX TruthValue
                        MAX-ACCESS read-write
                        STATUS current
                        DESCRIPTION
                                "/extremeWing-config/wlan[name=key1]/mac_registration_external/enable

                                Mac Registration External Status."
                        DEFVAL { false }
                        ::= { extremeWingCfgWlanMacRegistrationExternalEntry 1 }


                -- 1.3.6.1.4.1.1916.2.131.50.1.3.4.6.2.1.2
                extremeWingCfgWlanMacRegistrationExternalHost OBJECT-TYPE
                        SYNTAX DisplayString
                        MAX-ACCESS read-write
                        STATUS current
                        DESCRIPTION
                                "/extremeWing-config/wlan[name=key1]/mac_registration_external/host"
                        ::= { extremeWingCfgWlanMacRegistrationExternalEntry 2 }


                -- 1.3.6.1.4.1.1916.2.131.50.1.3.4.6.2.1.3
                extremeWingCfgWlanMacRegistrationExternalProxyMode OBJECT-TYPE
                        SYNTAX DisplayString
                        MAX-ACCESS read-write
                        STATUS current
                        DESCRIPTION
                                "/extremeWing-config/wlan[name=key1]/mac_registration_external/proxy_mode"
                        DEFVAL { "none" }
                        ::= { extremeWingCfgWlanMacRegistrationExternalEntry 3 }

		-- 1.3.6.1.4.1.1916.2.131.50.1.3.4.7
		extremeWingCfgWlanServiceMonitor OBJECT IDENTIFIER ::= { extremeWingCfgWlan 7 }

		
		-- 1.3.6.1.4.1.1916.2.131.50.1.3.4.7.1
		extremeWingCfgWlanServiceMonitorAdoptionTable OBJECT-TYPE
			SYNTAX SEQUENCE OF ExtremeWingCfgWlanServiceMonitorAdoptionEntry
			MAX-ACCESS not-accessible
			STATUS current
			DESCRIPTION
				"Description."
			::= { extremeWingCfgWlanServiceMonitor 1 }

		
		-- 1.3.6.1.4.1.1916.2.131.50.1.3.4.7.1.1
		extremeWingCfgWlanServiceMonitorAdoptionEntry OBJECT-TYPE
			SYNTAX ExtremeWingCfgWlanServiceMonitorAdoptionEntry
			MAX-ACCESS not-accessible
			STATUS current
			DESCRIPTION
				"Description."
			INDEX { extremeWingCfgWlanName }
			::= { extremeWingCfgWlanServiceMonitorAdoptionTable 1 }

		
		ExtremeWingCfgWlanServiceMonitorAdoptionEntry ::=
			SEQUENCE { 
				extremeWingCfgWlanServiceMonitorAdoptionName
					ExtremeWingIdentifier,
				extremeWingCfgWlanServiceMonitorAdoptionEnable
					TruthValue,
				extremeWingCfgWlanServiceMonitorAdoptionVlan
					Unsigned32
			 }

		-- 1.3.6.1.4.1.1916.2.131.50.1.3.4.7.1.1.1
		extremeWingCfgWlanServiceMonitorAdoptionName OBJECT-TYPE
			SYNTAX ExtremeWingIdentifier
			MAX-ACCESS read-only
			STATUS current
			DESCRIPTION
				"Name of the service to monitor (adoption or DHCP).
				XPATH: /extremeWing-config/wlan[name=key1]/service_monitor_adoption/name
				"
			::= { extremeWingCfgWlanServiceMonitorAdoptionEntry 1 }

		
		-- 1.3.6.1.4.1.1916.2.131.50.1.3.4.7.1.1.2
		extremeWingCfgWlanServiceMonitorAdoptionEnable OBJECT-TYPE
			SYNTAX TruthValue
			MAX-ACCESS read-write
			STATUS current
			DESCRIPTION
				"Enable/Disable the service monitor functionality for the service.
				XPATH: /extremeWing-config/wlan[name=key1]/service_monitor_adoption/enable"
			DEFVAL { false }
			::= { extremeWingCfgWlanServiceMonitorAdoptionEntry 2 }

		
		-- 1.3.6.1.4.1.1916.2.131.50.1.3.4.7.1.1.3
		extremeWingCfgWlanServiceMonitorAdoptionVlan OBJECT-TYPE
			SYNTAX Unsigned32 (1..4094)
			MAX-ACCESS read-write
			STATUS current
			DESCRIPTION
				"VLAN to which the clients need to be placed once the service being monitored fails.
				XPATH: /extremeWing-config/wlan[name=key1]/service_monitor_adoption/vlan"
			::= { extremeWingCfgWlanServiceMonitorAdoptionEntry 3 }

		-- 1.3.6.1.4.1.1916.2.131.50.1.3.4.7.2
		extremeWingCfgWlanServiceMonitorDhcpTable OBJECT-TYPE
			SYNTAX SEQUENCE OF ExtremeWingCfgWlanServiceMonitorDhcpEntry
			MAX-ACCESS not-accessible
			STATUS current
			DESCRIPTION
				"Description."
			::= { extremeWingCfgWlanServiceMonitor 2 }

		
		-- 1.3.6.1.4.1.1916.2.131.50.1.3.4.7.2.1
		extremeWingCfgWlanServiceMonitorDhcpEntry OBJECT-TYPE
			SYNTAX ExtremeWingCfgWlanServiceMonitorDhcpEntry
			MAX-ACCESS not-accessible
			STATUS current
			DESCRIPTION
				"Description."
			INDEX { extremeWingCfgWlanName }
			::= { extremeWingCfgWlanServiceMonitorDhcpTable 1 }

		
		ExtremeWingCfgWlanServiceMonitorDhcpEntry ::=
			SEQUENCE { 
				extremeWingCfgWlanServiceMonitorDhcpName
					ExtremeWingIdentifier,
				extremeWingCfgWlanServiceMonitorDhcpEnable
					TruthValue,
				extremeWingCfgWlanServiceMonitorDhcpVlan
					Unsigned32,
				extremeWingCfgWlanServiceMonitorDhcpCrmName
					DisplayString
			 }

		-- 1.3.6.1.4.1.1916.2.131.50.1.3.4.7.2.1.1
		extremeWingCfgWlanServiceMonitorDhcpName OBJECT-TYPE
			SYNTAX ExtremeWingIdentifier
			MAX-ACCESS read-only
			STATUS current
			DESCRIPTION
				"Description."
			::= { extremeWingCfgWlanServiceMonitorDhcpEntry 1 }

		
		-- 1.3.6.1.4.1.1916.2.131.50.1.3.4.7.2.1.2
		extremeWingCfgWlanServiceMonitorDhcpEnable OBJECT-TYPE
			SYNTAX TruthValue
			MAX-ACCESS read-write
			STATUS current
			DESCRIPTION
				"Enable/Disable the service monitor functionality for the service.
				XPATH: /extremeWing-config/wlan[name=key1]/service_monitor_dhcp/enable"
			DEFVAL { false }
			::= { extremeWingCfgWlanServiceMonitorDhcpEntry 2 }

		
		-- 1.3.6.1.4.1.1916.2.131.50.1.3.4.7.2.1.3
		extremeWingCfgWlanServiceMonitorDhcpVlan OBJECT-TYPE
			SYNTAX Unsigned32 (1..4094)
			MAX-ACCESS read-write
			STATUS current
			DESCRIPTION
				"VLAN to which the clients need to be placed once the service being monitored fails.
				XPATH: /extremeWing-config/wlan[name=key1]/service_monitor_dhcp/vlan"
			::= { extremeWingCfgWlanServiceMonitorDhcpEntry 3 }

		-- 1.3.6.1.4.1.1916.2.131.50.1.3.4.7.2.1.4
		extremeWingCfgWlanServiceMonitorDhcpCrmName OBJECT-TYPE
			SYNTAX DisplayString (SIZE (1..32))
			MAX-ACCESS read-write
			STATUS current
			DESCRIPTION
				"The CRM that is being used to monitor the service.
				XPATH: /extremeWing-config/wlan[name=key1]/service_monitor_dhcp/crm_name"
			DEFVAL { "" }
			::= { extremeWingCfgWlanServiceMonitorDhcpEntry 4 }


		-- 1.3.6.1.4.1.1916.2.131.50.1.3.4.8
		extremeWingCfgWlanTimeBasedAccessTable OBJECT-TYPE
			SYNTAX SEQUENCE OF ExtremeWingCfgWlanTimeBasedAccessEntry
			MAX-ACCESS not-accessible
			STATUS current
			DESCRIPTION
				"Description."
			::= { extremeWingCfgWlan 8 }

		
		-- 1.3.6.1.4.1.1916.2.131.50.1.3.4.8.1
		extremeWingCfgWlanTimeBasedAccessEntry OBJECT-TYPE
			SYNTAX ExtremeWingCfgWlanTimeBasedAccessEntry
			MAX-ACCESS not-accessible
			STATUS current
			DESCRIPTION
				"Description."
			INDEX { extremeWingCfgWlanName, extremeWingCfgWlanTimeBasedAccessDays }
			::= { extremeWingCfgWlanTimeBasedAccessTable 1 }

		
		ExtremeWingCfgWlanTimeBasedAccessEntry ::=
			SEQUENCE { 
				extremeWingCfgWlanTimeBasedAccessDays
					DisplayString,
				extremeWingCfgWlanTimeBasedAccessRowStatus
					RowStatus,
				extremeWingCfgWlanTimeBasedAccessStartTime
					DisplayString,
				extremeWingCfgWlanTimeBasedAccessEndTime
					DisplayString
			 }

		-- 1.3.6.1.4.1.1916.2.131.50.1.3.4.8.1.1
		extremeWingCfgWlanTimeBasedAccessDays OBJECT-TYPE
			SYNTAX DisplayString
			MAX-ACCESS read-create
			STATUS current
			DESCRIPTION
				"The days on which this rule would apply.
				/extremeWing-config/wlan[name=key1]/time_based_access[days=key2]/days
				"
			::= { extremeWingCfgWlanTimeBasedAccessEntry 1 }


		-- 1.3.6.1.4.1.1916.2.131.50.1.3.4.8.1.2
		extremeWingCfgWlanTimeBasedAccessRowStatus OBJECT-TYPE
			SYNTAX RowStatus
				{
				active(1),
				createAndGo(4),
				destroy(6)
				}
			MAX-ACCESS read-create
			STATUS current
			DESCRIPTION
				"Description."
			::= { extremeWingCfgWlanTimeBasedAccessEntry 2 }

		
		-- 1.3.6.1.4.1.1916.2.131.50.1.3.4.8.1.3
		extremeWingCfgWlanTimeBasedAccessStartTime OBJECT-TYPE
			SYNTAX DisplayString
			MAX-ACCESS read-create
			STATUS current
			DESCRIPTION
				"time at which this policy starts to apply
				/extremeWing-config/wlan[name=key1]/time_based_access[days=key2]/start_time"
			::= { extremeWingCfgWlanTimeBasedAccessEntry 3 }

		
		-- 1.3.6.1.4.1.1916.2.131.50.1.3.4.8.1.4
		extremeWingCfgWlanTimeBasedAccessEndTime OBJECT-TYPE
			SYNTAX DisplayString
			MAX-ACCESS read-create
			STATUS current
			DESCRIPTION
				"time at which this policy ends
				/extremeWing-config/wlan[name=key1]/time_based_access[days=key2]end_time"
			::= { extremeWingCfgWlanTimeBasedAccessEntry 4 }


-- /extremeWing-config/wlan_qos
		-- 1.3.6.1.4.1.1916.2.131.50.1.3.5
		extremeWingCfgWlanQos OBJECT IDENTIFIER ::= { extremeWingConfig 5 }

		
		-- 1.3.6.1.4.1.1916.2.131.50.1.3.5.1
		extremeWingCfgWlanQosTable OBJECT-TYPE
			SYNTAX SEQUENCE OF ExtremeWingCfgWlanQosEntry
			MAX-ACCESS not-accessible
			STATUS current
			DESCRIPTION
				"Configuration parameters of a wireless LAN QoS profile.
				
				/extremeWing-config/wlan_qos"
			::= { extremeWingCfgWlanQos 1 }

		
		-- 1.3.6.1.4.1.1916.2.131.50.1.3.5.1.1
		extremeWingCfgWlanQosEntry OBJECT-TYPE
			SYNTAX ExtremeWingCfgWlanQosEntry
			MAX-ACCESS not-accessible
			STATUS current
			DESCRIPTION
				"An entry in the table."
			INDEX { extremeWingCfgWlanQosName }
			::= { extremeWingCfgWlanQosTable 1 }

		
		ExtremeWingCfgWlanQosEntry ::=
			SEQUENCE { 
				extremeWingCfgWlanQosName
					ExtremeWingIdentifier,
				extremeWingCfgWlanQosClassification
					DisplayString,
				extremeWingCfgWlanQosNonWmmClassification
					DisplayString,
				extremeWingCfgWlanQosMulticastMaskPrimary
					DisplayString,
				extremeWingCfgWlanQosMulticastMaskSecondary
					DisplayString,
				extremeWingCfgWlanQosMulticastMaskAc
					DisplayString,
				extremeWingCfgWlanQosVoicePrioritization
					TruthValue,
				extremeWingCfgWlanQosSvpPrioritization
					TruthValue,
				extremeWingCfgWlanQosWmmPowerSave
					TruthValue,
				extremeWingCfgWlanQosWmmQbssLoadElement
					TruthValue,
				extremeWingCfgWlanQosWmmBestEffortTxopLimit
					Unsigned32,
				extremeWingCfgWlanQosWmmBestEffortAifsn
					Unsigned32,
				extremeWingCfgWlanQosWmmBestEffortCwMin
					Unsigned32,
				extremeWingCfgWlanQosWmmBestEffortCwMax
					Unsigned32,
				extremeWingCfgWlanQosWmmBackgroundTxopLimit
					Unsigned32,
				extremeWingCfgWlanQosWmmBackgroundAifsn
					Unsigned32,
				extremeWingCfgWlanQosWmmBackgroundCwMin
					Unsigned32,
				extremeWingCfgWlanQosWmmBackgroundCwMax
					Unsigned32,
				extremeWingCfgWlanQosWmmVideoTxopLimit
					Unsigned32,
				extremeWingCfgWlanQosWmmVideoAifsn
					Unsigned32,
				extremeWingCfgWlanQosWmmVideoCwMin
					Unsigned32,
				extremeWingCfgWlanQosWmmVideoCwMax
					Unsigned32,
				extremeWingCfgWlanQosWmmVoiceTxopLimit
					Unsigned32,
				extremeWingCfgWlanQosWmmVoiceAifsn
					Unsigned32,
				extremeWingCfgWlanQosWmmVoiceCwMin
					Unsigned32,
				extremeWingCfgWlanQosWmmVoiceCwMax
					Unsigned32,
				extremeWingCfgWlanQosWlanRlDownEnable
					TruthValue,
				extremeWingCfgWlanQosWlanRlDownRate
					Unsigned32,
				extremeWingCfgWlanQosWlanRlDownBurstSize
					Unsigned32,
				extremeWingCfgWlanQosWlanRlDownThreshBackground
					Unsigned32,
				extremeWingCfgWlanQosWlanRlDownThreshBestEffort
					Unsigned32,
				extremeWingCfgWlanQosWlanRlDownThreshVoice
					Unsigned32,
				extremeWingCfgWlanQosWlanRlDownThreshVideo
					Unsigned32,
				extremeWingCfgWlanQosWlanRlUpEnable
					TruthValue,
				extremeWingCfgWlanQosWlanRlUpRate
					Unsigned32,
				extremeWingCfgWlanQosWlanRlUpBurstSize
					Unsigned32,
				extremeWingCfgWlanQosWlanRlUpThreshBackground
					Unsigned32,
				extremeWingCfgWlanQosWlanRlUpThreshBestEffort
					Unsigned32,
				extremeWingCfgWlanQosWlanRlUpThreshVoice
					Unsigned32,
				extremeWingCfgWlanQosWlanRlUpThreshVideo
					Unsigned32,
				extremeWingCfgWlanQosMuRlDownEnable
					TruthValue,
				extremeWingCfgWlanQosMuRlDownRate
					Unsigned32,
				extremeWingCfgWlanQosMuRlDownBurstSize
					Unsigned32,
				extremeWingCfgWlanQosMuRlDownThreshBackground
					Unsigned32,
				extremeWingCfgWlanQosMuRlDownThreshBestEffort
					Unsigned32,
				extremeWingCfgWlanQosMuRlDownThreshVoice
					Unsigned32,
				extremeWingCfgWlanQosMuRlDownThreshVideo
					Unsigned32,
				extremeWingCfgWlanQosMuRlUpEnable
					TruthValue,
				extremeWingCfgWlanQosMuRlUpRate
					Unsigned32,
				extremeWingCfgWlanQosMuRlUpBurstSize
					Unsigned32,
				extremeWingCfgWlanQosMuRlUpThreshBackground
					Unsigned32,
				extremeWingCfgWlanQosMuRlUpThreshBestEffort
					Unsigned32,
				extremeWingCfgWlanQosMuRlUpThreshVoice
					Unsigned32,
				extremeWingCfgWlanQosMuRlUpThreshVideo
					Unsigned32,
				extremeWingCfgWlanQosQosTrustDscp
					TruthValue,
				extremeWingCfgWlanQosQosTrustWmm
					TruthValue
			 }

		-- 1.3.6.1.4.1.1916.2.131.50.1.3.5.1.1.1
		extremeWingCfgWlanQosName OBJECT-TYPE
			SYNTAX ExtremeWingIdentifier
			MAX-ACCESS read-only
			STATUS current
			DESCRIPTION
				"
				
				XPath: /extremeWing-config/wlan_qos[name=key1]/name"
			::= { extremeWingCfgWlanQosEntry 1 }

		
		-- 1.3.6.1.4.1.1916.2.131.50.1.3.5.1.1.3
		extremeWingCfgWlanQosClassification OBJECT-TYPE
			SYNTAX DisplayString
			MAX-ACCESS read-write
			STATUS current
			DESCRIPTION
				"How traffic on this WLAN will be classified (relative
				prioritization on the radio).
				
				Values:
				wmm
				voice
				video
				normal
				low
				
				XPath: /extremeWing-config/wlan_qos[name=key1]/classification"
			DEFVAL { "wmm" }
			::= { extremeWingCfgWlanQosEntry 3 }

		
		-- 1.3.6.1.4.1.1916.2.131.50.1.3.5.1.1.4
		extremeWingCfgWlanQosNonWmmClassification OBJECT-TYPE
			SYNTAX DisplayString
			MAX-ACCESS read-write
			STATUS current
			DESCRIPTION
				"Configure how non-wmm client traffic on this WLAN will be
				classified, if the wlan classification is wmm.
				
				Values:
				voice
				video
				normal
				low
				
				XPath: /extremeWing-config/wlan_qos[name=key1]/non_wmm_classification"
			DEFVAL { "normal" }
			::= { extremeWingCfgWlanQosEntry 4 }

		
		-- 1.3.6.1.4.1.1916.2.131.50.1.3.5.1.1.5
		extremeWingCfgWlanQosMulticastMaskPrimary OBJECT-TYPE
			SYNTAX DisplayString (SIZE (35))
			MAX-ACCESS read-write
			STATUS current
			DESCRIPTION
				"Egress multicast mask (matching packets will not be queued
				until DTIM).
				
				XPath: /extremeWing-config/wlan_qos[name=key1]/multicast_mask_primary"
			DEFVAL { "00-00-00-00-00-00/FF-FF-FF-FF-FF-FF" }
			::= { extremeWingCfgWlanQosEntry 5 }

		
		-- 1.3.6.1.4.1.1916.2.131.50.1.3.5.1.1.6
		extremeWingCfgWlanQosMulticastMaskSecondary OBJECT-TYPE
			SYNTAX DisplayString (SIZE (35))
			MAX-ACCESS read-write
			STATUS current
			DESCRIPTION
				"Egress multicast mask (matching packets will not be queued
				until DTIM).
				
				XPath: /extremeWing-config/wlan_qos[name=key1]/multicast_mask_secondary"
			DEFVAL { "00-00-00-00-00-00/FF-FF-FF-FF-FF-FF" }
			::= { extremeWingCfgWlanQosEntry 6 }

		
		-- 1.3.6.1.4.1.1916.2.131.50.1.3.5.1.1.7
		extremeWingCfgWlanQosMulticastMaskAc OBJECT-TYPE
			SYNTAX DisplayString
			MAX-ACCESS read-write
			STATUS current
			DESCRIPTION
				"How traffic that matches the multicast masks will be
				classified (relative prioritization on the radio).
				
				Values:
				voice
				video
				normal
				low
				default
				
				XPath: /extremeWing-config/wlan_qos[name=key1]/multicast_mask_ac"
			DEFVAL { "normal" }
			::= { extremeWingCfgWlanQosEntry 7 }

		
		-- 1.3.6.1.4.1.1916.2.131.50.1.3.5.1.1.8
		extremeWingCfgWlanQosVoicePrioritization OBJECT-TYPE
			SYNTAX TruthValue
			MAX-ACCESS read-write
			STATUS current
			DESCRIPTION
				"Prioritize voice Wireless Clients over other Wireless Clients
				(for non-WMM clients).
				
				XPath: /extremeWing-config/wlan_qos[name=key1]/voice_prioritization"
			DEFVAL { false }
			::= { extremeWingCfgWlanQosEntry 8 }

		
		-- 1.3.6.1.4.1.1916.2.131.50.1.3.5.1.1.9
		extremeWingCfgWlanQosSvpPrioritization OBJECT-TYPE
			SYNTAX TruthValue
			MAX-ACCESS read-write
			STATUS current
			DESCRIPTION
				"Enable Spectralink voice protocol support on this WLAN.
				
				XPath: /extremeWing-config/wlan_qos[name=key1]/svp_prioritization"
			DEFVAL { false }
			::= { extremeWingCfgWlanQosEntry 9 }

		
		-- 1.3.6.1.4.1.1916.2.131.50.1.3.5.1.1.10
		extremeWingCfgWlanQosWmmPowerSave OBJECT-TYPE
			SYNTAX TruthValue
			MAX-ACCESS read-write
			STATUS current
			DESCRIPTION
				"Enable support for WMM Power Save (U-APSD).
				
				XPath: /extremeWing-config/wlan_qos[name=key1]/wmm_power_save"
			DEFVAL { true }
			::= { extremeWingCfgWlanQosEntry 10 }

		
		-- 1.3.6.1.4.1.1916.2.131.50.1.3.5.1.1.11
		extremeWingCfgWlanQosWmmQbssLoadElement OBJECT-TYPE
			SYNTAX TruthValue
			MAX-ACCESS read-write
			STATUS current
			DESCRIPTION
				"Enable support for WMM QBSS Load Information Element in
				beacons and probe responses packets
				
				XPath: /extremeWing-config/wlan_qos[name=key1]/wmm_qbss_load_element"
			DEFVAL { true }
			::= { extremeWingCfgWlanQosEntry 11 }

		
		-- 1.3.6.1.4.1.1916.2.131.50.1.3.5.1.1.12
		extremeWingCfgWlanQosWmmBestEffortTxopLimit OBJECT-TYPE
			SYNTAX Unsigned32 (0..65535)
			MAX-ACCESS read-write
			STATUS current
			DESCRIPTION
				"
				
				XPath: /extremeWing-config/wlan_qos[name=key1]/wmm_best_effort_txop_limit"
			DEFVAL { 0 }
			::= { extremeWingCfgWlanQosEntry 12 }

		
		-- 1.3.6.1.4.1.1916.2.131.50.1.3.5.1.1.13
		extremeWingCfgWlanQosWmmBestEffortAifsn OBJECT-TYPE
			SYNTAX Unsigned32 (2..15)
			MAX-ACCESS read-write
			STATUS current
			DESCRIPTION
				"
				
				XPath: /extremeWing-config/wlan_qos[name=key1]/wmm_best_effort_aifsn"
			DEFVAL { 3 }
			::= { extremeWingCfgWlanQosEntry 13 }

		
		-- 1.3.6.1.4.1.1916.2.131.50.1.3.5.1.1.14
		extremeWingCfgWlanQosWmmBestEffortCwMin OBJECT-TYPE
			SYNTAX Unsigned32 (0..15)
			MAX-ACCESS read-write
			STATUS current
			DESCRIPTION
				"
				
				XPath: /extremeWing-config/wlan_qos[name=key1]/wmm_best_effort_cw_min"
			DEFVAL { 4 }
			::= { extremeWingCfgWlanQosEntry 14 }

		
		-- 1.3.6.1.4.1.1916.2.131.50.1.3.5.1.1.15
		extremeWingCfgWlanQosWmmBestEffortCwMax OBJECT-TYPE
			SYNTAX Unsigned32 (0..15)
			MAX-ACCESS read-write
			STATUS current
			DESCRIPTION
				"
				
				XPath: /extremeWing-config/wlan_qos[name=key1]/wmm_best_effort_cw_max"
			DEFVAL { 10 }
			::= { extremeWingCfgWlanQosEntry 15 }

		
		-- 1.3.6.1.4.1.1916.2.131.50.1.3.5.1.1.16
		extremeWingCfgWlanQosWmmBackgroundTxopLimit OBJECT-TYPE
			SYNTAX Unsigned32 (0..65535)
			MAX-ACCESS read-write
			STATUS current
			DESCRIPTION
				"
				
				XPath: /extremeWing-config/wlan_qos[name=key1]/wmm_background_txop_limit"
			DEFVAL { 0 }
			::= { extremeWingCfgWlanQosEntry 16 }

		
		-- 1.3.6.1.4.1.1916.2.131.50.1.3.5.1.1.17
		extremeWingCfgWlanQosWmmBackgroundAifsn OBJECT-TYPE
			SYNTAX Unsigned32 (2..15)
			MAX-ACCESS read-write
			STATUS current
			DESCRIPTION
				"
				
				XPath: /extremeWing-config/wlan_qos[name=key1]/wmm_background_aifsn"
			DEFVAL { 7 }
			::= { extremeWingCfgWlanQosEntry 17 }

		
		-- 1.3.6.1.4.1.1916.2.131.50.1.3.5.1.1.18
		extremeWingCfgWlanQosWmmBackgroundCwMin OBJECT-TYPE
			SYNTAX Unsigned32 (0..15)
			MAX-ACCESS read-write
			STATUS current
			DESCRIPTION
				"
				
				XPath: /extremeWing-config/wlan_qos[name=key1]/wmm_background_cw_min"
			DEFVAL { 4 }
			::= { extremeWingCfgWlanQosEntry 18 }

		
		-- 1.3.6.1.4.1.1916.2.131.50.1.3.5.1.1.19
		extremeWingCfgWlanQosWmmBackgroundCwMax OBJECT-TYPE
			SYNTAX Unsigned32 (0..15)
			MAX-ACCESS read-write
			STATUS current
			DESCRIPTION
				"
				
				XPath: /extremeWing-config/wlan_qos[name=key1]/wmm_background_cw_max"
			DEFVAL { 10 }
			::= { extremeWingCfgWlanQosEntry 19 }

		
		-- 1.3.6.1.4.1.1916.2.131.50.1.3.5.1.1.20
		extremeWingCfgWlanQosWmmVideoTxopLimit OBJECT-TYPE
			SYNTAX Unsigned32 (0..65535)
			MAX-ACCESS read-write
			STATUS current
			DESCRIPTION
				"
				
				XPath: /extremeWing-config/wlan_qos[name=key1]/wmm_video_txop_limit"
			DEFVAL { 94 }
			::= { extremeWingCfgWlanQosEntry 20 }

		
		-- 1.3.6.1.4.1.1916.2.131.50.1.3.5.1.1.21
		extremeWingCfgWlanQosWmmVideoAifsn OBJECT-TYPE
			SYNTAX Unsigned32 (2..15)
			MAX-ACCESS read-write
			STATUS current
			DESCRIPTION
				"
				
				XPath: /extremeWing-config/wlan_qos[name=key1]/wmm_video_aifsn"
			DEFVAL { 2 }
			::= { extremeWingCfgWlanQosEntry 21 }

		
		-- 1.3.6.1.4.1.1916.2.131.50.1.3.5.1.1.22
		extremeWingCfgWlanQosWmmVideoCwMin OBJECT-TYPE
			SYNTAX Unsigned32 (0..15)
			MAX-ACCESS read-write
			STATUS current
			DESCRIPTION
				"
				
				XPath: /extremeWing-config/wlan_qos[name=key1]/wmm_video_cw_min"
			DEFVAL { 3 }
			::= { extremeWingCfgWlanQosEntry 22 }

		
		-- 1.3.6.1.4.1.1916.2.131.50.1.3.5.1.1.23
		extremeWingCfgWlanQosWmmVideoCwMax OBJECT-TYPE
			SYNTAX Unsigned32 (0..15)
			MAX-ACCESS read-write
			STATUS current
			DESCRIPTION
				"
				
				XPath: /extremeWing-config/wlan_qos[name=key1]/wmm_video_cw_max"
			DEFVAL { 4 }
			::= { extremeWingCfgWlanQosEntry 23 }

		
		-- 1.3.6.1.4.1.1916.2.131.50.1.3.5.1.1.24
		extremeWingCfgWlanQosWmmVoiceTxopLimit OBJECT-TYPE
			SYNTAX Unsigned32 (0..65535)
			MAX-ACCESS read-write
			STATUS current
			DESCRIPTION
				"
				
				XPath: /extremeWing-config/wlan_qos[name=key1]/wmm_voice_txop_limit"
			DEFVAL { 47 }
			::= { extremeWingCfgWlanQosEntry 24 }

		
		-- 1.3.6.1.4.1.1916.2.131.50.1.3.5.1.1.25
		extremeWingCfgWlanQosWmmVoiceAifsn OBJECT-TYPE
			SYNTAX Unsigned32 (2..15)
			MAX-ACCESS read-write
			STATUS current
			DESCRIPTION
				"
				
				XPath: /extremeWing-config/wlan_qos[name=key1]/wmm_voice_aifsn"
			DEFVAL { 2 }
			::= { extremeWingCfgWlanQosEntry 25 }

		
		-- 1.3.6.1.4.1.1916.2.131.50.1.3.5.1.1.26
		extremeWingCfgWlanQosWmmVoiceCwMin OBJECT-TYPE
			SYNTAX Unsigned32 (0..15)
			MAX-ACCESS read-write
			STATUS current
			DESCRIPTION
				"
				
				XPath: /extremeWing-config/wlan_qos[name=key1]/wmm_voice_cw_min"
			DEFVAL { 2 }
			::= { extremeWingCfgWlanQosEntry 26 }

		
		-- 1.3.6.1.4.1.1916.2.131.50.1.3.5.1.1.27
		extremeWingCfgWlanQosWmmVoiceCwMax OBJECT-TYPE
			SYNTAX Unsigned32 (0..15)
			MAX-ACCESS read-write
			STATUS current
			DESCRIPTION
				"
				
				XPath: /extremeWing-config/wlan_qos[name=key1]/wmm_voice_cw_max"
			DEFVAL { 3 }
			::= { extremeWingCfgWlanQosEntry 27 }

		
		-- 1.3.6.1.4.1.1916.2.131.50.1.3.5.1.1.28
		extremeWingCfgWlanQosWlanRlDownEnable OBJECT-TYPE
			SYNTAX TruthValue
			MAX-ACCESS read-write
			STATUS current
			DESCRIPTION
				"Enable downstream (to air) traffic rate limiting on a WLAN.
				
				XPath: /extremeWing-config/wlan_qos[name=key1]/wlan_rl_down_enable"
			DEFVAL { false }
			::= { extremeWingCfgWlanQosEntry 28 }

		
		-- 1.3.6.1.4.1.1916.2.131.50.1.3.5.1.1.29
		extremeWingCfgWlanQosWlanRlDownRate OBJECT-TYPE
			SYNTAX Unsigned32 (50..1000000)
			UNITS "kbps"
			MAX-ACCESS read-write
			STATUS current
			DESCRIPTION
				"Traffic rate for downstream (to air) rate limiting on a WLAN.
				
				XPath: /extremeWing-config/wlan_qos[name=key1]/wlan_rl_down_rate"
			DEFVAL { 5000 }
			::= { extremeWingCfgWlanQosEntry 29 }

		
		-- 1.3.6.1.4.1.1916.2.131.50.1.3.5.1.1.30
		extremeWingCfgWlanQosWlanRlDownBurstSize OBJECT-TYPE
			SYNTAX Unsigned32 (2..1024)
			UNITS "kbytes"
			MAX-ACCESS read-write
			STATUS current
			DESCRIPTION
				"Maximum burst size for downstream (to air) rate limiting
				on a WLAN.
				
				XPath: /extremeWing-config/wlan_qos[name=key1]/wlan_rl_down_burst_size"
			DEFVAL { 320 }
			::= { extremeWingCfgWlanQosEntry 30 }

		
		-- 1.3.6.1.4.1.1916.2.131.50.1.3.5.1.1.31
		extremeWingCfgWlanQosWlanRlDownThreshBackground OBJECT-TYPE
			SYNTAX Unsigned32 (0..100)
			UNITS "%"
			MAX-ACCESS read-write
			STATUS current
			DESCRIPTION
				"Random early detection threshold in % of Maximum burst size
				for low priority traffic (downstream, to air, rate limiting
				on a WLAN).
				
				XPath: /extremeWing-config/wlan_qos[name=key1]/wlan_rl_down_thresh_background"
			DEFVAL { 50 }
			::= { extremeWingCfgWlanQosEntry 31 }

		
		-- 1.3.6.1.4.1.1916.2.131.50.1.3.5.1.1.32
		extremeWingCfgWlanQosWlanRlDownThreshBestEffort OBJECT-TYPE
			SYNTAX Unsigned32 (0..100)
			UNITS "%"
			MAX-ACCESS read-write
			STATUS current
			DESCRIPTION
				"Random early detection threshold in % of Maximum burst size
				for normal priority traffic (downstream, to air, rate limiting
				on a WLAN).
				
				XPath: /extremeWing-config/wlan_qos[name=key1]/wlan_rl_down_thresh_best_effort"
			DEFVAL { 50 }
			::= { extremeWingCfgWlanQosEntry 32 }

		
		-- 1.3.6.1.4.1.1916.2.131.50.1.3.5.1.1.33
		extremeWingCfgWlanQosWlanRlDownThreshVoice OBJECT-TYPE
			SYNTAX Unsigned32 (0..100)
			UNITS "%"
			MAX-ACCESS read-write
			STATUS current
			DESCRIPTION
				"Random early detection threshold in % of Maximum burst size
				for voice traffic (downstream, to air, rate limiting
				on a WLAN).
				
				XPath: /extremeWing-config/wlan_qos[name=key1]/wlan_rl_down_thresh_voice"
			DEFVAL { 0 }
			::= { extremeWingCfgWlanQosEntry 33 }

		
		-- 1.3.6.1.4.1.1916.2.131.50.1.3.5.1.1.34
		extremeWingCfgWlanQosWlanRlDownThreshVideo OBJECT-TYPE
			SYNTAX Unsigned32 (0..100)
			UNITS "%"
			MAX-ACCESS read-write
			STATUS current
			DESCRIPTION
				"Random early detection threshold in % of Maximum burst size
				for video traffic (downstream, to air, rate limiting
				on a WLAN).
				
				XPath: /extremeWing-config/wlan_qos[name=key1]/wlan_rl_down_thresh_video"
			DEFVAL { 25 }
			::= { extremeWingCfgWlanQosEntry 34 }

		
		-- 1.3.6.1.4.1.1916.2.131.50.1.3.5.1.1.35
		extremeWingCfgWlanQosWlanRlUpEnable OBJECT-TYPE
			SYNTAX TruthValue
			MAX-ACCESS read-write
			STATUS current
			DESCRIPTION
				"Enable upstream (from air) traffic rate limiting on a WLAN.
				
				XPath: /extremeWing-config/wlan_qos[name=key1]/wlan_rl_up_enable"
			DEFVAL { false }
			::= { extremeWingCfgWlanQosEntry 35 }

		
		-- 1.3.6.1.4.1.1916.2.131.50.1.3.5.1.1.36
		extremeWingCfgWlanQosWlanRlUpRate OBJECT-TYPE
			SYNTAX Unsigned32 (50..1000000)
			UNITS "kbps"
			MAX-ACCESS read-write
			STATUS current
			DESCRIPTION
				"Traffic rate for upstream (from air) rate limiting on a WLAN.
				
				XPath: /extremeWing-config/wlan_qos[name=key1]/wlan_rl_up_rate"
			DEFVAL { 5000 }
			::= { extremeWingCfgWlanQosEntry 36 }

		
		-- 1.3.6.1.4.1.1916.2.131.50.1.3.5.1.1.37
		extremeWingCfgWlanQosWlanRlUpBurstSize OBJECT-TYPE
			SYNTAX Unsigned32 (2..1024)
			UNITS "kbytes"
			MAX-ACCESS read-write
			STATUS current
			DESCRIPTION
				"Maximum burst size for upstream (from air) rate limiting
				on a WLAN.
				
				XPath: /extremeWing-config/wlan_qos[name=key1]/wlan_rl_up_burst_size"
			DEFVAL { 320 }
			::= { extremeWingCfgWlanQosEntry 37 }

		
		-- 1.3.6.1.4.1.1916.2.131.50.1.3.5.1.1.38
		extremeWingCfgWlanQosWlanRlUpThreshBackground OBJECT-TYPE
			SYNTAX Unsigned32 (0..100)
			UNITS "%"
			MAX-ACCESS read-write
			STATUS current
			DESCRIPTION
				"Random early detection threshold in % of Maximum burst size
				for low priority traffic (upstream, from air, rate limiting
				on a WLAN).
				
				XPath: /extremeWing-config/wlan_qos[name=key1]/wlan_rl_up_thresh_background"
			DEFVAL { 50 }
			::= { extremeWingCfgWlanQosEntry 38 }

		
		-- 1.3.6.1.4.1.1916.2.131.50.1.3.5.1.1.39
		extremeWingCfgWlanQosWlanRlUpThreshBestEffort OBJECT-TYPE
			SYNTAX Unsigned32 (0..100)
			UNITS "%"
			MAX-ACCESS read-write
			STATUS current
			DESCRIPTION
				"Random early detection threshold in % of Maximum burst size
				for normal priority traffic (upstream, from air,
				rate limiting on a WLAN).
				
				XPath: /extremeWing-config/wlan_qos[name=key1]/wlan_rl_up_thresh_best_effort"
			DEFVAL { 50 }
			::= { extremeWingCfgWlanQosEntry 39 }

		
		-- 1.3.6.1.4.1.1916.2.131.50.1.3.5.1.1.40
		extremeWingCfgWlanQosWlanRlUpThreshVoice OBJECT-TYPE
			SYNTAX Unsigned32 (0..100)
			UNITS "%"
			MAX-ACCESS read-write
			STATUS current
			DESCRIPTION
				"Random early detection threshold in % of Maximum burst size
				for voice traffic (upstream, from air, rate limiting
				on a WLAN).
				
				XPath: /extremeWing-config/wlan_qos[name=key1]/wlan_rl_up_thresh_voice"
			DEFVAL { 0 }
			::= { extremeWingCfgWlanQosEntry 40 }

		
		-- 1.3.6.1.4.1.1916.2.131.50.1.3.5.1.1.41
		extremeWingCfgWlanQosWlanRlUpThreshVideo OBJECT-TYPE
			SYNTAX Unsigned32 (0..100)
			UNITS "%"
			MAX-ACCESS read-write
			STATUS current
			DESCRIPTION
				"Random early detection threshold in % of Maximum burst size
				for video traffic (upstream, from air, rate limiting
				on a WLAN).
				
				XPath: /extremeWing-config/wlan_qos[name=key1]/wlan_rl_up_thresh_video"
			DEFVAL { 25 }
			::= { extremeWingCfgWlanQosEntry 41 }

		
		-- 1.3.6.1.4.1.1916.2.131.50.1.3.5.1.1.42
		extremeWingCfgWlanQosMuRlDownEnable OBJECT-TYPE
			SYNTAX TruthValue
			MAX-ACCESS read-write
			STATUS current
			DESCRIPTION
				"Enable downstream (to air) traffic rate limiting for
				Wireless Clients on a WLAN.
				
				XPath: /extremeWing-config/wlan_qos[name=key1]/mu_rl_down_enable"
			DEFVAL { false }
			::= { extremeWingCfgWlanQosEntry 42 }

		
		-- 1.3.6.1.4.1.1916.2.131.50.1.3.5.1.1.43
		extremeWingCfgWlanQosMuRlDownRate OBJECT-TYPE
			SYNTAX Unsigned32 (50..1000000)
			UNITS "kbps"
			MAX-ACCESS read-write
			STATUS current
			DESCRIPTION
				"Traffic rate for downstream (to air) rate limiting for
				Wireless Clients on a WLAN.
				
				XPath: /extremeWing-config/wlan_qos[name=key1]/mu_rl_down_rate"
			DEFVAL { 1000 }
			::= { extremeWingCfgWlanQosEntry 43 }

		
		-- 1.3.6.1.4.1.1916.2.131.50.1.3.5.1.1.44
		extremeWingCfgWlanQosMuRlDownBurstSize OBJECT-TYPE
			SYNTAX Unsigned32 (2..1024)
			UNITS "kbytes"
			MAX-ACCESS read-write
			STATUS current
			DESCRIPTION
				"Maximum burst size for downstream (to air) rate limiting for
				Wireless Clients on a WLAN.
				
				XPath: /extremeWing-config/wlan_qos[name=key1]/mu_rl_down_burst_size"
			DEFVAL { 64 }
			::= { extremeWingCfgWlanQosEntry 44 }

		
		-- 1.3.6.1.4.1.1916.2.131.50.1.3.5.1.1.45
		extremeWingCfgWlanQosMuRlDownThreshBackground OBJECT-TYPE
			SYNTAX Unsigned32 (0..100)
			UNITS "%"
			MAX-ACCESS read-write
			STATUS current
			DESCRIPTION
				"Random early detection threshold in % of Maximum burst size
				for low priority traffic (downstream, to air, rate limiting
				for clients on a WLAN.
				
				XPath: /extremeWing-config/wlan_qos[name=key1]/mu_rl_down_thresh_background"
			DEFVAL { 50 }
			::= { extremeWingCfgWlanQosEntry 45 }

		
		-- 1.3.6.1.4.1.1916.2.131.50.1.3.5.1.1.46
		extremeWingCfgWlanQosMuRlDownThreshBestEffort OBJECT-TYPE
			SYNTAX Unsigned32 (0..100)
			UNITS "%"
			MAX-ACCESS read-write
			STATUS current
			DESCRIPTION
				"Random early detection threshold in % of Maximum burst size
				for low priority traffic (downstream, to air, rate limiting
				for clients on a WLAN).
				
				XPath: /extremeWing-config/wlan_qos[name=key1]/mu_rl_down_thresh_best_effort"
			DEFVAL { 50 }
			::= { extremeWingCfgWlanQosEntry 46 }

		
		-- 1.3.6.1.4.1.1916.2.131.50.1.3.5.1.1.47
		extremeWingCfgWlanQosMuRlDownThreshVoice OBJECT-TYPE
			SYNTAX Unsigned32 (0..100)
			UNITS "%"
			MAX-ACCESS read-write
			STATUS current
			DESCRIPTION
				"Random early detection threshold in % of Maximum burst size
				for voice traffic (downstream, to air, rate limiting for
				clients on a WLAN).
				
				XPath: /extremeWing-config/wlan_qos[name=key1]/mu_rl_down_thresh_voice"
			DEFVAL { 0 }
			::= { extremeWingCfgWlanQosEntry 47 }

		
		-- 1.3.6.1.4.1.1916.2.131.50.1.3.5.1.1.48
		extremeWingCfgWlanQosMuRlDownThreshVideo OBJECT-TYPE
			SYNTAX Unsigned32 (0..100)
			UNITS "%"
			MAX-ACCESS read-write
			STATUS current
			DESCRIPTION
				"Random early detection threshold in % of Maximum burst size
				for video traffic (downstream, to air, rate limiting for
				clients on a WLAN).
				
				XPath: /extremeWing-config/wlan_qos[name=key1]/mu_rl_down_thresh_video"
			DEFVAL { 25 }
			::= { extremeWingCfgWlanQosEntry 48 }

		
		-- 1.3.6.1.4.1.1916.2.131.50.1.3.5.1.1.49
		extremeWingCfgWlanQosMuRlUpEnable OBJECT-TYPE
			SYNTAX TruthValue
			MAX-ACCESS read-write
			STATUS current
			DESCRIPTION
				"Enable upstream (from air) traffic rate limiting for
				Wireless Clients on a WLAN.
				
				XPath: /extremeWing-config/wlan_qos[name=key1]/mu_rl_up_enable"
			DEFVAL { false }
			::= { extremeWingCfgWlanQosEntry 49 }

		
		-- 1.3.6.1.4.1.1916.2.131.50.1.3.5.1.1.50
		extremeWingCfgWlanQosMuRlUpRate OBJECT-TYPE
			SYNTAX Unsigned32 (50..1000000)
			UNITS "kbps"
			MAX-ACCESS read-write
			STATUS current
			DESCRIPTION
				"Traffic rate for upstream (from air) rate limiting for
				Wireless Clients on a WLAN.
				
				XPath: /extremeWing-config/wlan_qos[name=key1]/mu_rl_up_rate"
			DEFVAL { 1000 }
			::= { extremeWingCfgWlanQosEntry 50 }

		
		-- 1.3.6.1.4.1.1916.2.131.50.1.3.5.1.1.51
		extremeWingCfgWlanQosMuRlUpBurstSize OBJECT-TYPE
			SYNTAX Unsigned32 (2..1024)
			UNITS "kbytes"
			MAX-ACCESS read-write
			STATUS current
			DESCRIPTION
				"Maximum burst size for upstream (from air) rate limiting for
				Wireless Clients on a WLAN.
				
				XPath: /extremeWing-config/wlan_qos[name=key1]/mu_rl_up_burst_size"
			DEFVAL { 64 }
			::= { extremeWingCfgWlanQosEntry 51 }

		
		-- 1.3.6.1.4.1.1916.2.131.50.1.3.5.1.1.52
		extremeWingCfgWlanQosMuRlUpThreshBackground OBJECT-TYPE
			SYNTAX Unsigned32 (0..100)
			UNITS "%"
			MAX-ACCESS read-write
			STATUS current
			DESCRIPTION
				"Random early detection threshold in % of Maximum burst size
				for low priority traffic (upstream, from air, rate limiting
				for clients on a WLAN).
				
				XPath: /extremeWing-config/wlan_qos[name=key1]/mu_rl_up_thresh_background"
			DEFVAL { 50 }
			::= { extremeWingCfgWlanQosEntry 52 }

		
		-- 1.3.6.1.4.1.1916.2.131.50.1.3.5.1.1.53
		extremeWingCfgWlanQosMuRlUpThreshBestEffort OBJECT-TYPE
			SYNTAX Unsigned32 (0..100)
			UNITS "%"
			MAX-ACCESS read-write
			STATUS current
			DESCRIPTION
				"Random early detection threshold in % of Maximum burst size
				for normal priority traffic (upstream, from air, rate limiting
				for clients on a WLAN).
				
				XPath: /extremeWing-config/wlan_qos[name=key1]/mu_rl_up_thresh_best_effort"
			DEFVAL { 50 }
			::= { extremeWingCfgWlanQosEntry 53 }

		
		-- 1.3.6.1.4.1.1916.2.131.50.1.3.5.1.1.54
		extremeWingCfgWlanQosMuRlUpThreshVoice OBJECT-TYPE
			SYNTAX Unsigned32 (0..100)
			UNITS "%"
			MAX-ACCESS read-write
			STATUS current
			DESCRIPTION
				"Random early detection threshold in % of Maximum burst size
				for voice traffic (upstream, from air, rate limiting
				for clients on a WLAN).
				
				XPath: /extremeWing-config/wlan_qos[name=key1]/mu_rl_up_thresh_voice"
			DEFVAL { 0 }
			::= { extremeWingCfgWlanQosEntry 54 }

		
		-- 1.3.6.1.4.1.1916.2.131.50.1.3.5.1.1.55
		extremeWingCfgWlanQosMuRlUpThreshVideo OBJECT-TYPE
			SYNTAX Unsigned32 (0..100)
			UNITS "%"
			MAX-ACCESS read-write
			STATUS current
			DESCRIPTION
				"Random early detection threshold in % of Maximum burst size
				for video traffic (upstream, from air, rate limiting
				for clients on a WLAN).
				
				XPath: /extremeWing-config/wlan_qos[name=key1]/mu_rl_up_thresh_video"
			DEFVAL { 25 }
			::= { extremeWingCfgWlanQosEntry 55 }

		
		-- 1.3.6.1.4.1.1916.2.131.50.1.3.5.1.1.56
		extremeWingCfgWlanQosQosTrustDscp OBJECT-TYPE
			SYNTAX TruthValue
			MAX-ACCESS read-write
			STATUS current
			DESCRIPTION
				"Trust IP DSCP values on WLANs.
				
				XPath: /extremeWing-config/wlan_qos[name=key1]/qos_trust_dscp"
			DEFVAL { true }
			::= { extremeWingCfgWlanQosEntry 56 }

		
		-- 1.3.6.1.4.1.1916.2.131.50.1.3.5.1.1.57
		extremeWingCfgWlanQosQosTrustWmm OBJECT-TYPE
			SYNTAX TruthValue
			MAX-ACCESS read-write
			STATUS current
			DESCRIPTION
				"Trust WMM values on WLANs.
				
				XPath: /extremeWing-config/wlan_qos[name=key1]/qos_trust_wmm"
			DEFVAL { true }
			::= { extremeWingCfgWlanQosEntry 57 }

		
		-- 1.3.6.1.4.1.1916.2.131.50.1.3.5.2
		extremeWingCfgWlanQosMcastStreamTable OBJECT-TYPE
			SYNTAX SEQUENCE OF ExtremeWingCfgWlanQosMcastStreamEntry
			MAX-ACCESS not-accessible
			STATUS current
			DESCRIPTION
				"Configure accelerated multicast streams address and
				forwarding QoS classification
				
				/extremeWing-config/wlan_qos/mcast_stream"
			::= { extremeWingCfgWlanQos 2 }

		
		-- 1.3.6.1.4.1.1916.2.131.50.1.3.5.2.1
		extremeWingCfgWlanQosMcastStreamEntry OBJECT-TYPE
			SYNTAX ExtremeWingCfgWlanQosMcastStreamEntry
			MAX-ACCESS not-accessible
			STATUS current
			DESCRIPTION
				"An entry in the table."
			INDEX { extremeWingCfgWlanQosName, extremeWingCfgWlanQosMcastStreamAddr }
			::= { extremeWingCfgWlanQosMcastStreamTable 1 }

		
		ExtremeWingCfgWlanQosMcastStreamEntry ::=
			SEQUENCE { 
				extremeWingCfgWlanQosMcastStreamAddr
					ExtremeWingIdentifier,
				extremeWingCfgWlanQosMcastStreamPriority
					DisplayString
			 }

		-- 1.3.6.1.4.1.1916.2.131.50.1.3.5.2.1.1
		extremeWingCfgWlanQosMcastStreamAddr OBJECT-TYPE
			SYNTAX ExtremeWingIdentifier
			MAX-ACCESS read-only
			STATUS current
			DESCRIPTION
				"Multicast IP address of the traffic stream that should be
				selected for accelerated delivery
				
				Note: an IP address of 0.0.0.0 is special, when it is selected
				that can be only entry in this table
								
				Although the type is an IP address, only multicast IP
				addresses (top 4 bits are E: 224.0.0.0 thru 239.255.255.255)
				should be set here.
				
				XPath: /extremeWing-config/wlan_qos[name=key1]/mcast_stream[addr=key2]/addr"
			::= { extremeWingCfgWlanQosMcastStreamEntry 1 }

		
		-- 1.3.6.1.4.1.1916.2.131.50.1.3.5.2.1.3
		extremeWingCfgWlanQosMcastStreamPriority OBJECT-TYPE
			SYNTAX DisplayString
			MAX-ACCESS read-write
			STATUS current
			DESCRIPTION
				"The forwarding qos classification (traffic class)
				
				Values:
				trust
				voice
				video
				best-effort
				background
				
				XPath: /extremeWing-config/wlan_qos[name=key1]/mcast_stream[addr=key2]/priority"
			DEFVAL { "trust" }
			::= { extremeWingCfgWlanQosMcastStreamEntry 3 }

		
-- /extremeWing-config/radio_qos
		-- 1.3.6.1.4.1.1916.2.131.50.1.3.6
		extremeWingCfgRadioQos OBJECT IDENTIFIER ::= { extremeWingConfig 6 }

		
		-- 1.3.6.1.4.1.1916.2.131.50.1.3.6.1
		extremeWingCfgRadioQosTable OBJECT-TYPE
			SYNTAX SEQUENCE OF ExtremeWingCfgRadioQosEntry
			MAX-ACCESS not-accessible
			STATUS current
			DESCRIPTION
				"Radio QoS profile
				
				/extremeWing-config/radio_qos"
			::= { extremeWingCfgRadioQos 1 }

		
		-- 1.3.6.1.4.1.1916.2.131.50.1.3.6.1.1
		extremeWingCfgRadioQosEntry OBJECT-TYPE
			SYNTAX ExtremeWingCfgRadioQosEntry
			MAX-ACCESS not-accessible
			STATUS current
			DESCRIPTION
				"An entry in the table."
			INDEX { extremeWingCfgRadioQosName }
			::= { extremeWingCfgRadioQosTable 1 }

		
		ExtremeWingCfgRadioQosEntry ::=
			SEQUENCE { 
				extremeWingCfgRadioQosName
					ExtremeWingIdentifier,
				extremeWingCfgRadioQosWmmBestEffortTxopLimit
					Unsigned32,
				extremeWingCfgRadioQosWmmBestEffortAifsn
					Unsigned32,
				extremeWingCfgRadioQosWmmBestEffortCwMin
					Unsigned32,
				extremeWingCfgRadioQosWmmBestEffortCwMax
					Unsigned32,
				extremeWingCfgRadioQosWmmBackgroundTxopLimit
					Unsigned32,
				extremeWingCfgRadioQosWmmBackgroundAifsn
					Unsigned32,
				extremeWingCfgRadioQosWmmBackgroundCwMin
					Unsigned32,
				extremeWingCfgRadioQosWmmBackgroundCwMax
					Unsigned32,
				extremeWingCfgRadioQosWmmVideoTxopLimit
					Unsigned32,
				extremeWingCfgRadioQosWmmVideoAifsn
					Unsigned32,
				extremeWingCfgRadioQosWmmVideoCwMin
					Unsigned32,
				extremeWingCfgRadioQosWmmVideoCwMax
					Unsigned32,
				extremeWingCfgRadioQosWmmVoiceTxopLimit
					Unsigned32,
				extremeWingCfgRadioQosWmmVoiceAifsn
					Unsigned32,
				extremeWingCfgRadioQosWmmVoiceCwMin
					Unsigned32,
				extremeWingCfgRadioQosWmmVoiceCwMax
					Unsigned32,
				extremeWingCfgRadioQosAdmCtrlFirewallDetectedTraffic
					TruthValue,
				extremeWingCfgRadioQosAdmCtrlImplicitTspec
					TruthValue,
				extremeWingCfgRadioQosAdmCtrlVoiceEnable
					TruthValue,
				extremeWingCfgRadioQosAdmCtrlVoiceMaxClients
					Unsigned32,
				extremeWingCfgRadioQosAdmCtrlVoiceMaxRoamedClients
					Unsigned32,
				extremeWingCfgRadioQosAdmCtrlVoiceMaxAirtimePercent
					Unsigned32,
				extremeWingCfgRadioQosAdmCtrlVoiceReservedForRoamPercent
					Unsigned32,
				extremeWingCfgRadioQosAdmCtrlVideoEnable
					TruthValue,
				extremeWingCfgRadioQosAdmCtrlVideoMaxClients
					Unsigned32,
				extremeWingCfgRadioQosAdmCtrlVideoMaxRoamedClients
					Unsigned32,
				extremeWingCfgRadioQosAdmCtrlVideoMaxAirtimePercent
					Unsigned32,
				extremeWingCfgRadioQosAdmCtrlVideoReservedForRoamPercent
					Unsigned32,
				extremeWingCfgRadioQosAdmCtrlBestEffortEnable
					TruthValue,
				extremeWingCfgRadioQosAdmCtrlBestEffortMaxClients
					Unsigned32,
				extremeWingCfgRadioQosAdmCtrlBestEffortMaxRoamedClients
					Unsigned32,
				extremeWingCfgRadioQosAdmCtrlBestEffortMaxAirtimePercent
					Unsigned32,
				extremeWingCfgRadioQosAdmCtrlBestEffortReservedForRoamPercent
					Unsigned32,
				extremeWingCfgRadioQosAdmCtrlBackgroundEnable
					TruthValue,
				extremeWingCfgRadioQosAdmCtrlBackgroundMaxClients
					Unsigned32,
				extremeWingCfgRadioQosAdmCtrlBackgroundMaxRoamedClients
					Unsigned32,
				extremeWingCfgRadioQosAdmCtrlBackgroundMaxAirtimePercent
					Unsigned32,
				extremeWingCfgRadioQosAdmCtrlBackgroundReservedForRoamPercent
					Unsigned32,
				extremeWingCfgRadioQosAccelMcastMaxStreams
					Unsigned32,
				extremeWingCfgRadioQosAccelMcastOverflowPolicy
					DisplayString,
				extremeWingCfgRadioQosAccelMcastMaxClientStreams
					Unsigned32,
				extremeWingCfgRadioQosAccelMcastStreamThreshold
					Unsigned32,
				extremeWingCfgRadioQosAccelMcastClientTimeout
					Unsigned32
			 }

		-- 1.3.6.1.4.1.1916.2.131.50.1.3.6.1.1.1
		extremeWingCfgRadioQosName OBJECT-TYPE
			SYNTAX ExtremeWingIdentifier
			MAX-ACCESS read-only
			STATUS current
			DESCRIPTION
				"
				
				XPath: /extremeWing-config/radio_qos[name=key1]/name"
			::= { extremeWingCfgRadioQosEntry 1 }

		
		-- 1.3.6.1.4.1.1916.2.131.50.1.3.6.1.1.3
		extremeWingCfgRadioQosWmmBestEffortTxopLimit OBJECT-TYPE
			SYNTAX Unsigned32 (0..65535)
			MAX-ACCESS read-write
			STATUS current
			DESCRIPTION
				"
				
				XPath: /extremeWing-config/radio_qos[name=key1]/wmm_best_effort_txop_limit"
			DEFVAL { 0 }
			::= { extremeWingCfgRadioQosEntry 3 }

		
		-- 1.3.6.1.4.1.1916.2.131.50.1.3.6.1.1.4
		extremeWingCfgRadioQosWmmBestEffortAifsn OBJECT-TYPE
			SYNTAX Unsigned32 (1..15)
			MAX-ACCESS read-write
			STATUS current
			DESCRIPTION
				"
				
				XPath: /extremeWing-config/radio_qos[name=key1]/wmm_best_effort_aifsn"
			DEFVAL { 3 }
			::= { extremeWingCfgRadioQosEntry 4 }

		
		-- 1.3.6.1.4.1.1916.2.131.50.1.3.6.1.1.5
		extremeWingCfgRadioQosWmmBestEffortCwMin OBJECT-TYPE
			SYNTAX Unsigned32 (0..15)
			MAX-ACCESS read-write
			STATUS current
			DESCRIPTION
				"
				
				XPath: /extremeWing-config/radio_qos[name=key1]/wmm_best_effort_cw_min"
			DEFVAL { 4 }
			::= { extremeWingCfgRadioQosEntry 5 }

		
		-- 1.3.6.1.4.1.1916.2.131.50.1.3.6.1.1.6
		extremeWingCfgRadioQosWmmBestEffortCwMax OBJECT-TYPE
			SYNTAX Unsigned32 (0..15)
			MAX-ACCESS read-write
			STATUS current
			DESCRIPTION
				"
				
				XPath: /extremeWing-config/radio_qos[name=key1]/wmm_best_effort_cw_max"
			DEFVAL { 6 }
			::= { extremeWingCfgRadioQosEntry 6 }

		
		-- 1.3.6.1.4.1.1916.2.131.50.1.3.6.1.1.7
		extremeWingCfgRadioQosWmmBackgroundTxopLimit OBJECT-TYPE
			SYNTAX Unsigned32 (0..65535)
			MAX-ACCESS read-write
			STATUS current
			DESCRIPTION
				"
				
				XPath: /extremeWing-config/radio_qos[name=key1]/wmm_background_txop_limit"
			DEFVAL { 0 }
			::= { extremeWingCfgRadioQosEntry 7 }

		
		-- 1.3.6.1.4.1.1916.2.131.50.1.3.6.1.1.8
		extremeWingCfgRadioQosWmmBackgroundAifsn OBJECT-TYPE
			SYNTAX Unsigned32 (1..15)
			MAX-ACCESS read-write
			STATUS current
			DESCRIPTION
				"
				
				XPath: /extremeWing-config/radio_qos[name=key1]/wmm_background_aifsn"
			DEFVAL { 7 }
			::= { extremeWingCfgRadioQosEntry 8 }

		
		-- 1.3.6.1.4.1.1916.2.131.50.1.3.6.1.1.9
		extremeWingCfgRadioQosWmmBackgroundCwMin OBJECT-TYPE
			SYNTAX Unsigned32 (0..15)
			MAX-ACCESS read-write
			STATUS current
			DESCRIPTION
				"
				
				XPath: /extremeWing-config/radio_qos[name=key1]/wmm_background_cw_min"
			DEFVAL { 4 }
			::= { extremeWingCfgRadioQosEntry 9 }

		
		-- 1.3.6.1.4.1.1916.2.131.50.1.3.6.1.1.10
		extremeWingCfgRadioQosWmmBackgroundCwMax OBJECT-TYPE
			SYNTAX Unsigned32 (0..15)
			MAX-ACCESS read-write
			STATUS current
			DESCRIPTION
				"
				
				XPath: /extremeWing-config/radio_qos[name=key1]/wmm_background_cw_max"
			DEFVAL { 10 }
			::= { extremeWingCfgRadioQosEntry 10 }

		
		-- 1.3.6.1.4.1.1916.2.131.50.1.3.6.1.1.11
		extremeWingCfgRadioQosWmmVideoTxopLimit OBJECT-TYPE
			SYNTAX Unsigned32 (0..65535)
			MAX-ACCESS read-write
			STATUS current
			DESCRIPTION
				"
				
				XPath: /extremeWing-config/radio_qos[name=key1]/wmm_video_txop_limit"
			DEFVAL { 94 }
			::= { extremeWingCfgRadioQosEntry 11 }

		
		-- 1.3.6.1.4.1.1916.2.131.50.1.3.6.1.1.12
		extremeWingCfgRadioQosWmmVideoAifsn OBJECT-TYPE
			SYNTAX Unsigned32 (1..15)
			MAX-ACCESS read-write
			STATUS current
			DESCRIPTION
				"
				
				XPath: /extremeWing-config/radio_qos[name=key1]/wmm_video_aifsn"
			DEFVAL { 1 }
			::= { extremeWingCfgRadioQosEntry 12 }

		
		-- 1.3.6.1.4.1.1916.2.131.50.1.3.6.1.1.13
		extremeWingCfgRadioQosWmmVideoCwMin OBJECT-TYPE
			SYNTAX Unsigned32 (0..15)
			MAX-ACCESS read-write
			STATUS current
			DESCRIPTION
				"
				
				XPath: /extremeWing-config/radio_qos[name=key1]/wmm_video_cw_min"
			DEFVAL { 3 }
			::= { extremeWingCfgRadioQosEntry 13 }

		
		-- 1.3.6.1.4.1.1916.2.131.50.1.3.6.1.1.14
		extremeWingCfgRadioQosWmmVideoCwMax OBJECT-TYPE
			SYNTAX Unsigned32 (0..15)
			MAX-ACCESS read-write
			STATUS current
			DESCRIPTION
				"
				
				XPath: /extremeWing-config/radio_qos[name=key1]/wmm_video_cw_max"
			DEFVAL { 4 }
			::= { extremeWingCfgRadioQosEntry 14 }

		
		-- 1.3.6.1.4.1.1916.2.131.50.1.3.6.1.1.15
		extremeWingCfgRadioQosWmmVoiceTxopLimit OBJECT-TYPE
			SYNTAX Unsigned32 (0..65535)
			MAX-ACCESS read-write
			STATUS current
			DESCRIPTION
				"
				
				XPath: /extremeWing-config/radio_qos[name=key1]/wmm_voice_txop_limit"
			DEFVAL { 47 }
			::= { extremeWingCfgRadioQosEntry 15 }

		
		-- 1.3.6.1.4.1.1916.2.131.50.1.3.6.1.1.16
		extremeWingCfgRadioQosWmmVoiceAifsn OBJECT-TYPE
			SYNTAX Unsigned32 (1..15)
			MAX-ACCESS read-write
			STATUS current
			DESCRIPTION
				"
				
				XPath: /extremeWing-config/radio_qos[name=key1]/wmm_voice_aifsn"
			DEFVAL { 1 }
			::= { extremeWingCfgRadioQosEntry 16 }

		
		-- 1.3.6.1.4.1.1916.2.131.50.1.3.6.1.1.17
		extremeWingCfgRadioQosWmmVoiceCwMin OBJECT-TYPE
			SYNTAX Unsigned32 (0..15)
			MAX-ACCESS read-write
			STATUS current
			DESCRIPTION
				"
				
				XPath: /extremeWing-config/radio_qos[name=key1]/wmm_voice_cw_min"
			DEFVAL { 2 }
			::= { extremeWingCfgRadioQosEntry 17 }

		
		-- 1.3.6.1.4.1.1916.2.131.50.1.3.6.1.1.18
		extremeWingCfgRadioQosWmmVoiceCwMax OBJECT-TYPE
			SYNTAX Unsigned32 (0..15)
			MAX-ACCESS read-write
			STATUS current
			DESCRIPTION
				"
				
				XPath: /extremeWing-config/radio_qos[name=key1]/wmm_voice_cw_max"
			DEFVAL { 3 }
			::= { extremeWingCfgRadioQosEntry 18 }

		
		-- 1.3.6.1.4.1.1916.2.131.50.1.3.6.1.1.19
		extremeWingCfgRadioQosAdmCtrlFirewallDetectedTraffic OBJECT-TYPE
			SYNTAX TruthValue
			MAX-ACCESS read-write
			STATUS current
			DESCRIPTION
				"Enforce admission control for traffic whose access category
				is detected by the firewall ALG (e.g. SIP voice calls).
				Could result in rejected calls
				
				XPath: /extremeWing-config/radio_qos[name=key1]/admission_control_firewall_detected_traffic"
			DEFVAL { true }
			::= { extremeWingCfgRadioQosEntry 19 }

		
		-- 1.3.6.1.4.1.1916.2.131.50.1.3.6.1.1.20
		extremeWingCfgRadioQosAdmCtrlImplicitTspec OBJECT-TYPE
			SYNTAX TruthValue
			MAX-ACCESS read-write
			STATUS current
			DESCRIPTION
				"Enforce admission control for clients that do not support
				WMM-TSPEC but are accessing admission controlled
				access categories. Could result in downgraded traffic
				
				XPath: /extremeWing-config/radio_qos[name=key1]/admission_control_implicit_tspec"
			DEFVAL { true }
			::= { extremeWingCfgRadioQosEntry 20 }

		
		-- 1.3.6.1.4.1.1916.2.131.50.1.3.6.1.1.21
		extremeWingCfgRadioQosAdmCtrlVoiceEnable OBJECT-TYPE
			SYNTAX TruthValue
			MAX-ACCESS read-write
			STATUS current
			DESCRIPTION
				"Enable Voice access category admission control.
				
				XPath: /extremeWing-config/radio_qos[name=key1]/admission_control_voice_enable"
			DEFVAL { false }
			::= { extremeWingCfgRadioQosEntry 21 }

		
		-- 1.3.6.1.4.1.1916.2.131.50.1.3.6.1.1.22
		extremeWingCfgRadioQosAdmCtrlVoiceMaxClients OBJECT-TYPE
			SYNTAX Unsigned32 (0..256)
			MAX-ACCESS read-write
			STATUS current
			DESCRIPTION
				"Maximum number of non-roamed wireless clients admitted.
				
				XPath: /extremeWing-config/radio_qos[name=key1]/admission_control_voice_max_mus"
			DEFVAL { 100 }
			::= { extremeWingCfgRadioQosEntry 22 }

		
		-- 1.3.6.1.4.1.1916.2.131.50.1.3.6.1.1.23
		extremeWingCfgRadioQosAdmCtrlVoiceMaxRoamedClients OBJECT-TYPE
			SYNTAX Unsigned32 (0..256)
			MAX-ACCESS read-write
			STATUS current
			DESCRIPTION
				"Maximum number of additional roamed wireless clients admitted.
				
				XPath: /extremeWing-config/radio_qos[name=key1]/admission_control_voice_max_roamed_mus"
			DEFVAL { 10 }
			::= { extremeWingCfgRadioQosEntry 23 }

		
		-- 1.3.6.1.4.1.1916.2.131.50.1.3.6.1.1.24
		extremeWingCfgRadioQosAdmCtrlVoiceMaxAirtimePercent OBJECT-TYPE
			SYNTAX Unsigned32 (0..150)
			MAX-ACCESS read-write
			STATUS current
			DESCRIPTION
				"Maximum percentage of airtime for this access category for
				non-roamed wireless clients.
				
				XPath: /extremeWing-config/radio_qos[name=key1]/admission_control_voice_max_airtime_percent"
			DEFVAL { 75 }
			::= { extremeWingCfgRadioQosEntry 24 }

		
		-- 1.3.6.1.4.1.1916.2.131.50.1.3.6.1.1.25
		extremeWingCfgRadioQosAdmCtrlVoiceReservedForRoamPercent OBJECT-TYPE
			SYNTAX Unsigned32 (0..150)
			MAX-ACCESS read-write
			STATUS current
			DESCRIPTION
				"Additional percentage of air time allocated exclusively for
				roamed wireless clients.
				
				XPath: /extremeWing-config/radio_qos[name=key1]/admission_control_voice_reserved_for_roam_percent"
			DEFVAL { 10 }
			::= { extremeWingCfgRadioQosEntry 25 }

		
		-- 1.3.6.1.4.1.1916.2.131.50.1.3.6.1.1.26
		extremeWingCfgRadioQosAdmCtrlVideoEnable OBJECT-TYPE
			SYNTAX TruthValue
			MAX-ACCESS read-write
			STATUS current
			DESCRIPTION
				"Enable Video access category admission control.
				
				XPath: /extremeWing-config/radio_qos[name=key1]/admission_control_video_enable"
			DEFVAL { false }
			::= { extremeWingCfgRadioQosEntry 26 }

		
		-- 1.3.6.1.4.1.1916.2.131.50.1.3.6.1.1.27
		extremeWingCfgRadioQosAdmCtrlVideoMaxClients OBJECT-TYPE
			SYNTAX Unsigned32 (0..256)
			MAX-ACCESS read-write
			STATUS current
			DESCRIPTION
				"Maximum number of non-roamed wireless clients admitted.
				
				XPath: /extremeWing-config/radio_qos[name=key1]/admission_control_video_max_mus"
			DEFVAL { 100 }
			::= { extremeWingCfgRadioQosEntry 27 }

		
		-- 1.3.6.1.4.1.1916.2.131.50.1.3.6.1.1.28
		extremeWingCfgRadioQosAdmCtrlVideoMaxRoamedClients OBJECT-TYPE
			SYNTAX Unsigned32 (0..256)
			MAX-ACCESS read-write
			STATUS current
			DESCRIPTION
				"Maximum number of additional roamed wireless clients admitted.
				
				XPath: /extremeWing-config/radio_qos[name=key1]/admission_control_video_max_roamed_mus"
			DEFVAL { 10 }
			::= { extremeWingCfgRadioQosEntry 28 }

		
		-- 1.3.6.1.4.1.1916.2.131.50.1.3.6.1.1.29
		extremeWingCfgRadioQosAdmCtrlVideoMaxAirtimePercent OBJECT-TYPE
			SYNTAX Unsigned32 (0..150)
			MAX-ACCESS read-write
			STATUS current
			DESCRIPTION
				"Maximum percentage of airtime for this access category for
				non-roamed wireless clients.
				
				XPath: /extremeWing-config/radio_qos[name=key1]/admission_control_video_max_airtime_percent"
			DEFVAL { 75 }
			::= { extremeWingCfgRadioQosEntry 29 }

		
		-- 1.3.6.1.4.1.1916.2.131.50.1.3.6.1.1.30
		extremeWingCfgRadioQosAdmCtrlVideoReservedForRoamPercent OBJECT-TYPE
			SYNTAX Unsigned32 (0..150)
			MAX-ACCESS read-write
			STATUS current
			DESCRIPTION
				"Additional percentage of air time allocated exclusively for
				roamed wireless clients.
				
				XPath: /extremeWing-config/radio_qos[name=key1]/admission_control_video_reserved_for_roam_percent"
			DEFVAL { 10 }
			::= { extremeWingCfgRadioQosEntry 30 }

		
		-- 1.3.6.1.4.1.1916.2.131.50.1.3.6.1.1.31
		extremeWingCfgRadioQosAdmCtrlBestEffortEnable OBJECT-TYPE
			SYNTAX TruthValue
			MAX-ACCESS read-write
			STATUS current
			DESCRIPTION
				"Enable Best Effort access category admission control.
				
				XPath: /extremeWing-config/radio_qos[name=key1]/admission_control_best_effort_enable"
			DEFVAL { false }
			::= { extremeWingCfgRadioQosEntry 31 }

		
		-- 1.3.6.1.4.1.1916.2.131.50.1.3.6.1.1.32
		extremeWingCfgRadioQosAdmCtrlBestEffortMaxClients OBJECT-TYPE
			SYNTAX Unsigned32 (0..256)
			MAX-ACCESS read-write
			STATUS current
			DESCRIPTION
				"Maximum number of non-roamed wireless clients admitted.
				
				XPath: /extremeWing-config/radio_qos[name=key1]/admission_control_best_effort_max_mus"
			DEFVAL { 100 }
			::= { extremeWingCfgRadioQosEntry 32 }

		
		-- 1.3.6.1.4.1.1916.2.131.50.1.3.6.1.1.33
		extremeWingCfgRadioQosAdmCtrlBestEffortMaxRoamedClients OBJECT-TYPE
			SYNTAX Unsigned32 (0..256)
			MAX-ACCESS read-write
			STATUS current
			DESCRIPTION
				"Maximum number of additional roamed wireless clients admitted.
				
				XPath: /extremeWing-config/radio_qos[name=key1]/admission_control_best_effort_max_roamed_mus"
			DEFVAL { 10 }
			::= { extremeWingCfgRadioQosEntry 33 }

		
		-- 1.3.6.1.4.1.1916.2.131.50.1.3.6.1.1.34
		extremeWingCfgRadioQosAdmCtrlBestEffortMaxAirtimePercent OBJECT-TYPE
			SYNTAX Unsigned32 (0..150)
			MAX-ACCESS read-write
			STATUS current
			DESCRIPTION
				"Maximum percentage of airtime for this access category for
				non-roamed wireless clients.
				
				XPath: /extremeWing-config/radio_qos[name=key1]/admission_control_best_effort_max_airtime_percent"
			DEFVAL { 75 }
			::= { extremeWingCfgRadioQosEntry 34 }

		
		-- 1.3.6.1.4.1.1916.2.131.50.1.3.6.1.1.35
		extremeWingCfgRadioQosAdmCtrlBestEffortReservedForRoamPercent OBJECT-TYPE
			SYNTAX Unsigned32 (0..150)
			MAX-ACCESS read-write
			STATUS current
			DESCRIPTION
				"Additional percentage of air time allocated exclusively for
				roamed wireless clients.
				
				XPath: /extremeWing-config/radio_qos[name=key1]/admission_control_best_effort_reserved_for_roam_percent"
			DEFVAL { 10 }
			::= { extremeWingCfgRadioQosEntry 35 }

		
		-- 1.3.6.1.4.1.1916.2.131.50.1.3.6.1.1.36
		extremeWingCfgRadioQosAdmCtrlBackgroundEnable OBJECT-TYPE
			SYNTAX TruthValue
			MAX-ACCESS read-write
			STATUS current
			DESCRIPTION
				"Enable Background access category admission control.
				
				XPath: /extremeWing-config/radio_qos[name=key1]/admission_control_background_enable"
			DEFVAL { false }
			::= { extremeWingCfgRadioQosEntry 36 }

		
		-- 1.3.6.1.4.1.1916.2.131.50.1.3.6.1.1.37
		extremeWingCfgRadioQosAdmCtrlBackgroundMaxClients OBJECT-TYPE
			SYNTAX Unsigned32 (0..256)
			MAX-ACCESS read-write
			STATUS current
			DESCRIPTION
				"Maximum number of non-roamed wireless clients admitted.
				
				XPath: /extremeWing-config/radio_qos[name=key1]/admission_control_background_max_mus"
			DEFVAL { 100 }
			::= { extremeWingCfgRadioQosEntry 37 }

		
		-- 1.3.6.1.4.1.1916.2.131.50.1.3.6.1.1.38
		extremeWingCfgRadioQosAdmCtrlBackgroundMaxRoamedClients OBJECT-TYPE
			SYNTAX Unsigned32 (0..256)
			MAX-ACCESS read-write
			STATUS current
			DESCRIPTION
				"Maximum number of additional roamed wireless clients admitted.
				
				XPath: /extremeWing-config/radio_qos[name=key1]/admission_control_background_max_roamed_mus"
			DEFVAL { 10 }
			::= { extremeWingCfgRadioQosEntry 38 }

		
		-- 1.3.6.1.4.1.1916.2.131.50.1.3.6.1.1.39
		extremeWingCfgRadioQosAdmCtrlBackgroundMaxAirtimePercent OBJECT-TYPE
			SYNTAX Unsigned32 (0..150)
			MAX-ACCESS read-write
			STATUS current
			DESCRIPTION
				"Maximum percentage of airtime for this access category for
				non-roamed wireless clients.
				
				XPath: /extremeWing-config/radio_qos[name=key1]/admission_control_background_max_airtime_percent"
			DEFVAL { 75 }
			::= { extremeWingCfgRadioQosEntry 39 }

		
		-- 1.3.6.1.4.1.1916.2.131.50.1.3.6.1.1.40
		extremeWingCfgRadioQosAdmCtrlBackgroundReservedForRoamPercent OBJECT-TYPE
			SYNTAX Unsigned32 (0..150)
			MAX-ACCESS read-write
			STATUS current
			DESCRIPTION
				"Additional percentage of air time allocated exclusively for
				roamed wireless clients.
				
				XPath: /extremeWing-config/radio_qos[name=key1]/admission_control_background_reserved_for_roam_percent"
			DEFVAL { 10 }
			::= { extremeWingCfgRadioQosEntry 40 }

		
		-- 1.3.6.1.4.1.1916.2.131.50.1.3.6.1.1.41
		extremeWingCfgRadioQosAccelMcastMaxStreams OBJECT-TYPE
			SYNTAX Unsigned32 (0..256)
			MAX-ACCESS read-write
			STATUS current
			DESCRIPTION
				"Maximum number of accelerated multicast streams per radio.
				
				XPath: /extremeWing-config/radio_qos[name=key1]/accelerated_multicast_max_streams"
			DEFVAL { 25 }
			::= { extremeWingCfgRadioQosEntry 41 }

		
		-- 1.3.6.1.4.1.1916.2.131.50.1.3.6.1.1.42
		extremeWingCfgRadioQosAccelMcastOverflowPolicy OBJECT-TYPE
			SYNTAX DisplayString
			MAX-ACCESS read-write
			STATUS current
			DESCRIPTION
				"Policy for what to do when more then the maximum number of
				accelerated multicast streams become active: Revert to
				non-accelerated multicast or reject new streams.
				
				Values:
				revert
				reject
				
				XPath: /extremeWing-config/radio_qos[name=key1]/accelerated_multicast_overflow_policy"
			DEFVAL { "reject" }
			::= { extremeWingCfgRadioQosEntry 42 }

		
		-- 1.3.6.1.4.1.1916.2.131.50.1.3.6.1.1.43
		extremeWingCfgRadioQosAccelMcastMaxClientStreams OBJECT-TYPE
			SYNTAX Unsigned32 (1..4)
			MAX-ACCESS read-write
			STATUS current
			DESCRIPTION
				"Maximum number of accelerated multicast streams per
				wireless client.
				
				XPath: /extremeWing-config/radio_qos[name=key1]/accelerated_multicast_max_client_streams"
			DEFVAL { 2 }
			::= { extremeWingCfgRadioQosEntry 43 }

		
		-- 1.3.6.1.4.1.1916.2.131.50.1.3.6.1.1.44
		extremeWingCfgRadioQosAccelMcastStreamThreshold OBJECT-TYPE
			SYNTAX Unsigned32 (1..500)
			MAX-ACCESS read-write
			STATUS current
			DESCRIPTION
				"Packets per second threshold for a multicast stream to
				qualify for accelerated multicast in case the multicast
				address was not explicitly configured.
				
				XPath: /extremeWing-config/radio_qos[name=key1]/accelerated_multicast_stream_threshold"
			DEFVAL { 25 }
			::= { extremeWingCfgRadioQosEntry 44 }

		
		-- 1.3.6.1.4.1.1916.2.131.50.1.3.6.1.1.45
		extremeWingCfgRadioQosAccelMcastClientTimeout OBJECT-TYPE
			SYNTAX Unsigned32 (5..6000)
			MAX-ACCESS read-write
			STATUS current
			DESCRIPTION
				"Number of seconds between reJOINING of a wireless client to
				an accelerated multicast stream. Client may be removed if it
				does not respond to a request during that time.
				
				XPath: /extremeWing-config/radio_qos[name=key1]/accelerated_multicast_client_timeout"
			DEFVAL { 60 }
			::= { extremeWingCfgRadioQosEntry 45 }

		
-- /extremeWing-config/aaa_policy
		-- 1.3.6.1.4.1.1916.2.131.50.1.3.7
		extremeWingCfgAaa OBJECT IDENTIFIER ::= { extremeWingConfig 7 }

		
		-- 1.3.6.1.4.1.1916.2.131.50.1.3.7.1
		extremeWingCfgAaaTable OBJECT-TYPE
			SYNTAX SEQUENCE OF ExtremeWingCfgAaaEntry
			MAX-ACCESS not-accessible
			STATUS current
			DESCRIPTION
				"AAA policy
				
				/extremeWing-config/aaa_policy"
			::= { extremeWingCfgAaa 1 }

		
		-- 1.3.6.1.4.1.1916.2.131.50.1.3.7.1.1
		extremeWingCfgAaaEntry OBJECT-TYPE
			SYNTAX ExtremeWingCfgAaaEntry
			MAX-ACCESS not-accessible
			STATUS current
			DESCRIPTION
				"An entry in the table."
			INDEX { extremeWingCfgAaaName }
			::= { extremeWingCfgAaaTable 1 }

		
		ExtremeWingCfgAaaEntry ::=
			SEQUENCE { 
				extremeWingCfgAaaName
					ExtremeWingIdentifier,
				extremeWingCfgAaaServerPoolingMode
					DisplayString,
				extremeWingCfgAaaMacAddrFormat
					DisplayString,
				extremeWingCfgAaaMacAddrCase
					DisplayString,
				extremeWingCfgAaaMacAddrAttributes
					DisplayString,
				extremeWingCfgAaaEapClientTimeout
					Unsigned32,
				extremeWingCfgAaaEapClientAttempts
					Unsigned32,
				extremeWingCfgAaaEapClientRetryFactor
					Unsigned32,
				extremeWingCfgAaaEapClientIdReqTimeout
					Unsigned32,
				extremeWingCfgAaaAuthProtocol
					DisplayString,
				extremeWingCfgAaaAccountingType
					DisplayString,
				extremeWingCfgAaaInterimAccountingInterval
					Unsigned32,
				extremeWingCfgAaaNacList
					ExtremeWingIdentifier
			 }

		-- 1.3.6.1.4.1.1916.2.131.50.1.3.7.1.1.1
		extremeWingCfgAaaName OBJECT-TYPE
			SYNTAX ExtremeWingIdentifier
			MAX-ACCESS read-only
			STATUS current
			DESCRIPTION
				"The user-defined name of the AAA policy.
				
				XPath: /extremeWing-config/aaa_policy[name=key1]/name"
			::= { extremeWingCfgAaaEntry 1 }

		
		-- 1.3.6.1.4.1.1916.2.131.50.1.3.7.1.1.3
		extremeWingCfgAaaServerPoolingMode OBJECT-TYPE
			SYNTAX DisplayString
			MAX-ACCESS read-write
			STATUS current
			DESCRIPTION
				"Controls how requests are transmitted across RADIUS servers.
				Failover implies working down the list of servers if any
				server is unresponsive. load-balanced implies use of all
				servers, transmitting requests in a round-robin fashion.
				
				Values:
				failover
				load-balance
				
				XPath: /extremeWing-config/aaa_policy[name=key1]/server_pooling_mode"
			DEFVAL { "failover" }
			::= { extremeWingCfgAaaEntry 3 }

		
		-- 1.3.6.1.4.1.1916.2.131.50.1.3.7.1.1.4
		extremeWingCfgAaaMacAddrFormat OBJECT-TYPE
			SYNTAX DisplayString
			MAX-ACCESS read-write
			STATUS current
			DESCRIPTION
				"Configure the format in which the MAC address is packed
				in the RADIUS request packets
				(AABBCCDDEEFF/AA:BB:CC:DD:EE:FF/AA-BB-CC-DD-EE-FF/
				AABB.CCDD.EEFF/AABBCC-DDEEFF).
				
				Values:
				no-delim
				pair-colon
				pair-hyphen
				quad-dot
				middle-hyphen
				
				XPath: /extremeWing-config/aaa_policy[name=key1]/mac_address_format/format"
			DEFVAL { "pair-hyphen" }
			::= { extremeWingCfgAaaEntry 4 }

		
		-- 1.3.6.1.4.1.1916.2.131.50.1.3.7.1.1.5
		extremeWingCfgAaaMacAddrCase OBJECT-TYPE
			SYNTAX DisplayString
			MAX-ACCESS read-write
			STATUS current
			DESCRIPTION
				"whether the MAC address is filled in upper case
				(AA-BB-CC-DD-EE-FF) or lower case (aa-bb-cc-dd-ee-ff)
				
				Values:
				upper
				lower
				
				XPath: /extremeWing-config/aaa_policy[name=key1]/mac_address_format/case"
			DEFVAL { "upper" }
			::= { extremeWingCfgAaaEntry 5 }

		
		-- 1.3.6.1.4.1.1916.2.131.50.1.3.7.1.1.6
		extremeWingCfgAaaMacAddrAttributes OBJECT-TYPE
			SYNTAX DisplayString
			MAX-ACCESS read-write
			STATUS current
			DESCRIPTION
				"whether this format specified applies only to the
				username/password in mac-auth, or for all attributes that
				include a mac address, such as calling-station-id,
				called-station-id etc
				
				Values:
				username-password
				all
				
				XPath: /extremeWing-config/aaa_policy[name=key1]/mac_address_format/attributes"
			DEFVAL { "username-password" }
			::= { extremeWingCfgAaaEntry 6 }

		
		-- 1.3.6.1.4.1.1916.2.131.50.1.3.7.1.1.7
		extremeWingCfgAaaEapClientTimeout OBJECT-TYPE
			SYNTAX Unsigned32 (1..60)
			UNITS "seconds"
			MAX-ACCESS read-write
			STATUS current
			DESCRIPTION
				"The amount of time after which an EAP request towards a
				Wireless Client is retried.
				
				XPath: /extremeWing-config/aaa_policy[name=key1]/eap_mu_timeout"
			DEFVAL { 3 }
			::= { extremeWingCfgAaaEntry 7 }

		
		-- 1.3.6.1.4.1.1916.2.131.50.1.3.7.1.1.8
		extremeWingCfgAaaEapClientAttempts OBJECT-TYPE
			SYNTAX Unsigned32 (1..10)
			MAX-ACCESS read-write
			STATUS current
			DESCRIPTION
				"The number of times an EAP request is transmitted towards
				a Wireless Client before giving up.
				
				XPath: /extremeWing-config/aaa_policy[name=key1]/eap_mu_attempts"
			DEFVAL { 3 }
			::= { extremeWingCfgAaaEntry 8 }

		
		-- 1.3.6.1.4.1.1916.2.131.50.1.3.7.1.1.9
		extremeWingCfgAaaEapClientRetryFactor OBJECT-TYPE
			SYNTAX Unsigned32 (50..200)
			MAX-ACCESS read-write
			STATUS current
			DESCRIPTION
				"Configures the scaling of the retransmission attempts.
				Timeout at each attempt is a function of this retry_timeout
				factor and the attempt number. 100 implies a constant timeout
				on each retry, smaller values indicate more aggressive
				(shorter) timeouts, larger numbers indicate more conservative
				(larger) timeouts on each successive attempt.
				
				XPath: /extremeWing-config/aaa_policy[name=key1]/eap_mu_retry_factor"
			DEFVAL { 100 }
			::= { extremeWingCfgAaaEntry 9 }

		
		-- 1.3.6.1.4.1.1916.2.131.50.1.3.7.1.1.10
		extremeWingCfgAaaEapClientIdReqTimeout OBJECT-TYPE
			SYNTAX Unsigned32 (1..60)
			UNITS "seconds"
			MAX-ACCESS read-write
			STATUS current
			DESCRIPTION
				"The amount of time after which an EAP-ID-Request towards a
				Wireless Client is retried.
				
				XPath: /extremeWing-config/aaa_policy[name=key1]/eap_mu_id_req_timeout"
			DEFVAL { 10 }
			::= { extremeWingCfgAaaEntry 10 }

		
		-- 1.3.6.1.4.1.1916.2.131.50.1.3.7.1.1.11
		extremeWingCfgAaaAuthProtocol OBJECT-TYPE
			SYNTAX DisplayString
			MAX-ACCESS read-write
			STATUS current
			DESCRIPTION
				"The authentication protocol (Password Authentication Protocol
				or Challenge Handshake Authentication Protocol) to use when
				the server is used for any non-EAP authentication.
				
				Values:
				pap
				chap
				
				XPath: /extremeWing-config/aaa_policy[name=key1]/authentication_protocol"
			DEFVAL { "pap" }
			::= { extremeWingCfgAaaEntry 11 }

		
		-- 1.3.6.1.4.1.1916.2.131.50.1.3.7.1.1.12
		extremeWingCfgAaaAccountingType OBJECT-TYPE
			SYNTAX DisplayString
			MAX-ACCESS read-write
			STATUS current
			DESCRIPTION
				"Control the type of RADIUS Accounting request packets that
				are to be generated.
				
				Values:
				stop-only
				start-stop
				start-interim-stop
				
				XPath: /extremeWing-config/aaa_policy[name=key1]/accounting_type"
			DEFVAL { "start-stop" }
			::= { extremeWingCfgAaaEntry 12 }

		
		-- 1.3.6.1.4.1.1916.2.131.50.1.3.7.1.1.13
		extremeWingCfgAaaInterimAccountingInterval OBJECT-TYPE
			SYNTAX Unsigned32 (60..3600)
			UNITS "seconds"
			MAX-ACCESS read-write
			STATUS current
			DESCRIPTION
				"The periodicity of the interim accounting requests.
				
				XPath: /extremeWing-config/aaa_policy[name=key1]/interim_accounting_interval"
			DEFVAL { 1800 }
			::= { extremeWingCfgAaaEntry 13 }

		
		-- 1.3.6.1.4.1.1916.2.131.50.1.3.7.1.1.14
		extremeWingCfgAaaNacList OBJECT-TYPE
			SYNTAX ExtremeWingIdentifier
			MAX-ACCESS read-write
			STATUS current
			DESCRIPTION
				"Filter to include or exclude certain Wireless Clients from
				network access control.
				
				XPath: /extremeWing-config/aaa_policy[name=key1]/nac_list"
			::= { extremeWingCfgAaaEntry 14 }

		
		-- 1.3.6.1.4.1.1916.2.131.50.1.3.7.2
		extremeWingCfgAaaAuthSrvrTable OBJECT-TYPE
			SYNTAX SEQUENCE OF ExtremeWingCfgAaaAuthSrvrEntry
			MAX-ACCESS not-accessible
			STATUS current
			DESCRIPTION
				"
				
				/extremeWing-config/aaa_policy/auth_srvr"
			::= { extremeWingCfgAaa 2 }

		
		-- 1.3.6.1.4.1.1916.2.131.50.1.3.7.2.1
		extremeWingCfgAaaAuthSrvrEntry OBJECT-TYPE
			SYNTAX ExtremeWingCfgAaaAuthSrvrEntry
			MAX-ACCESS not-accessible
			STATUS current
			DESCRIPTION
				"An entry in the table."
			INDEX { extremeWingCfgAaaName, extremeWingCfgAaaAuthSrvrIdx }
			::= { extremeWingCfgAaaAuthSrvrTable 1 }

		
		ExtremeWingCfgAaaAuthSrvrEntry ::=
			SEQUENCE { 
				extremeWingCfgAaaAuthSrvrIdx
					Unsigned32,
				extremeWingCfgAaaAuthSrvrType
					DisplayString,
				extremeWingCfgAaaAuthSrvrHost
					DisplayString,
				extremeWingCfgAaaAuthSrvrSecret
					DisplayString,
				extremeWingCfgAaaAuthSrvrPort
					Unsigned32,
				extremeWingCfgAaaAuthSrvrTimeout
					Unsigned32,
				extremeWingCfgAaaAuthSrvrAttempts
					Unsigned32,
				extremeWingCfgAaaAuthSrvrProxyMode
					DisplayString,
				extremeWingCfgAaaAuthSrvrNaiRouting
					TruthValue,
				extremeWingCfgAaaAuthSrvrRealmType
					DisplayString,
				extremeWingCfgAaaAuthSrvrRealm
					DisplayString,
				extremeWingCfgAaaAuthSrvrStripRealm
					TruthValue,
				extremeWingCfgAaaAuthSrvrRetryTimeoutFactor
					Unsigned32,
				extremeWingCfgAaaAuthSrvrNacEnable
					TruthValue,
				extremeWingCfgAaaAuthSrvrDscp
					Unsigned32
			 }

		-- 1.3.6.1.4.1.1916.2.131.50.1.3.7.2.1.1
		extremeWingCfgAaaAuthSrvrIdx OBJECT-TYPE
			SYNTAX Unsigned32 (1..6)
			MAX-ACCESS read-only
			STATUS current
			DESCRIPTION
				"The index into the list of servers.
				
				XPath: /extremeWing-config/aaa_policy[name=key1]/auth_srvr[server_idx=key2]/server_idx"
			::= { extremeWingCfgAaaAuthSrvrEntry 1 }

		
		-- 1.3.6.1.4.1.1916.2.131.50.1.3.7.2.1.3
		extremeWingCfgAaaAuthSrvrType OBJECT-TYPE
			SYNTAX DisplayString
			MAX-ACCESS read-write
			STATUS current
			DESCRIPTION
				"The type of RADIUS server to use
				
				Values:
				host
				onboard-self
				onboard-controller
				
				Note: If the type is onboard-self or onboard-controller only
				then host, secret, port, and proxy-mode need be specified.
				Otherwise these parameters are not applicable.
				
				XPath: /extremeWing-config/aaa_policy[name=key1]/auth_srvr[server_idx=key2]/server_type"
			DEFVAL { "host" }
			::= { extremeWingCfgAaaAuthSrvrEntry 3 }

		
		-- 1.3.6.1.4.1.1916.2.131.50.1.3.7.2.1.4
		extremeWingCfgAaaAuthSrvrHost OBJECT-TYPE
			SYNTAX DisplayString
			MAX-ACCESS read-write
			STATUS current
			DESCRIPTION
				"The hostname or IP address of the RADIUS server.
				
				XPath: /extremeWing-config/aaa_policy[name=key1]/auth_srvr[server_idx=key2]/host"
			::= { extremeWingCfgAaaAuthSrvrEntry 4 }

		
		-- 1.3.6.1.4.1.1916.2.131.50.1.3.7.2.1.5
		extremeWingCfgAaaAuthSrvrSecret OBJECT-TYPE
			SYNTAX DisplayString (SIZE (0..127))
			MAX-ACCESS read-write
			STATUS current
			DESCRIPTION
				"The shared secret between the RADIUS server and the Controller/AP.
				
				XPath: /extremeWing-config/aaa_policy[name=key1]/auth_srvr[server_idx=key2]/secret"
			DEFVAL { "" }
			::= { extremeWingCfgAaaAuthSrvrEntry 5 }

		
		-- 1.3.6.1.4.1.1916.2.131.50.1.3.7.2.1.6
		extremeWingCfgAaaAuthSrvrPort OBJECT-TYPE
			SYNTAX Unsigned32 (1..65535)
			MAX-ACCESS read-write
			STATUS current
			DESCRIPTION
				"The UDP port number where the RADIUS server is listening.
				
				XPath: /extremeWing-config/aaa_policy[name=key1]/auth_srvr[server_idx=key2]/port"
			DEFVAL { 1812 }
			::= { extremeWingCfgAaaAuthSrvrEntry 6 }

		
		-- 1.3.6.1.4.1.1916.2.131.50.1.3.7.2.1.7
		extremeWingCfgAaaAuthSrvrTimeout OBJECT-TYPE
			SYNTAX Unsigned32 (1..60)
			UNITS "seconds"
			MAX-ACCESS read-write
			STATUS current
			DESCRIPTION
				"The timeout in seconds after which the request to
				the RADIUS server will be retried.
				
				XPath: /extremeWing-config/aaa_policy[name=key1]/auth_srvr[server_idx=key2]/timeout"
			DEFVAL { 3 }
			::= { extremeWingCfgAaaAuthSrvrEntry 7 }

		
		-- 1.3.6.1.4.1.1916.2.131.50.1.3.7.2.1.8
		extremeWingCfgAaaAuthSrvrAttempts OBJECT-TYPE
			SYNTAX Unsigned32 (1..10)
			MAX-ACCESS read-write
			STATUS current
			DESCRIPTION
				"The number of times a request is sent towards a RADIUS server
				before giving up.
				
				XPath: /extremeWing-config/aaa_policy[name=key1]/auth_srvr[server_idx=key2]/attempts"
			DEFVAL { 3 }
			::= { extremeWingCfgAaaAuthSrvrEntry 8 }

		
		-- 1.3.6.1.4.1.1916.2.131.50.1.3.7.2.1.9
		extremeWingCfgAaaAuthSrvrProxyMode OBJECT-TYPE
			SYNTAX DisplayString
			MAX-ACCESS read-write
			STATUS current
			DESCRIPTION
				"Specfies whether the request is transmitted directly to
				the server or proxied through either the Controller or
				the RF Domain Manager.
				
				Values:
				none
				through-controller
				through-rf-domain-manager
				
				XPath: /extremeWing-config/aaa_policy[name=key1]/auth_srvr[server_idx=key2]/proxy_mode"
			DEFVAL { "none" }
			::= { extremeWingCfgAaaAuthSrvrEntry 9 }

		
		-- 1.3.6.1.4.1.1916.2.131.50.1.3.7.2.1.10
		extremeWingCfgAaaAuthSrvrNaiRouting OBJECT-TYPE
			SYNTAX TruthValue
			MAX-ACCESS read-write
			STATUS current
			DESCRIPTION
				"Whether this RADIUS server is to be selected based on part of
				the username (Network-Access-Identifier).
				
				XPath: /extremeWing-config/aaa_policy[name=key1]/auth_srvr[server_idx=key2]/nai_routing"
			DEFVAL { false }
			::= { extremeWingCfgAaaAuthSrvrEntry 10 }

		
		-- 1.3.6.1.4.1.1916.2.131.50.1.3.7.2.1.11
		extremeWingCfgAaaAuthSrvrRealmType OBJECT-TYPE
			SYNTAX DisplayString
			MAX-ACCESS read-write
			STATUS current
			DESCRIPTION
				"Whether the prefix or the suffix of the username should be
				matched to the realm.
				
				Values:
				prefix
				suffix
				
				XPath: /extremeWing-config/aaa_policy[name=key1]/auth_srvr[server_idx=key2]/realm_type"
			DEFVAL { "prefix" }
			::= { extremeWingCfgAaaAuthSrvrEntry 11 }

		
		-- 1.3.6.1.4.1.1916.2.131.50.1.3.7.2.1.12
		extremeWingCfgAaaAuthSrvrRealm OBJECT-TYPE
			SYNTAX DisplayString (SIZE (0..64))
			MAX-ACCESS read-write
			STATUS current
			DESCRIPTION
				"If the part of the username matches this string, this server
				is selected for authentication.
				
				XPath: /extremeWing-config/aaa_policy[name=key1]/auth_srvr[server_idx=key2]/realm"
			DEFVAL { "" }
			::= { extremeWingCfgAaaAuthSrvrEntry 12 }

		
		-- 1.3.6.1.4.1.1916.2.131.50.1.3.7.2.1.13
		extremeWingCfgAaaAuthSrvrStripRealm OBJECT-TYPE
			SYNTAX TruthValue
			MAX-ACCESS read-write
			STATUS current
			DESCRIPTION
				"Configures whether the realm is stripped from the username
				before the request is forwarded to a server.
				
				XPath: /extremeWing-config/aaa_policy[name=key1]/auth_srvr[server_idx=key2]/strip_realm"
			DEFVAL { false }
			::= { extremeWingCfgAaaAuthSrvrEntry 13 }

		
		-- 1.3.6.1.4.1.1916.2.131.50.1.3.7.2.1.14
		extremeWingCfgAaaAuthSrvrRetryTimeoutFactor OBJECT-TYPE
			SYNTAX Unsigned32 (50..200)
			MAX-ACCESS read-write
			STATUS current
			DESCRIPTION
				"Configures the scaling of the retransmission attempts.
				Timeout at each attempt is a function of this retry_timeout
				factor and the attempt number. 100 implies a constant timeout
				on each retry, smaller values indicate more aggressive
				(shorter) timeouts, larger numbers indicate more conservative
				(larger) timeouts on each successive attempt.
				
				XPath: /extremeWing-config/aaa_policy[name=key1]/auth_srvr[server_idx=key2]/retry_timeout_factor"
			DEFVAL { 100 }
			::= { extremeWingCfgAaaAuthSrvrEntry 14 }

		
		-- 1.3.6.1.4.1.1916.2.131.50.1.3.7.2.1.15
		extremeWingCfgAaaAuthSrvrNacEnable OBJECT-TYPE
			SYNTAX TruthValue
			MAX-ACCESS read-write
			STATUS current
			DESCRIPTION
				"Enable Network Access Control (NAC) on this RADIUS server.
				
				XPath: /extremeWing-config/aaa_policy[name=key1]/auth_srvr[server_idx=key2]/nac_enable"
			DEFVAL { false }
			::= { extremeWingCfgAaaAuthSrvrEntry 15 }

		
		-- 1.3.6.1.4.1.1916.2.131.50.1.3.7.2.1.16
		extremeWingCfgAaaAuthSrvrDscp OBJECT-TYPE
			SYNTAX Unsigned32 (0..63)
			MAX-ACCESS read-write
			STATUS current
			DESCRIPTION
				"Configures the packet priority in request packets sent to
				the RADIUS server
				
				XPath: /extremeWing-config/aaa_policy[name=key1]/auth_srvr[server_idx=key2]/dscp"
			DEFVAL { 46 }
			::= { extremeWingCfgAaaAuthSrvrEntry 16 }

		
		-- 1.3.6.1.4.1.1916.2.131.50.1.3.7.3
		extremeWingCfgAaaAcctSrvrTable OBJECT-TYPE
			SYNTAX SEQUENCE OF ExtremeWingCfgAaaAcctSrvrEntry
			MAX-ACCESS not-accessible
			STATUS current
			DESCRIPTION
				"
				
				/extremeWing-config/aaa_policy/acct_srvr"
			::= { extremeWingCfgAaa 3 }

		
		-- 1.3.6.1.4.1.1916.2.131.50.1.3.7.3.1
		extremeWingCfgAaaAcctSrvrEntry OBJECT-TYPE
			SYNTAX ExtremeWingCfgAaaAcctSrvrEntry
			MAX-ACCESS not-accessible
			STATUS current
			DESCRIPTION
				"An entry in the table."
			INDEX { extremeWingCfgAaaName, extremeWingCfgAaaAcctSrvrIdx }
			::= { extremeWingCfgAaaAcctSrvrTable 1 }

		
		ExtremeWingCfgAaaAcctSrvrEntry ::=
			SEQUENCE { 
				extremeWingCfgAaaAcctSrvrIdx
					Unsigned32,
				extremeWingCfgAaaAcctSrvrType
					DisplayString,
				extremeWingCfgAaaAcctSrvrHost
					DisplayString,
				extremeWingCfgAaaAcctSrvrSecret
					DisplayString,
				extremeWingCfgAaaAcctSrvrPort
					Unsigned32,
				extremeWingCfgAaaAcctSrvrTimeout
					Unsigned32,
				extremeWingCfgAaaAcctSrvrAttempts
					Unsigned32,
				extremeWingCfgAaaAcctSrvrProxyMode
					DisplayString,
				extremeWingCfgAaaAcctSrvrNaiRouting
					TruthValue,
				extremeWingCfgAaaAcctSrvrRealmType
					DisplayString,
				extremeWingCfgAaaAcctSrvrRealm
					DisplayString,
				extremeWingCfgAaaAcctSrvrStripRealm
					TruthValue,
				extremeWingCfgAaaAcctSrvrRetryTimeoutFactor
					Unsigned32,
				extremeWingCfgAaaAcctSrvrDscp
					Unsigned32
			 }

		-- 1.3.6.1.4.1.1916.2.131.50.1.3.7.3.1.1
		extremeWingCfgAaaAcctSrvrIdx OBJECT-TYPE
			SYNTAX Unsigned32 (1..6)
			MAX-ACCESS read-only
			STATUS current
			DESCRIPTION
				"The index into the list of servers.
				
				XPath: /extremeWing-config/aaa_policy[name=key1]/acct_srvr[server_idx=key2]/server_idx"
			::= { extremeWingCfgAaaAcctSrvrEntry 1 }

		
		-- 1.3.6.1.4.1.1916.2.131.50.1.3.7.3.1.3
		extremeWingCfgAaaAcctSrvrType OBJECT-TYPE
			SYNTAX DisplayString
			MAX-ACCESS read-write
			STATUS current
			DESCRIPTION
				"The type of RADIUS server to use
				
				Values:
				host
				onboard-self
				onboard-controller
				
				Note:
				If the type is onboard-self or onboard-controller only then
				host, secret, port, and proxy-mode need be specified.
				Otherwise these parameters are not applicable.
				
				XPath: /extremeWing-config/aaa_policy[name=key1]/acct_srvr[server_idx=key2]/server_type"
			DEFVAL { "host" }
			::= { extremeWingCfgAaaAcctSrvrEntry 3 }

		
		-- 1.3.6.1.4.1.1916.2.131.50.1.3.7.3.1.4
		extremeWingCfgAaaAcctSrvrHost OBJECT-TYPE
			SYNTAX DisplayString
			MAX-ACCESS read-write
			STATUS current
			DESCRIPTION
				"The hostname or IP address of the RADIUS server.
				
				XPath: /extremeWing-config/aaa_policy[name=key1]/acct_srvr[server_idx=key2]/host"
			::= { extremeWingCfgAaaAcctSrvrEntry 4 }

		
		-- 1.3.6.1.4.1.1916.2.131.50.1.3.7.3.1.5
		extremeWingCfgAaaAcctSrvrSecret OBJECT-TYPE
			SYNTAX DisplayString (SIZE (0..127))
			MAX-ACCESS read-write
			STATUS current
			DESCRIPTION
				"The shared secret between the RADIUS server and
				the Controller/AP.
				
				XPath: /extremeWing-config/aaa_policy[name=key1]/acct_srvr[server_idx=key2]/secret"
			DEFVAL { "" }
			::= { extremeWingCfgAaaAcctSrvrEntry 5 }

		
		-- 1.3.6.1.4.1.1916.2.131.50.1.3.7.3.1.6
		extremeWingCfgAaaAcctSrvrPort OBJECT-TYPE
			SYNTAX Unsigned32 (1..65535)
			MAX-ACCESS read-write
			STATUS current
			DESCRIPTION
				"The UDP port number where the RADIUS server is listening.
				
				XPath: /extremeWing-config/aaa_policy[name=key1]/acct_srvr[server_idx=key2]/port"
			DEFVAL { 1813 }
			::= { extremeWingCfgAaaAcctSrvrEntry 6 }

		
		-- 1.3.6.1.4.1.1916.2.131.50.1.3.7.3.1.7
		extremeWingCfgAaaAcctSrvrTimeout OBJECT-TYPE
			SYNTAX Unsigned32 (1..60)
			UNITS "seconds"
			MAX-ACCESS read-write
			STATUS current
			DESCRIPTION
				"The timeout in seconds after which the request to
				the RADIUS server will be retried.
				
				XPath: /extremeWing-config/aaa_policy[name=key1]/acct_srvr[server_idx=key2]/timeout"
			DEFVAL { 5 }
			::= { extremeWingCfgAaaAcctSrvrEntry 7 }

		
		-- 1.3.6.1.4.1.1916.2.131.50.1.3.7.3.1.8
		extremeWingCfgAaaAcctSrvrAttempts OBJECT-TYPE
			SYNTAX Unsigned32 (1..10)
			MAX-ACCESS read-write
			STATUS current
			DESCRIPTION
				"The number of times a request is sent towards a RADIUS server
				before giving up.
				
				XPath: /extremeWing-config/aaa_policy[name=key1]/acct_srvr[server_idx=key2]/attempts"
			DEFVAL { 3 }
			::= { extremeWingCfgAaaAcctSrvrEntry 8 }

		
		-- 1.3.6.1.4.1.1916.2.131.50.1.3.7.3.1.9
		extremeWingCfgAaaAcctSrvrProxyMode OBJECT-TYPE
			SYNTAX DisplayString
			MAX-ACCESS read-write
			STATUS current
			DESCRIPTION
				"Specfies whether the request is transmitted directly to
				the server or proxied through either the Controller or
				the RF Domain Manager.
				
				Values:
				none
				through-controller
				through-rf-domain-manager
				
				XPath: /extremeWing-config/aaa_policy[name=key1]/acct_srvr[server_idx=key2]/proxy_mode"
			DEFVAL { "none" }
			::= { extremeWingCfgAaaAcctSrvrEntry 9 }

		
		-- 1.3.6.1.4.1.1916.2.131.50.1.3.7.3.1.10
		extremeWingCfgAaaAcctSrvrNaiRouting OBJECT-TYPE
			SYNTAX TruthValue
			MAX-ACCESS read-write
			STATUS current
			DESCRIPTION
				"Whether this RADIUS server is to be selected based on part of
				the username (Network-Access-Identifier).
				
				XPath: /extremeWing-config/aaa_policy[name=key1]/acct_srvr[server_idx=key2]/nai_routing"
			DEFVAL { false }
			::= { extremeWingCfgAaaAcctSrvrEntry 10 }

		
		-- 1.3.6.1.4.1.1916.2.131.50.1.3.7.3.1.11
		extremeWingCfgAaaAcctSrvrRealmType OBJECT-TYPE
			SYNTAX DisplayString
			MAX-ACCESS read-write
			STATUS current
			DESCRIPTION
				"Whether the prefix or the suffix of the username should be
				matched to the realm.
				
				Values:
				prefix
				suffix
				
				XPath: /extremeWing-config/aaa_policy[name=key1]/acct_srvr[server_idx=key2]/realm_type"
			DEFVAL { "prefix" }
			::= { extremeWingCfgAaaAcctSrvrEntry 11 }

		
		-- 1.3.6.1.4.1.1916.2.131.50.1.3.7.3.1.12
		extremeWingCfgAaaAcctSrvrRealm OBJECT-TYPE
			SYNTAX DisplayString (SIZE (0..64))
			MAX-ACCESS read-write
			STATUS current
			DESCRIPTION
				"If a part of the username (prefix or suffix depending on
				realm_type) matches this parameter this server is selected
				for authentication.
				
				XPath: /extremeWing-config/aaa_policy[name=key1]/acct_srvr[server_idx=key2]/realm"
			DEFVAL { "" }
			::= { extremeWingCfgAaaAcctSrvrEntry 12 }

		
		-- 1.3.6.1.4.1.1916.2.131.50.1.3.7.3.1.13
		extremeWingCfgAaaAcctSrvrStripRealm OBJECT-TYPE
			SYNTAX TruthValue
			MAX-ACCESS read-write
			STATUS current
			DESCRIPTION
				"Configures whether the realm is stripped from the username
				before the request is forwarded to a server.
				
				XPath: /extremeWing-config/aaa_policy[name=key1]/acct_srvr[server_idx=key2]/strip_realm"
			DEFVAL { false }
			::= { extremeWingCfgAaaAcctSrvrEntry 13 }

		
		-- 1.3.6.1.4.1.1916.2.131.50.1.3.7.3.1.14
		extremeWingCfgAaaAcctSrvrRetryTimeoutFactor OBJECT-TYPE
			SYNTAX Unsigned32 (50..200)
			MAX-ACCESS read-write
			STATUS current
			DESCRIPTION
				"Configures the scaling of the retransmission attempts.
				Timeout at each attempt is a function of this retry_timeout
				factor and the attempt number. 100 implies a constant timeout
				on each retry, smaller values indicate more aggressive
				(shorter) timeouts, larger numbers indicate more conservative
				(larger) timeouts on each successive attempt.
				
				XPath: /extremeWing-config/aaa_policy[name=key1]/acct_srvr[server_idx=key2]/retry_timeout_factor"
			DEFVAL { 100 }
			::= { extremeWingCfgAaaAcctSrvrEntry 14 }

		
		-- 1.3.6.1.4.1.1916.2.131.50.1.3.7.3.1.15
		extremeWingCfgAaaAcctSrvrDscp OBJECT-TYPE
			SYNTAX Unsigned32 (0..63)
			MAX-ACCESS read-write
			STATUS current
			DESCRIPTION
				"Configures the packet priority in request packets sent to
				the RADIUS server
				
				XPath: /extremeWing-config/aaa_policy[name=key1]/acct_srvr[server_idx=key2]/dscp"
			DEFVAL { 34 }
			::= { extremeWingCfgAaaAcctSrvrEntry 15 }

		
-- /extremeWing-config/assoc_acl
		-- 1.3.6.1.4.1.1916.2.131.50.1.3.8
		extremeWingCfgAssocAcl OBJECT IDENTIFIER ::= { extremeWingConfig 8 }

		
		-- 1.3.6.1.4.1.1916.2.131.50.1.3.8.1
		extremeWingCfgAssocAclTable OBJECT-TYPE
			SYNTAX SEQUENCE OF ExtremeWingCfgAssocAclEntry
			MAX-ACCESS not-accessible
			STATUS current
			DESCRIPTION
				"Association ACL
				
				/extremeWing-config/assoc_acl"
			::= { extremeWingCfgAssocAcl 1 }

		
		-- 1.3.6.1.4.1.1916.2.131.50.1.3.8.1.1
		extremeWingCfgAssocAclEntry OBJECT-TYPE
			SYNTAX ExtremeWingCfgAssocAclEntry
			MAX-ACCESS not-accessible
			STATUS current
			DESCRIPTION
				"An entry in the table."
			INDEX { extremeWingCfgAssocAclName }
			::= { extremeWingCfgAssocAclTable 1 }

		
		ExtremeWingCfgAssocAclEntry ::=
			SEQUENCE { 
				extremeWingCfgAssocAclName
					ExtremeWingIdentifier
			 }

		-- 1.3.6.1.4.1.1916.2.131.50.1.3.8.1.1.1
		extremeWingCfgAssocAclName OBJECT-TYPE
			SYNTAX ExtremeWingIdentifier
			MAX-ACCESS read-only
			STATUS current
			DESCRIPTION
				"The name of the Association ACL policy.
				
				XPath: /extremeWing-config/assoc_acl[name=key1]/name"
			::= { extremeWingCfgAssocAclEntry 1 }

		
		-- 1.3.6.1.4.1.1916.2.131.50.1.3.8.2
		extremeWingCfgAssocAclRuleTable OBJECT-TYPE
			SYNTAX SEQUENCE OF ExtremeWingCfgAssocAclRuleEntry
			MAX-ACCESS not-accessible
			STATUS current
			DESCRIPTION
				"
				
				/extremeWing-config/assoc_acl/rule"
			::= { extremeWingCfgAssocAcl 2 }

		
		-- 1.3.6.1.4.1.1916.2.131.50.1.3.8.2.1
		extremeWingCfgAssocAclRuleEntry OBJECT-TYPE
			SYNTAX ExtremeWingCfgAssocAclRuleEntry
			MAX-ACCESS not-accessible
			STATUS current
			DESCRIPTION
				"An entry in the table."
			INDEX { extremeWingCfgAssocAclName, extremeWingCfgAssocAclRulePrecedence }
			::= { extremeWingCfgAssocAclRuleTable 1 }

		
		ExtremeWingCfgAssocAclRuleEntry ::=
			SEQUENCE { 
				extremeWingCfgAssocAclRulePrecedence
					Unsigned32,
				extremeWingCfgAssocAclRulePermit
					TruthValue,
				extremeWingCfgAssocAclRuleMac0
					MacAddress,
				extremeWingCfgAssocAclRuleMac1
					MacAddress
			 }

		-- 1.3.6.1.4.1.1916.2.131.50.1.3.8.2.1.1
		extremeWingCfgAssocAclRulePrecedence OBJECT-TYPE
			SYNTAX Unsigned32 (1..1000)
			MAX-ACCESS read-only
			STATUS current
			DESCRIPTION
				"The index/precedence of a particular rule. Rules are matched
				in order of increasing precedence.
				
				XPath: /extremeWing-config/assoc_acl[name=key1]/rule[precedence=key2]/precedence"
			::= { extremeWingCfgAssocAclRuleEntry 1 }

		
		-- 1.3.6.1.4.1.1916.2.131.50.1.3.8.2.1.3
		extremeWingCfgAssocAclRulePermit OBJECT-TYPE
			SYNTAX TruthValue
			MAX-ACCESS read-write
			STATUS current
			DESCRIPTION
				"Configure whether to disallow access if a MAC matches
				this rule, or to fall through to the next rule.
				
				XPath: /extremeWing-config/assoc_acl[name=key1]/rule[precedence=key2]/permit"
			DEFVAL { false }
			::= { extremeWingCfgAssocAclRuleEntry 3 }

		
		-- 1.3.6.1.4.1.1916.2.131.50.1.3.8.2.1.4
		extremeWingCfgAssocAclRuleMac0 OBJECT-TYPE
			SYNTAX MacAddress
			MAX-ACCESS read-write
			STATUS current
			DESCRIPTION
				"The starting MAC address in the range of MACs that apply to
				this rule.
				
				XPath: /extremeWing-config/assoc_acl[name=key1]/rule[precedence=key2]/mac0"
			DEFVAL { '000000000000'h }
			::= { extremeWingCfgAssocAclRuleEntry 4 }

		
		-- 1.3.6.1.4.1.1916.2.131.50.1.3.8.2.1.5
		extremeWingCfgAssocAclRuleMac1 OBJECT-TYPE
			SYNTAX MacAddress
			MAX-ACCESS read-write
			STATUS current
			DESCRIPTION
				"The ending MAC address in the range of MACs that apply to
				this rule.
				
				XPath: /extremeWing-config/assoc_acl[name=key1]/rule[precedence=key2]/mac1"
			DEFVAL { 'FFFFFFFFFFFF'h }
			::= { extremeWingCfgAssocAclRuleEntry 5 }

		
-- /extremeWing-config/smart_rf_policy
		-- 1.3.6.1.4.1.1916.2.131.50.1.3.9
		extremeWingCfgSmartRf OBJECT IDENTIFIER ::= { extremeWingConfig 9 }

		
		-- 1.3.6.1.4.1.1916.2.131.50.1.3.9.1
		extremeWingCfgSmartRfTable OBJECT-TYPE
			SYNTAX SEQUENCE OF ExtremeWingCfgSmartRfEntry
			MAX-ACCESS not-accessible
			STATUS current
			DESCRIPTION
				"Configuration parameters of a wireless Smart-RF profile
				
				/extremeWing-config/smart_rf_policy"
			::= { extremeWingCfgSmartRf 1 }

		
		-- 1.3.6.1.4.1.1916.2.131.50.1.3.9.1.1
		extremeWingCfgSmartRfEntry OBJECT-TYPE
			SYNTAX ExtremeWingCfgSmartRfEntry
			MAX-ACCESS not-accessible
			STATUS current
			DESCRIPTION
				"An entry in the table."
			INDEX { extremeWingCfgSmartRfName }
			::= { extremeWingCfgSmartRfTable 1 }

		
		ExtremeWingCfgSmartRfEntry ::=
			SEQUENCE { 
				extremeWingCfgSmartRfName
					ExtremeWingIdentifier,
				extremeWingCfgSmartRfEnable
					TruthValue,
				extremeWingCfgSmartRfSensitivity
					DisplayString,
				extremeWingCfgSmartRfAutoAssignSensor
					TruthValue,
				extremeWingCfgSmartRfMinPowerA
					Unsigned32,
				extremeWingCfgSmartRfMaxPowerA
					Unsigned32,
				extremeWingCfgSmartRfMinPowerBg
					Unsigned32,
				extremeWingCfgSmartRfMaxPowerBg
					Unsigned32,
				extremeWingCfgSmartRfChannelWidthA
					DisplayString,
				extremeWingCfgSmartRfChannelWidthBg
					DisplayString,
				extremeWingCfgSmartRfGroupByArea
					TruthValue,
				extremeWingCfgSmartRfGroupByFloor
					TruthValue,
				extremeWingCfgSmartRfSmartOcsMonitoring
					TruthValue,
				extremeWingCfgSmartRfOcsDurationA
					Unsigned32,
				extremeWingCfgSmartRfOcsDurationBg
					Unsigned32,
				extremeWingCfgSmartRfOcsFrequencyA
					Unsigned32,
				extremeWingCfgSmartRfOcsFrequencyBg
					Unsigned32,
				extremeWingCfgSmartRfOcsSampleCountA
					Unsigned32,
				extremeWingCfgSmartRfOcsSampleCountBg
					Unsigned32,
				extremeWingCfgSmartRfOcsExtendedScanFrequencyA
					Unsigned32,
				extremeWingCfgSmartRfOcsExtendedScanFrequencyBg
					Unsigned32,
				extremeWingCfgSmartRfOcsVoiceAwareA
					DisplayString,
				extremeWingCfgSmartRfOcsVoiceAwareBg
					DisplayString,
				extremeWingCfgSmartRfOcsPspAwareA
					DisplayString,
				extremeWingCfgSmartRfOcsPspAwareBg
					DisplayString,
				extremeWingCfgSmartRfInterferenceRecovery
					TruthValue,
				extremeWingCfgSmartRfIrNoise
					TruthValue,
				extremeWingCfgSmartRfIrInterference
					TruthValue,
				extremeWingCfgSmartRfIrClientThreshold
					Unsigned32,
				extremeWingCfgSmartRfIrChannelSwitchDeltaA
					Unsigned32,
				extremeWingCfgSmartRfIrChannelSwitchDeltaBg
					Unsigned32,
				extremeWingCfgSmartRfNeighborRecovery
					TruthValue,
				extremeWingCfgSmartRfNrPowerThresholdA
					Integer32,
				extremeWingCfgSmartRfNrPowerThresholdBg
					Integer32,
				extremeWingCfgSmartRfCoverageHoleRecovery
					TruthValue,
				extremeWingCfgSmartRfChrIntervalA
					Unsigned32,
				extremeWingCfgSmartRfChrIntervalBg
					Unsigned32,
				extremeWingCfgSmartRfChrCovIntervalA
					Unsigned32,
				extremeWingCfgSmartRfChrCovIntervalBg
					Unsigned32,
				extremeWingCfgSmartRfChrSnrThresholdA
					Unsigned32,
				extremeWingCfgSmartRfChrSnrThresholdBg
					Unsigned32,
				extremeWingCfgSmartRfChrClientThresholdA
					Unsigned32,
				extremeWingCfgSmartRfChrClientThresholdBg
					Unsigned32,
				extremeWingCfgSmartRfChannelHoldTime
					Unsigned32,
				extremeWingCfgSmartRfPowerHoldTime
					Unsigned32,
				extremeWingCfgSmartRfOcsMeshpointA
					DisplayString,
				extremeWingCfgSmartRfOcsMeshpointBg
					DisplayString
			 }

		-- 1.3.6.1.4.1.1916.2.131.50.1.3.9.1.1.1
		extremeWingCfgSmartRfName OBJECT-TYPE
			SYNTAX ExtremeWingIdentifier
			MAX-ACCESS read-only
			STATUS current
			DESCRIPTION
				"
				
				XPath: /extremeWing-config/smart_rf_policy[name=key1]/name"
			::= { extremeWingCfgSmartRfEntry 1 }

		
		-- 1.3.6.1.4.1.1916.2.131.50.1.3.9.1.1.3
		extremeWingCfgSmartRfEnable OBJECT-TYPE
			SYNTAX TruthValue
			MAX-ACCESS read-write
			STATUS current
			DESCRIPTION
				"
				
				XPath: /extremeWing-config/smart_rf_policy[name=key1]/enable"
			DEFVAL { false }
			::= { extremeWingCfgSmartRfEntry 3 }

		
		-- 1.3.6.1.4.1.1916.2.131.50.1.3.9.1.1.4
		extremeWingCfgSmartRfSensitivity OBJECT-TYPE
			SYNTAX DisplayString
			MAX-ACCESS read-write
			STATUS current
			DESCRIPTION
				"choose smart-rf sensitivity settings, modifies configuration
				parameters to preset values.
				
				Values:
				low
				medium
				high
				custom
				
				XPath: /extremeWing-config/smart_rf_policy[name=key1]/sensitivity"
			DEFVAL { "medium" }
			::= { extremeWingCfgSmartRfEntry 4 }

		
		-- 1.3.6.1.4.1.1916.2.131.50.1.3.9.1.1.5
		extremeWingCfgSmartRfAutoAssignSensor OBJECT-TYPE
			SYNTAX TruthValue
			MAX-ACCESS read-write
			STATUS current
			DESCRIPTION
				"smart-rf automatically assigns optimal sensors for wips and
				rogue ap detection.
				
				XPath: /extremeWing-config/smart_rf_policy[name=key1]/auto_assign_sensor"
			DEFVAL { false }
			::= { extremeWingCfgSmartRfEntry 5 }

		
		-- 1.3.6.1.4.1.1916.2.131.50.1.3.9.1.1.6
		extremeWingCfgSmartRfMinPowerA OBJECT-TYPE
			SYNTAX Unsigned32 (1..20)
			UNITS "dBm"
			MAX-ACCESS read-write
			STATUS current
			DESCRIPTION
				"Minimum assignable power on 5GHz radios
				
				XPath: /extremeWing-config/smart_rf_policy[name=key1]/min_power_a"
			DEFVAL { 4 }
			::= { extremeWingCfgSmartRfEntry 6 }

		
		-- 1.3.6.1.4.1.1916.2.131.50.1.3.9.1.1.7
		extremeWingCfgSmartRfMaxPowerA OBJECT-TYPE
			SYNTAX Unsigned32 (1..20)
			UNITS "dBm"
			MAX-ACCESS read-write
			STATUS current
			DESCRIPTION
				"Maximum assignable power on 5GHz radios
				
				XPath: /extremeWing-config/smart_rf_policy[name=key1]/max_power_a"
			DEFVAL { 17 }
			::= { extremeWingCfgSmartRfEntry 7 }

		
		-- 1.3.6.1.4.1.1916.2.131.50.1.3.9.1.1.8
		extremeWingCfgSmartRfMinPowerBg OBJECT-TYPE
			SYNTAX Unsigned32 (1..20)
			UNITS "dBm"
			MAX-ACCESS read-write
			STATUS current
			DESCRIPTION
				"Minimum assignable power on 2.4GHz radios
				
				XPath: /extremeWing-config/smart_rf_policy[name=key1]/min_power_bg"
			DEFVAL { 4 }
			::= { extremeWingCfgSmartRfEntry 8 }

		
		-- 1.3.6.1.4.1.1916.2.131.50.1.3.9.1.1.9
		extremeWingCfgSmartRfMaxPowerBg OBJECT-TYPE
			SYNTAX Unsigned32 (1..20)
			UNITS "dBm"
			MAX-ACCESS read-write
			STATUS current
			DESCRIPTION
				"Maximum assignable power on 2.4GHz radios
				
				XPath: /extremeWing-config/smart_rf_policy[name=key1]/max_power_bg"
			DEFVAL { 17 }
			::= { extremeWingCfgSmartRfEntry 9 }

		
		-- 1.3.6.1.4.1.1916.2.131.50.1.3.9.1.1.10
		extremeWingCfgSmartRfChannelWidthA OBJECT-TYPE
			SYNTAX DisplayString
			MAX-ACCESS read-write
			STATUS current
			DESCRIPTION
				"Channel width that Smart-RF should assign to 5GHz radios
				
				Values:
				20MHz
				40MHz
				auto
				
				XPath: /extremeWing-config/smart_rf_policy[name=key1]/channel_width_a"
			DEFVAL { "40MHz" }
			::= { extremeWingCfgSmartRfEntry 10 }

		
		-- 1.3.6.1.4.1.1916.2.131.50.1.3.9.1.1.11
		extremeWingCfgSmartRfChannelWidthBg OBJECT-TYPE
			SYNTAX DisplayString
			MAX-ACCESS read-write
			STATUS current
			DESCRIPTION
				"Channel width that Smart-RF should assign to 2.4GHz radios
				
				Values:
				20MHz
				40MHz
				auto
				
				XPath: /extremeWing-config/smart_rf_policy[name=key1]/channel_width_bg"
			DEFVAL { "20MHz" }
			::= { extremeWingCfgSmartRfEntry 11 }

		
		-- 1.3.6.1.4.1.1916.2.131.50.1.3.9.1.1.12
		extremeWingCfgSmartRfGroupByArea OBJECT-TYPE
			SYNTAX TruthValue
			MAX-ACCESS read-write
			STATUS current
			DESCRIPTION
				"Perform grouping of radios by area.
				
				XPath: /extremeWing-config/smart_rf_policy[name=key1]/group_by_area"
			DEFVAL { false }
			::= { extremeWingCfgSmartRfEntry 12 }

		
		-- 1.3.6.1.4.1.1916.2.131.50.1.3.9.1.1.13
		extremeWingCfgSmartRfGroupByFloor OBJECT-TYPE
			SYNTAX TruthValue
			MAX-ACCESS read-write
			STATUS current
			DESCRIPTION
				"Perform grouping of radios by floor.
				
				XPath: /extremeWing-config/smart_rf_policy[name=key1]/group_by_floor"
			DEFVAL { false }
			::= { extremeWingCfgSmartRfEntry 13 }

		
		-- 1.3.6.1.4.1.1916.2.131.50.1.3.9.1.1.14
		extremeWingCfgSmartRfSmartOcsMonitoring OBJECT-TYPE
			SYNTAX TruthValue
			MAX-ACCESS read-write
			STATUS current
			DESCRIPTION
				"Perform off channel scanning to perform recoveries.
				
				XPath: /extremeWing-config/smart_rf_policy[name=key1]/smart_ocs_monitoring"
			DEFVAL { true }
			::= { extremeWingCfgSmartRfEntry 14 }

		
		-- 1.3.6.1.4.1.1916.2.131.50.1.3.9.1.1.15
		extremeWingCfgSmartRfOcsDurationA OBJECT-TYPE
			SYNTAX Unsigned32 (20..150)
			UNITS "milliseconds"
			MAX-ACCESS read-write
			STATUS current
			DESCRIPTION
				"Duration in milliseconds to spend off-channel for 5GHz radios.
				
				XPath: /extremeWing-config/smart_rf_policy[name=key1]/ocs_duration_a"
			DEFVAL { 50 }
			::= { extremeWingCfgSmartRfEntry 15 }

		
		-- 1.3.6.1.4.1.1916.2.131.50.1.3.9.1.1.16
		extremeWingCfgSmartRfOcsDurationBg OBJECT-TYPE
			SYNTAX Unsigned32 (20..150)
			UNITS "milliseconds"
			MAX-ACCESS read-write
			STATUS current
			DESCRIPTION
				"Duration in milliseconds to spend off-channel for
				2.4GHz radios.
				
				XPath: /extremeWing-config/smart_rf_policy[name=key1]/ocs_duration_bg"
			DEFVAL { 50 }
			::= { extremeWingCfgSmartRfEntry 16 }

		
		-- 1.3.6.1.4.1.1916.2.131.50.1.3.9.1.1.17
		extremeWingCfgSmartRfOcsFrequencyA OBJECT-TYPE
			SYNTAX Unsigned32 (1..120)
			UNITS "seconds"
			MAX-ACCESS read-write
			STATUS current
			DESCRIPTION
				"Frequency at which off channel scanning has to be performed
				for 5GHz radios.
				
				XPath: /extremeWing-config/smart_rf_policy[name=key1]/ocs_frequency_a"
			DEFVAL { 6 }
			::= { extremeWingCfgSmartRfEntry 17 }

		
		-- 1.3.6.1.4.1.1916.2.131.50.1.3.9.1.1.18
		extremeWingCfgSmartRfOcsFrequencyBg OBJECT-TYPE
			SYNTAX Unsigned32 (1..120)
			UNITS "seconds"
			MAX-ACCESS read-write
			STATUS current
			DESCRIPTION
				"Frequency at which off channel scanning has to be performed
				for 2.4GHz radios.
				
				XPath: /extremeWing-config/smart_rf_policy[name=key1]/ocs_frequency_bg"
			DEFVAL { 6 }
			::= { extremeWingCfgSmartRfEntry 18 }

		
		-- 1.3.6.1.4.1.1916.2.131.50.1.3.9.1.1.19
		extremeWingCfgSmartRfOcsSampleCountA OBJECT-TYPE
			SYNTAX Unsigned32 (1..15)
			MAX-ACCESS read-write
			STATUS current
			DESCRIPTION
				"Number of samples to take during off channel scan for
				5GHz radios.
				
				XPath: /extremeWing-config/smart_rf_policy[name=key1]/ocs_sample_count_a"
			DEFVAL { 5 }
			::= { extremeWingCfgSmartRfEntry 19 }

		
		-- 1.3.6.1.4.1.1916.2.131.50.1.3.9.1.1.20
		extremeWingCfgSmartRfOcsSampleCountBg OBJECT-TYPE
			SYNTAX Unsigned32 (1..15)
			MAX-ACCESS read-write
			STATUS current
			DESCRIPTION
				"Number of samples to take during off channel scan for
				2.4GHz radios.
				
				XPath: /extremeWing-config/smart_rf_policy[name=key1]/ocs_sample_count_bg"
			DEFVAL { 5 }
			::= { extremeWingCfgSmartRfEntry 20 }

		
		-- 1.3.6.1.4.1.1916.2.131.50.1.3.9.1.1.21
		extremeWingCfgSmartRfOcsExtendedScanFrequencyA OBJECT-TYPE
			SYNTAX Unsigned32 (0..50)
			MAX-ACCESS read-write
			STATUS current
			DESCRIPTION
				"Frequency at which an extended scan has to be performed on
				5GHz radios instead of a normal neighbor only scan.
				
				XPath: /extremeWing-config/smart_rf_policy[name=key1]/ocs_extended_scan_frequency_a"
			DEFVAL { 5 }
			::= { extremeWingCfgSmartRfEntry 21 }

		
		-- 1.3.6.1.4.1.1916.2.131.50.1.3.9.1.1.22
		extremeWingCfgSmartRfOcsExtendedScanFrequencyBg OBJECT-TYPE
			SYNTAX Unsigned32 (0..50)
			MAX-ACCESS read-write
			STATUS current
			DESCRIPTION
				"Frequency at which an extended scan has to be performed on
				2.4GHz radios instead of a normal neighbor only scan.
				
				XPath: /extremeWing-config/smart_rf_policy[name=key1]/ocs_extended_scan_frequency_bg"
			DEFVAL { 5 }
			::= { extremeWingCfgSmartRfEntry 22 }

		
		-- 1.3.6.1.4.1.1916.2.131.50.1.3.9.1.1.23
		extremeWingCfgSmartRfOcsVoiceAwareA OBJECT-TYPE
			SYNTAX DisplayString
			MAX-ACCESS read-write
			STATUS current
			DESCRIPTION
				"Voice awareness setting during off channel scan for
				5GHz radios
				
				Values:
				dynamic
				strict
				disable
				
				XPath: /extremeWing-config/smart_rf_policy[name=key1]/ocs_voice_aware_a"
			DEFVAL { "dynamic" }
			::= { extremeWingCfgSmartRfEntry 23 }

		
		-- 1.3.6.1.4.1.1916.2.131.50.1.3.9.1.1.24
		extremeWingCfgSmartRfOcsVoiceAwareBg OBJECT-TYPE
			SYNTAX DisplayString
			MAX-ACCESS read-write
			STATUS current
			DESCRIPTION
				"Voice awareness setting during off channel scan for
				2.4GHz radios
				
				Values:
				dynamic
				strict
				disable
				
				XPath: /extremeWing-config/smart_rf_policy[name=key1]/ocs_voice_aware_bg"
			DEFVAL { "dynamic" }
			::= { extremeWingCfgSmartRfEntry 24 }

		
		-- 1.3.6.1.4.1.1916.2.131.50.1.3.9.1.1.25
		extremeWingCfgSmartRfOcsPspAwareA OBJECT-TYPE
			SYNTAX DisplayString
			MAX-ACCESS read-write
			STATUS current
			DESCRIPTION
				"PSP awareness setting during off channel scan for 5GHz radios
				
				Values:
				dynamic
				strict
				disable
				
				XPath: /extremeWing-config/smart_rf_policy[name=key1]/ocs_psp_aware_a"
			DEFVAL { "dynamic" }
			::= { extremeWingCfgSmartRfEntry 25 }

		
		-- 1.3.6.1.4.1.1916.2.131.50.1.3.9.1.1.26
		extremeWingCfgSmartRfOcsPspAwareBg OBJECT-TYPE
			SYNTAX DisplayString
			MAX-ACCESS read-write
			STATUS current
			DESCRIPTION
				"PSP awareness setting during off channel scan for
				2.4GHz radios
				
				Values:
				dynamic
				strict
				disable
				
				XPath: /extremeWing-config/smart_rf_policy[name=key1]/ocs_psp_aware_bg"
			DEFVAL { "dynamic" }
			::= { extremeWingCfgSmartRfEntry 26 }

		
		-- 1.3.6.1.4.1.1916.2.131.50.1.3.9.1.1.27
		extremeWingCfgSmartRfInterferenceRecovery OBJECT-TYPE
			SYNTAX TruthValue
			MAX-ACCESS read-write
			STATUS current
			DESCRIPTION
				"Recover issues due to excessive noise and interference.
				
				XPath: /extremeWing-config/smart_rf_policy[name=key1]/interference_recovery"
			DEFVAL { true }
			::= { extremeWingCfgSmartRfEntry 27 }

		
		-- 1.3.6.1.4.1.1916.2.131.50.1.3.9.1.1.28
		extremeWingCfgSmartRfIrNoise OBJECT-TYPE
			SYNTAX TruthValue
			MAX-ACCESS read-write
			STATUS current
			DESCRIPTION
				"Take noise into consideration while performing interference
				recovery.
				
				XPath: /extremeWing-config/smart_rf_policy[name=key1]/ir_noise"
			DEFVAL { true }
			::= { extremeWingCfgSmartRfEntry 28 }

		
		-- 1.3.6.1.4.1.1916.2.131.50.1.3.9.1.1.29
		extremeWingCfgSmartRfIrInterference OBJECT-TYPE
			SYNTAX TruthValue
			MAX-ACCESS read-write
			STATUS current
			DESCRIPTION
				"Take external interference into consideration while performing
				interference recovery.
				
				XPath: /extremeWing-config/smart_rf_policy[name=key1]/ir_interference"
			DEFVAL { true }
			::= { extremeWingCfgSmartRfEntry 29 }

		
		-- 1.3.6.1.4.1.1916.2.131.50.1.3.9.1.1.30
		extremeWingCfgSmartRfIrClientThreshold OBJECT-TYPE
			SYNTAX Unsigned32 (1..255)
			MAX-ACCESS read-write
			STATUS current
			DESCRIPTION
				"Number of associated clients after which channel change due to
				interference recovery is not allowed.
				
				XPath: /extremeWing-config/smart_rf_policy[name=key1]/ir_client_threshold"
			DEFVAL { 50 }
			::= { extremeWingCfgSmartRfEntry 30 }

		
		-- 1.3.6.1.4.1.1916.2.131.50.1.3.9.1.1.31
		extremeWingCfgSmartRfIrChannelSwitchDeltaA OBJECT-TYPE
			SYNTAX Unsigned32 (5..35)
			UNITS "dBm"
			MAX-ACCESS read-write
			STATUS current
			DESCRIPTION
				"Difference in interference between current channel and
				the best possible channel to perform a channel switch on
				5GHz radios
				
				XPath: /extremeWing-config/smart_rf_policy[name=key1]/ir_channel_switch_delta_a"
			DEFVAL { 20 }
			::= { extremeWingCfgSmartRfEntry 31 }

		
		-- 1.3.6.1.4.1.1916.2.131.50.1.3.9.1.1.32
		extremeWingCfgSmartRfIrChannelSwitchDeltaBg OBJECT-TYPE
			SYNTAX Unsigned32 (5..35)
			UNITS "dBm"
			MAX-ACCESS read-write
			STATUS current
			DESCRIPTION
				"Difference in interference between current channel and
				the best possible channel to perform a channel switch on
				2.4GHz radios
				
				XPath: /extremeWing-config/smart_rf_policy[name=key1]/ir_channel_switch_delta_bg"
			DEFVAL { 20 }
			::= { extremeWingCfgSmartRfEntry 32 }

		
		-- 1.3.6.1.4.1.1916.2.131.50.1.3.9.1.1.33
		extremeWingCfgSmartRfNeighborRecovery OBJECT-TYPE
			SYNTAX TruthValue
			MAX-ACCESS read-write
			STATUS current
			DESCRIPTION
				"Recover issues due to faulty neighbor radios.
				
				XPath: /extremeWing-config/smart_rf_policy[name=key1]/neighbor_recovery"
			DEFVAL { true }
			::= { extremeWingCfgSmartRfEntry 33 }

		
		-- 1.3.6.1.4.1.1916.2.131.50.1.3.9.1.1.34
		extremeWingCfgSmartRfNrPowerThresholdA OBJECT-TYPE
			SYNTAX Integer32 (-85..-55)
			UNITS "dBm"
			MAX-ACCESS read-write
			STATUS current
			DESCRIPTION
				"Power threshold to be used while performing neighbor recovery
				on 5GHz radios.
				
				XPath: /extremeWing-config/smart_rf_policy[name=key1]/nr_power_threshold_a"
			DEFVAL { -70 }
			::= { extremeWingCfgSmartRfEntry 34 }

		
		-- 1.3.6.1.4.1.1916.2.131.50.1.3.9.1.1.35
		extremeWingCfgSmartRfNrPowerThresholdBg OBJECT-TYPE
			SYNTAX Integer32 (-85..-55)
			UNITS "dBm"
			MAX-ACCESS read-write
			STATUS current
			DESCRIPTION
				"Power threshold to be used while performing neighbor recovery
				on 2.4GHz radios.
				
				XPath: /extremeWing-config/smart_rf_policy[name=key1]/nr_power_threshold_bg"
			DEFVAL { -70 }
			::= { extremeWingCfgSmartRfEntry 35 }

		
		-- 1.3.6.1.4.1.1916.2.131.50.1.3.9.1.1.36
		extremeWingCfgSmartRfCoverageHoleRecovery OBJECT-TYPE
			SYNTAX TruthValue
			MAX-ACCESS read-write
			STATUS current
			DESCRIPTION
				"Recover from coverage hole.
				
				XPath: /extremeWing-config/smart_rf_policy[name=key1]/coverage_hole_recovery"
			DEFVAL { true }
			::= { extremeWingCfgSmartRfEntry 36 }

		
		-- 1.3.6.1.4.1.1916.2.131.50.1.3.9.1.1.37
		extremeWingCfgSmartRfChrIntervalA OBJECT-TYPE
			SYNTAX Unsigned32 (1..120)
			UNITS "seconds"
			MAX-ACCESS read-write
			STATUS current
			DESCRIPTION
				"Interval at which coverage-hole-recovery should be performed
				for 5GHz radios.
				
				XPath: /extremeWing-config/smart_rf_policy[name=key1]/chr_interval_a"
			DEFVAL { 30 }
			::= { extremeWingCfgSmartRfEntry 37 }

		
		-- 1.3.6.1.4.1.1916.2.131.50.1.3.9.1.1.38
		extremeWingCfgSmartRfChrIntervalBg OBJECT-TYPE
			SYNTAX Unsigned32 (1..120)
			UNITS "seconds"
			MAX-ACCESS read-write
			STATUS current
			DESCRIPTION
				"Interval at which coverage-hole-recovery should be performed
				for 2.4GHz radios.
				
				XPath: /extremeWing-config/smart_rf_policy[name=key1]/chr_interval_bg"
			DEFVAL { 30 }
			::= { extremeWingCfgSmartRfEntry 38 }

		
		-- 1.3.6.1.4.1.1916.2.131.50.1.3.9.1.1.39
		extremeWingCfgSmartRfChrCovIntervalA OBJECT-TYPE
			SYNTAX Unsigned32 (1..120)
			UNITS "seconds"
			MAX-ACCESS read-write
			STATUS current
			DESCRIPTION
				"Interval at which coverage-hole-recovery should be performed
				after coverage hole is discovered for 5GHz radios.
				
				XPath: /extremeWing-config/smart_rf_policy[name=key1]/chr_cov_interval_a"
			DEFVAL { 10 }
			::= { extremeWingCfgSmartRfEntry 39 }

		
		-- 1.3.6.1.4.1.1916.2.131.50.1.3.9.1.1.40
		extremeWingCfgSmartRfChrCovIntervalBg OBJECT-TYPE
			SYNTAX Unsigned32 (1..120)
			UNITS "seconds"
			MAX-ACCESS read-write
			STATUS current
			DESCRIPTION
				"Interval at which coverage-hole-recovery should be performed
				after coverage hole is discovered for 2.4GHz radios.
				
				XPath: /extremeWing-config/smart_rf_policy[name=key1]/chr_cov_interval_bg"
			DEFVAL { 10 }
			::= { extremeWingCfgSmartRfEntry 40 }

		
		-- 1.3.6.1.4.1.1916.2.131.50.1.3.9.1.1.41
		extremeWingCfgSmartRfChrSnrThresholdA OBJECT-TYPE
			SYNTAX Unsigned32 (1..75)
			UNITS "dB"
			MAX-ACCESS read-write
			STATUS current
			DESCRIPTION
				"The signal to noise ratio below which coverage recovery is
				initiated for 5GHz radios.
				
				XPath: /extremeWing-config/smart_rf_policy[name=key1]/chr_snr_threshold_a"
			DEFVAL { 20 }
			::= { extremeWingCfgSmartRfEntry 41 }

		
		-- 1.3.6.1.4.1.1916.2.131.50.1.3.9.1.1.42
		extremeWingCfgSmartRfChrSnrThresholdBg OBJECT-TYPE
			SYNTAX Unsigned32 (1..75)
			UNITS "dB"
			MAX-ACCESS read-write
			STATUS current
			DESCRIPTION
				"The signal to noise ratio below which coverage recovery is
				initiated for 2.4GHz radios.
				
				XPath: /extremeWing-config/smart_rf_policy[name=key1]/chr_snr_threshold_bg"
			DEFVAL { 20 }
			::= { extremeWingCfgSmartRfEntry 42 }

		
		-- 1.3.6.1.4.1.1916.2.131.50.1.3.9.1.1.43
		extremeWingCfgSmartRfChrClientThresholdA OBJECT-TYPE
			SYNTAX Unsigned32 (1..255)
			MAX-ACCESS read-write
			STATUS current
			DESCRIPTION
				"Minimum number of clients below SNR threhold required for
				coverage hole recovery on 5GHz radios.
				
				XPath: /extremeWing-config/smart_rf_policy[name=key1]/chr_client_threshold_a"
			DEFVAL { 1 }
			::= { extremeWingCfgSmartRfEntry 43 }

		
		-- 1.3.6.1.4.1.1916.2.131.50.1.3.9.1.1.44
		extremeWingCfgSmartRfChrClientThresholdBg OBJECT-TYPE
			SYNTAX Unsigned32 (1..255)
			MAX-ACCESS read-write
			STATUS current
			DESCRIPTION
				"Minimum number of clients below SNR threhold required for
				coverage hole recovery on 2.4GHz radios.
				
				XPath: /extremeWing-config/smart_rf_policy[name=key1]/chr_client_threshold_bg"
			DEFVAL { 1 }
			::= { extremeWingCfgSmartRfEntry 44 }

		
		-- 1.3.6.1.4.1.1916.2.131.50.1.3.9.1.1.45
		extremeWingCfgSmartRfChannelHoldTime OBJECT-TYPE
			SYNTAX Unsigned32 (0..86400)
			UNITS "seconds"
			MAX-ACCESS read-write
			STATUS current
			DESCRIPTION
				"The minimum time between two channel changes on a radio
				during interference recovery.
				
				XPath: /extremeWing-config/smart_rf_policy[name=key1]/channel_hold_time"
			DEFVAL { 3600 }
			::= { extremeWingCfgSmartRfEntry 45 }

		
		-- 1.3.6.1.4.1.1916.2.131.50.1.3.9.1.1.46
		extremeWingCfgSmartRfPowerHoldTime OBJECT-TYPE
			SYNTAX Unsigned32 (0..3600)
			UNITS "seconds"
			MAX-ACCESS read-write
			STATUS current
			DESCRIPTION
				"The minimum time between two power changes on a radio during
				neighbor recovery.
				
				XPath: /extremeWing-config/smart_rf_policy[name=key1]/power_hold_time"
			DEFVAL { 0 }
			::= { extremeWingCfgSmartRfEntry 46 }

		
		-- 1.3.6.1.4.1.1916.2.131.50.1.3.9.1.1.47
		extremeWingCfgSmartRfOcsMeshpointA OBJECT-TYPE
			SYNTAX DisplayString (SIZE (1..64))
			MAX-ACCESS read-write
			STATUS current
			DESCRIPTION
				"Meshpoint to be monitored during off channel scan for 5GHz radios
				
				XPath: /extremeWing-config/smart_rf_policy[name=key1]/ocs_meshpoint_a"
			::= { extremeWingCfgSmartRfEntry 47 }

		
		-- 1.3.6.1.4.1.1916.2.131.50.1.3.9.1.1.48
		extremeWingCfgSmartRfOcsMeshpointBg OBJECT-TYPE
			SYNTAX DisplayString (SIZE (1..64))
			MAX-ACCESS read-write
			STATUS current
			DESCRIPTION
				"Meshpoint to be monitored during off channel scan for 2.4GHz radios
				
				XPath: /extremeWing-config/smart_rf_policy[name=key1]/ocs_meshpoint_bg"
			::= { extremeWingCfgSmartRfEntry 48 }

		
-- /extremeWing-config/captive_portal
		-- 1.3.6.1.4.1.1916.2.131.50.1.3.10
		extremeWingCfgCaptPrtl OBJECT IDENTIFIER ::= { extremeWingConfig 10 }

		
		-- 1.3.6.1.4.1.1916.2.131.50.1.3.10.1
		extremeWingCfgCaptPrtlTable OBJECT-TYPE
			SYNTAX SEQUENCE OF ExtremeWingCfgCaptPrtlEntry
			MAX-ACCESS not-accessible
			STATUS current
			DESCRIPTION
				"Configuration parameters of a WLAN/VLAN captive portal
				authentication profile
				
				/extremeWing-config/captive_portal"
			::= { extremeWingCfgCaptPrtl 1 }

		
		-- 1.3.6.1.4.1.1916.2.131.50.1.3.10.1.1
		extremeWingCfgCaptPrtlEntry OBJECT-TYPE
			SYNTAX ExtremeWingCfgCaptPrtlEntry
			MAX-ACCESS not-accessible
			STATUS current
			DESCRIPTION
				"An entry in the table."
			INDEX { extremeWingCfgCaptPrtlName }
			::= { extremeWingCfgCaptPrtlTable 1 }

		
		ExtremeWingCfgCaptPrtlEntry ::=
			SEQUENCE { 
				extremeWingCfgCaptPrtlName
					ExtremeWingIdentifier,
				extremeWingCfgCaptPrtlAccessType
					DisplayString,
				extremeWingCfgCaptPrtlAccessTime
					Unsigned32,
				extremeWingCfgCaptPrtlCustomAuthInfo
					DisplayString,
				extremeWingCfgCaptPrtlConnectionMode
					DisplayString,
				extremeWingCfgCaptPrtlInactivityTimeout
					Unsigned32,
				extremeWingCfgCaptPrtlServer
					DisplayString,
				extremeWingCfgCaptPrtlServerMode
					DisplayString,
				extremeWingCfgCaptPrtlSimultaneousUsers
					Unsigned32,
				extremeWingCfgCaptPrtlTermsAgreement
					TruthValue,
				extremeWingCfgCaptPrtlWebpageLocation
					DisplayString,
				extremeWingCfgCaptPrtlAccountingRadius
					TruthValue,
				extremeWingCfgCaptPrtlAaaPolicy
					ExtremeWingIdentifier,
				extremeWingCfgCaptPrtlDnsWhitelist
					ExtremeWingIdentifier,
				extremeWingCfgCaptPrtlWebpageAutoUpload
					TruthValue,
                                extremeWingCfgCaptPrtlExternalLoginUrl
                                        DisplayString,
                                extremeWingCfgCaptPrtlExternalWelcomeUrl
                                        DisplayString,
                                extremeWingCfgCaptPrtlExternalFailUrl
                                        DisplayString,
                                extremeWingCfgCaptPrtlExternalAgreementUrl
                                        DisplayString
			 }

		-- 1.3.6.1.4.1.1916.2.131.50.1.3.10.1.1.1
		extremeWingCfgCaptPrtlName OBJECT-TYPE
			SYNTAX ExtremeWingIdentifier
			MAX-ACCESS read-only
			STATUS current
			DESCRIPTION
				"
				
				XPath: /extremeWing-config/captive_portal[name=key1]/name"
			::= { extremeWingCfgCaptPrtlEntry 1 }

		
		-- 1.3.6.1.4.1.1916.2.131.50.1.3.10.1.1.3
		extremeWingCfgCaptPrtlAccessType OBJECT-TYPE
			SYNTAX DisplayString
			MAX-ACCESS read-write
			STATUS current
			DESCRIPTION
				"Access type of this captive portal
				
				Values:
				no-auth
				logging
				custom-auth-radius
				radius
				
				XPath: /extremeWing-config/captive_portal[name=key1]/access_type"
			DEFVAL { "radius" }
			::= { extremeWingCfgCaptPrtlEntry 3 }

		
		-- 1.3.6.1.4.1.1916.2.131.50.1.3.10.1.1.4
		extremeWingCfgCaptPrtlAccessTime OBJECT-TYPE
			SYNTAX Unsigned32 (30..10080)
			UNITS "minutes"
			MAX-ACCESS read-write
			STATUS current
			DESCRIPTION
				"Allowed access time for the client. Used when there is
				no session time value in RADIUS response.
				
				XPath: /extremeWing-config/captive_portal[name=key1]/access_time"
			DEFVAL { 1440 }
			::= { extremeWingCfgCaptPrtlEntry 4 }

		
		-- 1.3.6.1.4.1.1916.2.131.50.1.3.10.1.1.5
		extremeWingCfgCaptPrtlCustomAuthInfo OBJECT-TYPE
			SYNTAX DisplayString (SIZE (32))
			MAX-ACCESS read-write
			STATUS current
			DESCRIPTION
				"Custom user information used for RADIUS lookup/logging when
				access-type custom-auth-radius/logging is configured.
				
				XPath: /extremeWing-config/captive_portal[name=key1]/custom_auth_info"
			::= { extremeWingCfgCaptPrtlEntry 5 }

		
		-- 1.3.6.1.4.1.1916.2.131.50.1.3.10.1.1.6
		extremeWingCfgCaptPrtlConnectionMode OBJECT-TYPE
			SYNTAX DisplayString
			MAX-ACCESS read-write
			STATUS current
			DESCRIPTION
				"
				Values:
				http
				https
				
				XPath: /extremeWing-config/captive_portal[name=key1]/connection_mode"
			DEFVAL { "http" }
			::= { extremeWingCfgCaptPrtlEntry 6 }

		
		-- 1.3.6.1.4.1.1916.2.131.50.1.3.10.1.1.7
		extremeWingCfgCaptPrtlInactivityTimeout OBJECT-TYPE
			SYNTAX Unsigned32 (300..1800)
			UNITS "seconds"
			MAX-ACCESS read-write
			STATUS current
			DESCRIPTION
				"If a frame is not received from client for this
				amount of time, then current session will be removed.
				
				XPath: /extremeWing-config/captive_portal[name=key1]/inactivity_timeout"
			DEFVAL { 600 }
			::= { extremeWingCfgCaptPrtlEntry 7 }

		
		-- 1.3.6.1.4.1.1916.2.131.50.1.3.10.1.1.8
		extremeWingCfgCaptPrtlServer OBJECT-TYPE
			SYNTAX DisplayString
			MAX-ACCESS read-write
			STATUS current
			DESCRIPTION
				"Device(s) hosting the captive portal service, Address of
				controller or access point for centralized mode,
				Virtual hostname of controller(s) in case of
				centralized-controller mode
				
				XPath: /extremeWing-config/captive_portal[name=key1]/server"
			::= { extremeWingCfgCaptPrtlEntry 8 }

		
		-- 1.3.6.1.4.1.1916.2.131.50.1.3.10.1.1.9
		extremeWingCfgCaptPrtlServerMode OBJECT-TYPE
			SYNTAX DisplayString
			MAX-ACCESS read-write
			STATUS current
			DESCRIPTION
				"In centralized/centralized-controller mode, the configured
				server is used as the captive portal server.  In self mode,
				the device serving the WLAN is used as the
				captive portal server.
				
				Values:
				self
				centralized
				centralized-controller
				
				XPath: /extremeWing-config/captive_portal[name=key1]/server_mode"
			DEFVAL { "self" }
			::= { extremeWingCfgCaptPrtlEntry 9 }

		
		-- 1.3.6.1.4.1.1916.2.131.50.1.3.10.1.1.10
		extremeWingCfgCaptPrtlSimultaneousUsers OBJECT-TYPE
			SYNTAX Unsigned32 (1..8192)
			MAX-ACCESS read-write
			STATUS current
			DESCRIPTION
				"Number of MAC addresses that are allowed to use a username at
				the same time.
				
				XPath: /extremeWing-config/captive_portal[name=key1]/simultaneous-users"
			::= { extremeWingCfgCaptPrtlEntry 10 }

		
		-- 1.3.6.1.4.1.1916.2.131.50.1.3.10.1.1.11
		extremeWingCfgCaptPrtlTermsAgreement OBJECT-TYPE
			SYNTAX TruthValue
			MAX-ACCESS read-write
			STATUS current
			DESCRIPTION
				"Combined with any access type, terms needs to be included in
				agreement page
				
				XPath: /extremeWing-config/captive_portal[name=key1]/terms_agreement"
			DEFVAL { false }
			::= { extremeWingCfgCaptPrtlEntry 11 }

		
		-- 1.3.6.1.4.1.1916.2.131.50.1.3.10.1.1.12
		extremeWingCfgCaptPrtlWebpageLocation OBJECT-TYPE
			SYNTAX DisplayString
			MAX-ACCESS read-write
			STATUS current
			DESCRIPTION
				"
				Values:
				internal
				external
				advanced
				
				XPath: /extremeWing-config/captive_portal[name=key1]/webpage_location"
			DEFVAL { "internal" }
			::= { extremeWingCfgCaptPrtlEntry 12 }

		
		-- 1.3.6.1.4.1.1916.2.131.50.1.3.10.1.1.13
		extremeWingCfgCaptPrtlAccountingRadius OBJECT-TYPE
			SYNTAX TruthValue
			MAX-ACCESS read-write
			STATUS current
			DESCRIPTION
				"
				
				XPath: /extremeWing-config/captive_portal[name=key1]/accounting_radius"
			DEFVAL { false }
			::= { extremeWingCfgCaptPrtlEntry 13 }

		
		-- 1.3.6.1.4.1.1916.2.131.50.1.3.10.1.1.14
		extremeWingCfgCaptPrtlAaaPolicy OBJECT-TYPE
			SYNTAX ExtremeWingIdentifier
			MAX-ACCESS read-write
			STATUS current
			DESCRIPTION
				"
				
				XPath: /extremeWing-config/captive_portal[name=key1]/aaa_policy"
			::= { extremeWingCfgCaptPrtlEntry 14 }

		
		-- 1.3.6.1.4.1.1916.2.131.50.1.3.10.1.1.15
		extremeWingCfgCaptPrtlDnsWhitelist OBJECT-TYPE
			SYNTAX ExtremeWingIdentifier
			MAX-ACCESS read-write
			STATUS current
			DESCRIPTION
				"
				
				XPath: /extremeWing-config/captive_portal[name=key1]/dns_whitelist"
			::= { extremeWingCfgCaptPrtlEntry 15 }

		-- 1.3.6.1.4.1.1916.2.131.50.1.3.10.1.1.16
		extremeWingCfgCaptPrtlWebpageAutoUpload OBJECT-TYPE
			SYNTAX TruthValue
			MAX-ACCESS read-write
			STATUS current
			DESCRIPTION
				"
				
				XPath: /extremeWing-config/captive_portal[name=key1]/webpage_auto_upload"
			DEFVAL { false }
			::= { extremeWingCfgCaptPrtlEntry 16 }

                -- 1.3.6.1.4.1.1916.2.131.50.1.3.10.1.1.17
                extremeWingCfgCaptPrtlExternalLoginUrl OBJECT-TYPE
                        SYNTAX DisplayString
                        MAX-ACCESS read-write
                        STATUS current
                        DESCRIPTION
                                "External webportal login page URL

                                XPath: /extremeWing-config/captive_portal[name=key1]/external_pages/login"
                        ::= { extremeWingCfgCaptPrtlEntry 17 }

                -- 1.3.6.1.4.1.1916.2.131.50.1.3.10.1.1.18
                extremeWingCfgCaptPrtlExternalWelcomeUrl OBJECT-TYPE
                        SYNTAX DisplayString
                        MAX-ACCESS read-write
                        STATUS current
                        DESCRIPTION
                                "External webportal welcome page URL

                                XPath: /extremeWing-config/captive_portal[name=key1]/external_pages/welcome"
                        ::= { extremeWingCfgCaptPrtlEntry 18 }

                -- 1.3.6.1.4.1.1916.2.131.50.1.3.10.1.1.19
                extremeWingCfgCaptPrtlExternalFailUrl OBJECT-TYPE
                        SYNTAX DisplayString
                        MAX-ACCESS read-write
                        STATUS current
                        DESCRIPTION
                                "External webportal fail page URL

                                XPath: /extremeWing-config/captive_portal[name=key1]/external_pages/fail"
                        ::= { extremeWingCfgCaptPrtlEntry 19 }

                -- 1.3.6.1.4.1.1916.2.131.50.1.3.10.1.1.20
                extremeWingCfgCaptPrtlExternalAgreementUrl OBJECT-TYPE
                        SYNTAX DisplayString
                        MAX-ACCESS read-write
                        STATUS current
                        DESCRIPTION
                                "External webportal agreement page URL

                                XPath: /extremeWing-config/captive_portal[name=key1]/external_pages/agreement"
                        ::= { extremeWingCfgCaptPrtlEntry 20 }

		-- 1.3.6.1.4.1.1916.2.131.50.1.3.10.4
		extremeWingCfgCaptPrtlAcctSyslogTable OBJECT-TYPE
			SYNTAX SEQUENCE OF ExtremeWingCfgCaptPrtlAcctSyslogEntry
			MAX-ACCESS not-accessible
			STATUS current
			DESCRIPTION
				"
				
				/extremeWing-config/captive_portal"
			::= { extremeWingCfgCaptPrtl 4 }

		
		-- 1.3.6.1.4.1.1916.2.131.50.1.3.10.4.1
		extremeWingCfgCaptPrtlAcctSyslogEntry OBJECT-TYPE
			SYNTAX ExtremeWingCfgCaptPrtlAcctSyslogEntry
			MAX-ACCESS not-accessible
			STATUS current
			DESCRIPTION
				"An entry in the table."
			INDEX { extremeWingCfgCaptPrtlName }
			::= { extremeWingCfgCaptPrtlAcctSyslogTable 1 }

		
		ExtremeWingCfgCaptPrtlAcctSyslogEntry ::=
			SEQUENCE { 
				extremeWingCfgCaptPrtlAcctSyslogEnable
					TruthValue,
				extremeWingCfgCaptPrtlAcctSyslogHost
					DisplayString,
				extremeWingCfgCaptPrtlAcctSyslogPort
					Unsigned32
			 }

		-- 1.3.6.1.4.1.1916.2.131.50.1.3.10.4.1.1
		extremeWingCfgCaptPrtlAcctSyslogEnable OBJECT-TYPE
			SYNTAX TruthValue
			MAX-ACCESS read-write
			STATUS current
			DESCRIPTION
				"
				
				XPath: /extremeWing-config/captive_portal[name=key1]/accounting_syslog/enable"
			DEFVAL { false }
			::= { extremeWingCfgCaptPrtlAcctSyslogEntry 1 }

		
		-- 1.3.6.1.4.1.1916.2.131.50.1.3.10.4.1.2
		extremeWingCfgCaptPrtlAcctSyslogHost OBJECT-TYPE
			SYNTAX DisplayString
			MAX-ACCESS read-write
			STATUS current
			DESCRIPTION
				"
				
				XPath: /extremeWing-config/captive_portal[name=key1]/accounting_syslog/host"
			::= { extremeWingCfgCaptPrtlAcctSyslogEntry 2 }

		
		-- 1.3.6.1.4.1.1916.2.131.50.1.3.10.4.1.3
		extremeWingCfgCaptPrtlAcctSyslogPort OBJECT-TYPE
			SYNTAX Unsigned32 (1..65535)
			MAX-ACCESS read-write
			STATUS current
			DESCRIPTION
				"
				
				XPath: /extremeWing-config/captive_portal[name=key1]/accounting_syslog/port"
			DEFVAL { 514 }
			::= { extremeWingCfgCaptPrtlAcctSyslogEntry 3 }

		-- 1.3.6.1.4.1.1916.2.131.50.1.3.10.5
		extremeWingCfgCaptPrtlInternalPageNoServTable OBJECT-TYPE
			SYNTAX SEQUENCE OF ExtremeWingCfgCaptPrtlInternalPageNoServEntry
			MAX-ACCESS not-accessible
			STATUS current
			DESCRIPTION
				"Description."
			::= { extremeWingCfgCaptPrtl 5 }

		
		-- 1.3.6.1.4.1.1916.2.131.50.1.3.10.5.1
		extremeWingCfgCaptPrtlInternalPageNoServEntry OBJECT-TYPE
			SYNTAX ExtremeWingCfgCaptPrtlInternalPageNoServEntry
			MAX-ACCESS not-accessible
			STATUS current
			DESCRIPTION
				"Description."
			INDEX { extremeWingCfgCaptPrtlName }
			::= { extremeWingCfgCaptPrtlInternalPageNoServTable 1 }

		
		ExtremeWingCfgCaptPrtlInternalPageNoServEntry ::=
			SEQUENCE { 
				extremeWingCfgCaptPrtlInternalPageNoServDescription
					DisplayString,
				extremeWingCfgCaptPrtlInternalPageNoServFooter
					DisplayString,
				extremeWingCfgCaptPrtlInternalPageNoServHeader
					DisplayString,
				extremeWingCfgCaptPrtlInternalPageNoServMainLogoUrl
					DisplayString,
				extremeWingCfgCaptPrtlInternalPageNoServSmallLogoUrl
					DisplayString,
				extremeWingCfgCaptPrtlInternalPageNoServTitle
					DisplayString
			 }

		-- 1.3.6.1.4.1.1916.2.131.50.1.3.10.5.1.1
		extremeWingCfgCaptPrtlInternalPageNoServDescription OBJECT-TYPE
			SYNTAX DisplayString
			MAX-ACCESS read-write
			STATUS current
			DESCRIPTION
				"Description to embed in this page
				 XPath: /extremeWing-config/captive_portal[name=key1]/internal_pages_no_service/description"
			::= { extremeWingCfgCaptPrtlInternalPageNoServEntry 1 }

		
		-- 1.3.6.1.4.1.1916.2.131.50.1.3.10.5.1.2
		extremeWingCfgCaptPrtlInternalPageNoServFooter OBJECT-TYPE
			SYNTAX DisplayString (SIZE (0..255))
			MAX-ACCESS read-write
			STATUS current
			DESCRIPTION
				"Footer information to embed for this page
				XPath: /extremeWing-config/captive_portal[name=key1]/internal_pages_no_service/footer"
			::= { extremeWingCfgCaptPrtlInternalPageNoServEntry 2 }

		
		-- 1.3.6.1.4.1.1916.2.131.50.1.3.10.5.1.3
		extremeWingCfgCaptPrtlInternalPageNoServHeader OBJECT-TYPE
			SYNTAX DisplayString (SIZE (0..255))
			MAX-ACCESS read-write
			STATUS current
			DESCRIPTION
				"Header information for this page
				XPath: /extremeWing-config/captive_portal[name=key1]/internal_pages_no_service/header"
			::= { extremeWingCfgCaptPrtlInternalPageNoServEntry 3 }


		-- 1.3.6.1.4.1.1916.2.131.50.1.3.10.5.1.4
		extremeWingCfgCaptPrtlInternalPageNoServMainLogoUrl OBJECT-TYPE
			SYNTAX DisplayString (SIZE (0..255))
			MAX-ACCESS read-write
			STATUS current
			DESCRIPTION
				"The URL from where the image will be loaded
				 XPath: /extremeWing-config/captive_portal[name=key1]/internal_pages_no_service/main_logo"
			::= { extremeWingCfgCaptPrtlInternalPageNoServEntry 4 }

		
		-- 1.3.6.1.4.1.1916.2.131.50.1.3.10.5.1.5
		extremeWingCfgCaptPrtlInternalPageNoServSmallLogoUrl OBJECT-TYPE
			SYNTAX DisplayString (SIZE (0..255))
			MAX-ACCESS read-write
			STATUS current
			DESCRIPTION
				"The URL from where the image will be loaded
				XPath: /extremeWing-config/captive_portal[name=key1]/internal_pages_no_service/small_logo
				"
			::= { extremeWingCfgCaptPrtlInternalPageNoServEntry 5 }

		
		-- 1.3.6.1.4.1.1916.2.131.50.1.3.10.5.1.6
		extremeWingCfgCaptPrtlInternalPageNoServTitle OBJECT-TYPE
			SYNTAX DisplayString (SIZE (0..255))
			MAX-ACCESS read-write
			STATUS current
			DESCRIPTION
				"Title for this page
				XPath: /extremeWing-config/captive_portal[name=key1]/internal_pages_no_service/title"
			::= { extremeWingCfgCaptPrtlInternalPageNoServEntry 6 }

		
-- /extremeWing-config/dns_whitelist
		-- 1.3.6.1.4.1.1916.2.131.50.1.3.11
		extremeWingCfgDnsWhitelist OBJECT IDENTIFIER ::= { extremeWingConfig 11 }

		
		-- 1.3.6.1.4.1.1916.2.131.50.1.3.11.1
		extremeWingCfgDnsWhitelistTable OBJECT-TYPE
			SYNTAX SEQUENCE OF ExtremeWingCfgDnsWhitelistEntry
			MAX-ACCESS not-accessible
			STATUS current
			DESCRIPTION
				"Whitelisted hostname and domainname entries.
				
				/extremeWing-config/dns_whitelist"
			::= { extremeWingCfgDnsWhitelist 1 }

		
		-- 1.3.6.1.4.1.1916.2.131.50.1.3.11.1.1
		extremeWingCfgDnsWhitelistEntry OBJECT-TYPE
			SYNTAX ExtremeWingCfgDnsWhitelistEntry
			MAX-ACCESS not-accessible
			STATUS current
			DESCRIPTION
				"An entry in the table."
			INDEX { extremeWingCfgDnsWhitelistName }
			::= { extremeWingCfgDnsWhitelistTable 1 }

		
		ExtremeWingCfgDnsWhitelistEntry ::=
			SEQUENCE { 
				extremeWingCfgDnsWhitelistName
					ExtremeWingIdentifier
			 }

		-- 1.3.6.1.4.1.1916.2.131.50.1.3.11.1.1.1
		extremeWingCfgDnsWhitelistName OBJECT-TYPE
			SYNTAX ExtremeWingIdentifier
			MAX-ACCESS read-only
			STATUS current
			DESCRIPTION
				"
				
				XPath: /extremeWing-config/dns_whitelist[name=key1]/name"
			::= { extremeWingCfgDnsWhitelistEntry 1 }

		
		-- 1.3.6.1.4.1.1916.2.131.50.1.3.11.2
		extremeWingCfgDnsWhitelistInstTable OBJECT-TYPE
			SYNTAX SEQUENCE OF ExtremeWingCfgDnsWhitelistInstEntry
			MAX-ACCESS not-accessible
			STATUS current
			DESCRIPTION
				"
				
				/extremeWing-config/dns_whitelist/entry"
			::= { extremeWingCfgDnsWhitelist 2 }

		
		-- 1.3.6.1.4.1.1916.2.131.50.1.3.11.2.1
		extremeWingCfgDnsWhitelistInstEntry OBJECT-TYPE
			SYNTAX ExtremeWingCfgDnsWhitelistInstEntry
			MAX-ACCESS not-accessible
			STATUS current
			DESCRIPTION
				"An entry in the table."
			INDEX { extremeWingCfgDnsWhitelistName, extremeWingCfgDnsWhitelistInstName }
			::= { extremeWingCfgDnsWhitelistInstTable 1 }

		
		ExtremeWingCfgDnsWhitelistInstEntry ::=
			SEQUENCE { 
				extremeWingCfgDnsWhitelistInstName
					ExtremeWingIdentifier,
				extremeWingCfgDnsWhitelistInstSuffix
					TruthValue
			 }

		-- 1.3.6.1.4.1.1916.2.131.50.1.3.11.2.1.1
		extremeWingCfgDnsWhitelistInstName OBJECT-TYPE
			SYNTAX ExtremeWingIdentifier
			MAX-ACCESS read-only
			STATUS current
			DESCRIPTION
				"Hostname or Domain Name or IP address.
				
				XPath: /extremeWing-config/dns_whitelist[name=key1]/entry[entry=key2]/entry"
			::= { extremeWingCfgDnsWhitelistInstEntry 1 }

		
		-- 1.3.6.1.4.1.1916.2.131.50.1.3.11.2.1.3
		extremeWingCfgDnsWhitelistInstSuffix OBJECT-TYPE
			SYNTAX TruthValue
			MAX-ACCESS read-write
			STATUS current
			DESCRIPTION
				"Match any hostname or domainname including this entry
				as suffix.
				
				XPath: /extremeWing-config/dns_whitelist[name=key1]/entry[entry=key2]/suffix"
			DEFVAL { false }
			::= { extremeWingCfgDnsWhitelistInstEntry 3 }

		
-- /extremeWing-config/ip_acl
		-- 1.3.6.1.4.1.1916.2.131.50.1.3.12
		extremeWingCfgIpAcl OBJECT IDENTIFIER ::= { extremeWingConfig 12 }

		
		-- 1.3.6.1.4.1.1916.2.131.50.1.3.12.1
		extremeWingCfgIpAclTable OBJECT-TYPE
			SYNTAX SEQUENCE OF ExtremeWingCfgIpAclEntry
			MAX-ACCESS not-accessible
			STATUS current
			DESCRIPTION
				"
				
				/extremeWing-config/ip_acl"
			::= { extremeWingCfgIpAcl 1 }

		
		-- 1.3.6.1.4.1.1916.2.131.50.1.3.12.1.1
		extremeWingCfgIpAclEntry OBJECT-TYPE
			SYNTAX ExtremeWingCfgIpAclEntry
			MAX-ACCESS not-accessible
			STATUS current
			DESCRIPTION
				"An entry in the table."
			INDEX { extremeWingCfgIpAclName }
			::= { extremeWingCfgIpAclTable 1 }

		
		ExtremeWingCfgIpAclEntry ::=
			SEQUENCE { 
				extremeWingCfgIpAclName
					ExtremeWingIdentifier
			 }

		-- 1.3.6.1.4.1.1916.2.131.50.1.3.12.1.1.1
		extremeWingCfgIpAclName OBJECT-TYPE
			SYNTAX ExtremeWingIdentifier
			MAX-ACCESS read-only
			STATUS current
			DESCRIPTION
				"
				
				XPath: /extremeWing-config/ip_acl[name=key1]/name"
			::= { extremeWingCfgIpAclEntry 1 }

		
		-- 1.3.6.1.4.1.1916.2.131.50.1.3.12.2
		extremeWingCfgIpAclRuleTable OBJECT-TYPE
			SYNTAX SEQUENCE OF ExtremeWingCfgIpAclRuleEntry
			MAX-ACCESS not-accessible
			STATUS current
			DESCRIPTION
				"
				
				/extremeWing-config/ip_acl/ip_rules"
			::= { extremeWingCfgIpAcl 2 }

		
		-- 1.3.6.1.4.1.1916.2.131.50.1.3.12.2.1
		extremeWingCfgIpAclRuleEntry OBJECT-TYPE
			SYNTAX ExtremeWingCfgIpAclRuleEntry
			MAX-ACCESS not-accessible
			STATUS current
			DESCRIPTION
				"An entry in the table."
			INDEX { extremeWingCfgIpAclName, extremeWingCfgIpAclRulePrecedence }
			::= { extremeWingCfgIpAclRuleTable 1 }

		
		ExtremeWingCfgIpAclRuleEntry ::=
			SEQUENCE { 
				extremeWingCfgIpAclRulePrecedence
					Unsigned32,
				extremeWingCfgIpAclRuleAllow
					DisplayString,
				extremeWingCfgIpAclRulePriorityField
					DisplayString,
				extremeWingCfgIpAclRuleMarkDscp
					Unsigned32,
				extremeWingCfgIpAclRuleMark8021p
					Unsigned32,
				extremeWingCfgIpAclRuleDescription
					DisplayString,
				extremeWingCfgIpAclRuleProtocol
					Unsigned32,
				extremeWingCfgIpAclRuleSip
					DisplayString,
				extremeWingCfgIpAclRuleDip
					DisplayString
			 }

		-- 1.3.6.1.4.1.1916.2.131.50.1.3.12.2.1.1
		extremeWingCfgIpAclRulePrecedence OBJECT-TYPE
			SYNTAX Unsigned32 (1..5000)
			MAX-ACCESS read-only
			STATUS current
			DESCRIPTION
				"The precedence number for the Access Control Entry (ACE).
				1 is the highest precedence rule and 5000 is the lowest
				precedence rule.
				
				XPath: /extremeWing-config/ip_acl[name=key1]/ip_rules[precedence=key2]/precedence"
			::= { extremeWingCfgIpAclRuleEntry 1 }

		
		-- 1.3.6.1.4.1.1916.2.131.50.1.3.12.2.1.3
		extremeWingCfgIpAclRuleAllow OBJECT-TYPE
			SYNTAX DisplayString
			MAX-ACCESS read-write
			STATUS current
			DESCRIPTION
				"
				Values:
				deny
				permit
				
				XPath: /extremeWing-config/ip_acl[name=key1]/ip_rules[precedence=key2]/allow"
			DEFVAL { "deny" }
			::= { extremeWingCfgIpAclRuleEntry 3 }

		
		-- 1.3.6.1.4.1.1916.2.131.50.1.3.12.2.1.4
		extremeWingCfgIpAclRulePriorityField OBJECT-TYPE
			SYNTAX DisplayString
			MAX-ACCESS read-write
			STATUS current
			DESCRIPTION
				"
				Values:
				8021p
				dscp
				
				XPath: /extremeWing-config/ip_acl[name=key1]/ip_rules[precedence=key2]/priority_field"
			DEFVAL { "dscp" }
			::= { extremeWingCfgIpAclRuleEntry 4 }

		
		-- 1.3.6.1.4.1.1916.2.131.50.1.3.12.2.1.5
		extremeWingCfgIpAclRuleMarkDscp OBJECT-TYPE
			SYNTAX Unsigned32 (0..63)
			MAX-ACCESS read-write
			STATUS current
			DESCRIPTION
				"Modify DSCP TOS bits in IP header.
				
				XPath: /extremeWing-config/ip_acl[name=key1]/ip_rules[precedence=key2]/mark_dscp"
			::= { extremeWingCfgIpAclRuleEntry 5 }

		
		-- 1.3.6.1.4.1.1916.2.131.50.1.3.12.2.1.6
		extremeWingCfgIpAclRuleMark8021p OBJECT-TYPE
			SYNTAX Unsigned32 (0..7)
			MAX-ACCESS read-write
			STATUS current
			DESCRIPTION
				"Modify 802.1p VLAN user priority
				
				XPath: /extremeWing-config/ip_acl[name=key1]/ip_rules[precedence=key2]/mark_8021p"
			::= { extremeWingCfgIpAclRuleEntry 6 }

		
		-- 1.3.6.1.4.1.1916.2.131.50.1.3.12.2.1.7
		extremeWingCfgIpAclRuleDescription OBJECT-TYPE
			SYNTAX DisplayString (SIZE (0..128))
			MAX-ACCESS read-write
			STATUS current
			DESCRIPTION
				"
				
				XPath: /extremeWing-config/ip_acl[name=key1]/ip_rules[precedence=key2]/description"
			::= { extremeWingCfgIpAclRuleEntry 7 }

		
		-- 1.3.6.1.4.1.1916.2.131.50.1.3.12.2.1.8
		extremeWingCfgIpAclRuleProtocol OBJECT-TYPE
			SYNTAX Unsigned32 (0..254)
			MAX-ACCESS read-write
			STATUS current
			DESCRIPTION
				"configure ip, tcp, udp, igmp, icmp, gre, ospf, vrrp, igp,
				eigrp protocols or any protocol number
				
				XPath: /extremeWing-config/ip_acl[name=key1]/ip_rules[precedence=key2]/protocol"
			::= { extremeWingCfgIpAclRuleEntry 8 }

		
		-- 1.3.6.1.4.1.1916.2.131.50.1.3.12.2.1.9
		extremeWingCfgIpAclRuleSip OBJECT-TYPE
			SYNTAX DisplayString
			MAX-ACCESS read-write
			STATUS current
			DESCRIPTION
				"configure host/network, for host configuration,
				network mask /32 has to be specified
				
				XPath: /extremeWing-config/ip_acl[name=key1]/ip_rules[precedence=key2]/sip"
			::= { extremeWingCfgIpAclRuleEntry 9 }

		
		-- 1.3.6.1.4.1.1916.2.131.50.1.3.12.2.1.10
		extremeWingCfgIpAclRuleDip OBJECT-TYPE
			SYNTAX DisplayString
			MAX-ACCESS read-write
			STATUS current
			DESCRIPTION
				"configure host/network, for host configuration,
				network mask /32 has to be specified
				
				XPath: /extremeWing-config/ip_acl[name=key1]/ip_rules[precedence=key2]/dip"
			::= { extremeWingCfgIpAclRuleEntry 10 }

		
-- /extremeWing-config/mac_acl
		-- 1.3.6.1.4.1.1916.2.131.50.1.3.13
		extremeWingCfgMacAcl OBJECT IDENTIFIER ::= { extremeWingConfig 13 }

		
		-- 1.3.6.1.4.1.1916.2.131.50.1.3.13.1
		extremeWingCfgMacAclTable OBJECT-TYPE
			SYNTAX SEQUENCE OF ExtremeWingCfgMacAclEntry
			MAX-ACCESS not-accessible
			STATUS current
			DESCRIPTION
				"
				
				/extremeWing-config/mac_acl"
			::= { extremeWingCfgMacAcl 1 }

		
		-- 1.3.6.1.4.1.1916.2.131.50.1.3.13.1.1
		extremeWingCfgMacAclEntry OBJECT-TYPE
			SYNTAX ExtremeWingCfgMacAclEntry
			MAX-ACCESS not-accessible
			STATUS current
			DESCRIPTION
				"An entry in the table."
			INDEX { extremeWingCfgMacAclName }
			::= { extremeWingCfgMacAclTable 1 }

		
		ExtremeWingCfgMacAclEntry ::=
			SEQUENCE { 
				extremeWingCfgMacAclName
					ExtremeWingIdentifier
			 }

		-- 1.3.6.1.4.1.1916.2.131.50.1.3.13.1.1.1
		extremeWingCfgMacAclName OBJECT-TYPE
			SYNTAX ExtremeWingIdentifier
			MAX-ACCESS read-only
			STATUS current
			DESCRIPTION
				"
				
				XPath: /extremeWing-config/mac_acl[name=key1]/name"
			::= { extremeWingCfgMacAclEntry 1 }

		
		-- 1.3.6.1.4.1.1916.2.131.50.1.3.13.2
		extremeWingCfgMacAclRuleTable OBJECT-TYPE
			SYNTAX SEQUENCE OF ExtremeWingCfgMacAclRuleEntry
			MAX-ACCESS not-accessible
			STATUS current
			DESCRIPTION
				"
				
				/extremeWing-config/mac_acl/mac_rules"
			::= { extremeWingCfgMacAcl 2 }

		
		-- 1.3.6.1.4.1.1916.2.131.50.1.3.13.2.1
		extremeWingCfgMacAclRuleEntry OBJECT-TYPE
			SYNTAX ExtremeWingCfgMacAclRuleEntry
			MAX-ACCESS not-accessible
			STATUS current
			DESCRIPTION
				"An entry in the table."
			INDEX { extremeWingCfgMacAclName, extremeWingCfgMacAclRulePrecedence }
			::= { extremeWingCfgMacAclRuleTable 1 }

		
		ExtremeWingCfgMacAclRuleEntry ::=
			SEQUENCE { 
				extremeWingCfgMacAclRulePrecedence
					Unsigned32,
				extremeWingCfgMacAclRuleAllow
					DisplayString,
				extremeWingCfgMacAclRulePriorityField
					DisplayString,
				extremeWingCfgMacAclRuleMarkDscp
					Unsigned32,
				extremeWingCfgMacAclRuleMark8021p
					Unsigned32,
				extremeWingCfgMacAclRuleDescription
					DisplayString,
				extremeWingCfgMacAclRuleSmac
					MacAddress,
				extremeWingCfgMacAclRuleSmacMask
					MacAddress,
				extremeWingCfgMacAclRuleDmac
					MacAddress,
				extremeWingCfgMacAclRuleDmacMask
					MacAddress,
				extremeWingCfgMacAclRuleMatchVlan
					Unsigned32,
				extremeWingCfgMacAclRuleMatchDot1p
					Unsigned32,
				extremeWingCfgMacAclRuleMatchType
					DisplayString
			 }

		-- 1.3.6.1.4.1.1916.2.131.50.1.3.13.2.1.1
		extremeWingCfgMacAclRulePrecedence OBJECT-TYPE
			SYNTAX Unsigned32 (1..5000)
			MAX-ACCESS read-only
			STATUS current
			DESCRIPTION
				"The precedence number for the Access Control Entry (ACE).
				1 is the highest precedence rule and 5000 is the lowest
				precedence rule.
				
				XPath: /extremeWing-config/mac_acl[name=key1]/mac_rules[precedence=key2]/precedence"
			::= { extremeWingCfgMacAclRuleEntry 1 }

		
		-- 1.3.6.1.4.1.1916.2.131.50.1.3.13.2.1.3
		extremeWingCfgMacAclRuleAllow OBJECT-TYPE
			SYNTAX DisplayString
			MAX-ACCESS read-write
			STATUS current
			DESCRIPTION
				"
				Values:
				deny
				permit
				
				XPath: /extremeWing-config/mac_acl[name=key1]/mac_rules[precedence=key2]/allow"
			DEFVAL { "deny" }
			::= { extremeWingCfgMacAclRuleEntry 3 }

		
		-- 1.3.6.1.4.1.1916.2.131.50.1.3.13.2.1.4
		extremeWingCfgMacAclRulePriorityField OBJECT-TYPE
			SYNTAX DisplayString
			MAX-ACCESS read-write
			STATUS current
			DESCRIPTION
				"
				Values:
				8021p
				dscp
				
				XPath: /extremeWing-config/mac_acl[name=key1]/mac_rules[precedence=key2]/priority_field"
			DEFVAL { "dscp" }
			::= { extremeWingCfgMacAclRuleEntry 4 }

		
		-- 1.3.6.1.4.1.1916.2.131.50.1.3.13.2.1.5
		extremeWingCfgMacAclRuleMarkDscp OBJECT-TYPE
			SYNTAX Unsigned32 (0..63)
			MAX-ACCESS read-write
			STATUS current
			DESCRIPTION
				"Modify DSCP TOS bits in IP header.
				
				XPath: /extremeWing-config/mac_acl[name=key1]/mac_rules[precedence=key2]/mark_dscp"
			::= { extremeWingCfgMacAclRuleEntry 5 }

		
		-- 1.3.6.1.4.1.1916.2.131.50.1.3.13.2.1.6
		extremeWingCfgMacAclRuleMark8021p OBJECT-TYPE
			SYNTAX Unsigned32 (0..7)
			MAX-ACCESS read-write
			STATUS current
			DESCRIPTION
				"Modify 802.1p VLAN user priority
				
				XPath: /extremeWing-config/mac_acl[name=key1]/mac_rules[precedence=key2]/mark_8021p"
			::= { extremeWingCfgMacAclRuleEntry 6 }

		
		-- 1.3.6.1.4.1.1916.2.131.50.1.3.13.2.1.7
		extremeWingCfgMacAclRuleDescription OBJECT-TYPE
			SYNTAX DisplayString (SIZE (0..128))
			MAX-ACCESS read-write
			STATUS current
			DESCRIPTION
				"
				
				XPath: /extremeWing-config/mac_acl[name=key1]/mac_rules[precedence=key2]/description"
			::= { extremeWingCfgMacAclRuleEntry 7 }

		
		-- 1.3.6.1.4.1.1916.2.131.50.1.3.13.2.1.8
		extremeWingCfgMacAclRuleSmac OBJECT-TYPE
			SYNTAX MacAddress
			MAX-ACCESS read-write
			STATUS current
			DESCRIPTION
				"
				
				XPath: /extremeWing-config/mac_acl[name=key1]/mac_rules[precedence=key2]/smac"
			::= { extremeWingCfgMacAclRuleEntry 8 }

		
		-- 1.3.6.1.4.1.1916.2.131.50.1.3.13.2.1.9
		extremeWingCfgMacAclRuleSmacMask OBJECT-TYPE
			SYNTAX MacAddress
			MAX-ACCESS read-write
			STATUS current
			DESCRIPTION
				"
				
				XPath: /extremeWing-config/mac_acl[name=key1]/mac_rules[precedence=key2]/smac_mask"
			DEFVAL { 'FFFFFFFFFFFF'h }
			::= { extremeWingCfgMacAclRuleEntry 9 }

		
		-- 1.3.6.1.4.1.1916.2.131.50.1.3.13.2.1.10
		extremeWingCfgMacAclRuleDmac OBJECT-TYPE
			SYNTAX MacAddress
			MAX-ACCESS read-write
			STATUS current
			DESCRIPTION
				"
				
				XPath: /extremeWing-config/mac_acl[name=key1]/mac_rules[precedence=key2]/dmac"
			::= { extremeWingCfgMacAclRuleEntry 10 }

		
		-- 1.3.6.1.4.1.1916.2.131.50.1.3.13.2.1.11
		extremeWingCfgMacAclRuleDmacMask OBJECT-TYPE
			SYNTAX MacAddress
			MAX-ACCESS read-write
			STATUS current
			DESCRIPTION
				"
				
				XPath: /extremeWing-config/mac_acl[name=key1]/mac_rules[precedence=key2]/dmac_mask"
			DEFVAL { 'FFFFFFFFFFFF'h }
			::= { extremeWingCfgMacAclRuleEntry 11 }

		
		-- 1.3.6.1.4.1.1916.2.131.50.1.3.13.2.1.12
		extremeWingCfgMacAclRuleMatchVlan OBJECT-TYPE
			SYNTAX Unsigned32 (1..4094)
			MAX-ACCESS read-write
			STATUS current
			DESCRIPTION
				"
				
				XPath: /extremeWing-config/mac_acl[name=key1]/mac_rules[precedence=key2]/match_vlan"
			::= { extremeWingCfgMacAclRuleEntry 12 }

		
		-- 1.3.6.1.4.1.1916.2.131.50.1.3.13.2.1.13
		extremeWingCfgMacAclRuleMatchDot1p OBJECT-TYPE
			SYNTAX Unsigned32 (0..7)
			MAX-ACCESS read-write
			STATUS current
			DESCRIPTION
				"8021.p priority to match
				
				XPath: /extremeWing-config/mac_acl[name=key1]/mac_rules[precedence=key2]/match_dot1p"
			::= { extremeWingCfgMacAclRuleEntry 13 }

		
		-- 1.3.6.1.4.1.1916.2.131.50.1.3.13.2.1.14
		extremeWingCfgMacAclRuleMatchType OBJECT-TYPE
			SYNTAX DisplayString (SIZE (0..16))
			MAX-ACCESS read-write
			STATUS current
			DESCRIPTION
				"ethertype protocol to match, can be one of the following
				strings:
				ip|ipv6 | arp | wisp | mint | 8021q | rarp | aarp | 
				appletalk | ipx |  <1-65535>
				
				XPath: /extremeWing-config/mac_acl[name=key1]/mac_rules[precedence=key2]/match_type"
			::= { extremeWingCfgMacAclRuleEntry 14 }

		
-- /extremeWing-config/wips_policy
		-- 1.3.6.1.4.1.1916.2.131.50.1.3.14
		extremeWingCfgWips OBJECT IDENTIFIER ::= { extremeWingConfig 14 }

		
		-- 1.3.6.1.4.1.1916.2.131.50.1.3.14.1
		extremeWingCfgWipsTable OBJECT-TYPE
			SYNTAX SEQUENCE OF ExtremeWingCfgWipsEntry
			MAX-ACCESS not-accessible
			STATUS current
			DESCRIPTION
				"
				
				/extremeWing-config/wips_policy"
			::= { extremeWingCfgWips 1 }

		
		-- 1.3.6.1.4.1.1916.2.131.50.1.3.14.1.1
		extremeWingCfgWipsEntry OBJECT-TYPE
			SYNTAX ExtremeWingCfgWipsEntry
			MAX-ACCESS not-accessible
			STATUS current
			DESCRIPTION
				"An entry in the table."
			INDEX { extremeWingCfgWipsName }
			::= { extremeWingCfgWipsTable 1 }

		
		ExtremeWingCfgWipsEntry ::=
			SEQUENCE { 
				extremeWingCfgWipsName
					ExtremeWingIdentifier,
				extremeWingCfgWipsEnable
					TruthValue,
				extremeWingCfgWipsHistoryThrottleDuration
					Unsigned32,
				extremeWingCfgWipsApDetection
					TruthValue,
				extremeWingCfgWipsApDetectionAgeout
					Unsigned32,
				extremeWingCfgWipsApDetectionWaitTime
					Unsigned32,
				extremeWingCfgWipsDeviceCategorization
					ExtremeWingIdentifier
			 }

		-- 1.3.6.1.4.1.1916.2.131.50.1.3.14.1.1.1
		extremeWingCfgWipsName OBJECT-TYPE
			SYNTAX ExtremeWingIdentifier
			MAX-ACCESS read-only
			STATUS current
			DESCRIPTION
				"
				
				XPath: /extremeWing-config/wips_policy[name=key1]/name"
			::= { extremeWingCfgWipsEntry 1 }

		
		-- 1.3.6.1.4.1.1916.2.131.50.1.3.14.1.1.3
		extremeWingCfgWipsEnable OBJECT-TYPE
			SYNTAX TruthValue
			MAX-ACCESS read-write
			STATUS current
			DESCRIPTION
				"Specifies if the given wips policy is enabled or not
				
				XPath: /extremeWing-config/wips_policy[name=key1]/enable"
			DEFVAL { true }
			::= { extremeWingCfgWipsEntry 3 }

		
		-- 1.3.6.1.4.1.1916.2.131.50.1.3.14.1.1.4
		extremeWingCfgWipsHistoryThrottleDuration OBJECT-TYPE
			SYNTAX Unsigned32 (30..86400)
			UNITS "seconds"
			MAX-ACCESS read-write
			STATUS current
			DESCRIPTION
				"The duration for which event duplicates are not stored in history.
				
				XPath: /extremeWing-config/wips_policy[name=key1]/history_throttle_duration"
			DEFVAL { 120 }
			::= { extremeWingCfgWipsEntry 4 }

		
		-- 1.3.6.1.4.1.1916.2.131.50.1.3.14.1.1.5
		extremeWingCfgWipsApDetection OBJECT-TYPE
			SYNTAX TruthValue
			MAX-ACCESS read-write
			STATUS current
			DESCRIPTION
				"enable Rogue AP detection
				
				XPath: /extremeWing-config/wips_policy[name=key1]/ap_detection"
			DEFVAL { false }
			::= { extremeWingCfgWipsEntry 5 }

		
		-- 1.3.6.1.4.1.1916.2.131.50.1.3.14.1.1.6
		extremeWingCfgWipsApDetectionAgeout OBJECT-TYPE
			SYNTAX Unsigned32 (30..86400)
			UNITS "seconds"
			MAX-ACCESS read-write
			STATUS current
			DESCRIPTION
				"ageout time for rogue APs
				
				XPath: /extremeWing-config/wips_policy[name=key1]/ap_detection_ageout"
			DEFVAL { 300 }
			::= { extremeWingCfgWipsEntry 6 }

		
		-- 1.3.6.1.4.1.1916.2.131.50.1.3.14.1.1.7
		extremeWingCfgWipsApDetectionWaitTime OBJECT-TYPE
			SYNTAX Unsigned32 (10..600)
			UNITS "seconds"
			MAX-ACCESS read-write
			STATUS current
			DESCRIPTION
				"wait time to determine before an AP is identified as rogue
				
				XPath: /extremeWing-config/wips_policy[name=key1]/ap_detection_wait_time"
			DEFVAL { 60 }
			::= { extremeWingCfgWipsEntry 7 }

		
		-- 1.3.6.1.4.1.1916.2.131.50.1.3.14.1.1.8
		extremeWingCfgWipsDeviceCategorization OBJECT-TYPE
			SYNTAX ExtremeWingIdentifier
			MAX-ACCESS read-write
			STATUS current
			DESCRIPTION
				"
				
				XPath: /extremeWing-config/wips_policy[name=key1]/device_categorization"
			::= { extremeWingCfgWipsEntry 8 }

		
-- /extremeWing-config/dhcp_server_policy
		-- 1.3.6.1.4.1.1916.2.131.50.1.3.15
		extremeWingCfgDhcpSvr OBJECT IDENTIFIER ::= { extremeWingConfig 15 }

		
		-- 1.3.6.1.4.1.1916.2.131.50.1.3.15.1
		extremeWingCfgDhcpSvrTable OBJECT-TYPE
			SYNTAX SEQUENCE OF ExtremeWingCfgDhcpSvrEntry
			MAX-ACCESS not-accessible
			STATUS current
			DESCRIPTION
				"User definition for the on-board DHCP server.
				
				/extremeWing-config/dhcp_server_policy"
			::= { extremeWingCfgDhcpSvr 1 }

		
		-- 1.3.6.1.4.1.1916.2.131.50.1.3.15.1.1
		extremeWingCfgDhcpSvrEntry OBJECT-TYPE
			SYNTAX ExtremeWingCfgDhcpSvrEntry
			MAX-ACCESS not-accessible
			STATUS current
			DESCRIPTION
				"An entry in the table."
			INDEX { extremeWingCfgDhcpSvrName }
			::= { extremeWingCfgDhcpSvrTable 1 }

		
		ExtremeWingCfgDhcpSvrEntry ::=
			SEQUENCE { 
				extremeWingCfgDhcpSvrName
					ExtremeWingIdentifier,
				extremeWingCfgDhcpSvrIgnoreBootp
					TruthValue,
				extremeWingCfgDhcpSvrPingInterval
					Unsigned32
			 }

		-- 1.3.6.1.4.1.1916.2.131.50.1.3.15.1.1.1
		extremeWingCfgDhcpSvrName OBJECT-TYPE
			SYNTAX ExtremeWingIdentifier
			MAX-ACCESS read-only
			STATUS current
			DESCRIPTION
				"
				
				XPath: /extremeWing-config/dhcp_server_policy[name=key1]/name"
			::= { extremeWingCfgDhcpSvrEntry 1 }

		
		-- 1.3.6.1.4.1.1916.2.131.50.1.3.15.1.1.3
		extremeWingCfgDhcpSvrIgnoreBootp OBJECT-TYPE
			SYNTAX TruthValue
			MAX-ACCESS read-write
			STATUS current
			DESCRIPTION
				"Configure DHCP server to ignore BOOTP requests.
				
				XPath: /extremeWing-config/dhcp_server_policy[name=key1]/ignore_bootp"
			DEFVAL { false }
			::= { extremeWingCfgDhcpSvrEntry 3 }

		
		-- 1.3.6.1.4.1.1916.2.131.50.1.3.15.1.1.4
		extremeWingCfgDhcpSvrPingInterval OBJECT-TYPE
			SYNTAX Unsigned32 (1..10)
			UNITS "seconds"
			MAX-ACCESS read-write
			STATUS current
			DESCRIPTION
				"Ping timeout interval.
				
				XPath: /extremeWing-config/dhcp_server_policy[name=key1]/dhcpSvrPingInterval"
			DEFVAL { 1 }
			::= { extremeWingCfgDhcpSvrEntry 4 }

		
		-- 1.3.6.1.4.1.1916.2.131.50.1.3.15.2
		extremeWingCfgDhcpSvrClassTable OBJECT-TYPE
			SYNTAX SEQUENCE OF ExtremeWingCfgDhcpSvrClassEntry
			MAX-ACCESS not-accessible
			STATUS current
			DESCRIPTION
				"
				
				/extremeWing-config/dhcp_server_policy/dhcp_class"
			::= { extremeWingCfgDhcpSvr 2 }

		
		-- 1.3.6.1.4.1.1916.2.131.50.1.3.15.2.1
		extremeWingCfgDhcpSvrClassEntry OBJECT-TYPE
			SYNTAX ExtremeWingCfgDhcpSvrClassEntry
			MAX-ACCESS not-accessible
			STATUS current
			DESCRIPTION
				"An entry in the table."
			INDEX { extremeWingCfgDhcpSvrName, extremeWingCfgDhcpSvrClassName }
			::= { extremeWingCfgDhcpSvrClassTable 1 }

		
		ExtremeWingCfgDhcpSvrClassEntry ::=
			SEQUENCE { 
				extremeWingCfgDhcpSvrClassName
					ExtremeWingIdentifier,
				extremeWingCfgDhcpSvrClassMultipleUserClass
					TruthValue
			 }

		-- 1.3.6.1.4.1.1916.2.131.50.1.3.15.2.1.1
		extremeWingCfgDhcpSvrClassName OBJECT-TYPE
			SYNTAX ExtremeWingIdentifier
			MAX-ACCESS read-only
			STATUS current
			DESCRIPTION
				"
				
				XPath: /extremeWing-config/dhcp_server_policy[name=key1]/dhcp_class[name=key2]/name"
			::= { extremeWingCfgDhcpSvrClassEntry 1 }

		
		-- 1.3.6.1.4.1.1916.2.131.50.1.3.15.2.1.3
		extremeWingCfgDhcpSvrClassMultipleUserClass OBJECT-TYPE
			SYNTAX TruthValue
			MAX-ACCESS read-write
			STATUS current
			DESCRIPTION
				"Enable multiple user class option.
				
				XPath: /extremeWing-config/dhcp_server_policy[name=key1]/dhcp_class[name=key2]/multiple_user_class"
			DEFVAL { false }
			::= { extremeWingCfgDhcpSvrClassEntry 3 }

		
		-- 1.3.6.1.4.1.1916.2.131.50.1.3.15.3
		extremeWingCfgDhcpSvrOptionTable OBJECT-TYPE
			SYNTAX SEQUENCE OF ExtremeWingCfgDhcpSvrOptionEntry
			MAX-ACCESS not-accessible
			STATUS current
			DESCRIPTION
				"Define an option; the value is assigned inside the pool.
				
				/extremeWing-config/dhcp_server_policy/dhcp_options"
			::= { extremeWingCfgDhcpSvr 3 }

		
		-- 1.3.6.1.4.1.1916.2.131.50.1.3.15.3.1
		extremeWingCfgDhcpSvrOptionEntry OBJECT-TYPE
			SYNTAX ExtremeWingCfgDhcpSvrOptionEntry
			MAX-ACCESS not-accessible
			STATUS current
			DESCRIPTION
				"An entry in the table."
			INDEX { extremeWingCfgDhcpSvrName, extremeWingCfgDhcpSvrOptionName }
			::= { extremeWingCfgDhcpSvrOptionTable 1 }

		
		ExtremeWingCfgDhcpSvrOptionEntry ::=
			SEQUENCE { 
				extremeWingCfgDhcpSvrOptionName
					ExtremeWingIdentifier,
				extremeWingCfgDhcpSvrOptionCode
					Unsigned32,
				extremeWingCfgDhcpSvrOptionType
					DisplayString
			 }

		-- 1.3.6.1.4.1.1916.2.131.50.1.3.15.3.1.1
		extremeWingCfgDhcpSvrOptionName OBJECT-TYPE
			SYNTAX ExtremeWingIdentifier
			MAX-ACCESS read-only
			STATUS current
			DESCRIPTION
				"
				
				XPath: /extremeWing-config/dhcp_server_policy[name=key1]/dhcp_options[name=key2]/name"
			::= { extremeWingCfgDhcpSvrOptionEntry 1 }

		
		-- 1.3.6.1.4.1.1916.2.131.50.1.3.15.3.1.3
		extremeWingCfgDhcpSvrOptionCode OBJECT-TYPE
			SYNTAX Unsigned32 (0..254)
			MAX-ACCESS read-write
			STATUS current
			DESCRIPTION
				"
				
				XPath: /extremeWing-config/dhcp_server_policy[name=key1]/dhcp_options[name=key2]/code"
			::= { extremeWingCfgDhcpSvrOptionEntry 3 }

		
		-- 1.3.6.1.4.1.1916.2.131.50.1.3.15.3.1.4
		extremeWingCfgDhcpSvrOptionType OBJECT-TYPE
			SYNTAX DisplayString
			MAX-ACCESS read-write
			STATUS current
			DESCRIPTION
				"
				Values:
				ip
				ascii
				hexstring
				
				XPath: /extremeWing-config/dhcp_server_policy[name=key1]/dhcp_options[name=key2]/type"
			::= { extremeWingCfgDhcpSvrOptionEntry 4 }

		
		-- 1.3.6.1.4.1.1916.2.131.50.1.3.15.4
		extremeWingCfgDhcpSvrPoolTable OBJECT-TYPE
			SYNTAX SEQUENCE OF ExtremeWingCfgDhcpSvrPoolEntry
			MAX-ACCESS not-accessible
			STATUS current
			DESCRIPTION
				"
				
				/extremeWing-config/dhcp_server_policy/dhcp_pools"
			::= { extremeWingCfgDhcpSvr 4 }

		
		-- 1.3.6.1.4.1.1916.2.131.50.1.3.15.4.1
		extremeWingCfgDhcpSvrPoolEntry OBJECT-TYPE
			SYNTAX ExtremeWingCfgDhcpSvrPoolEntry
			MAX-ACCESS not-accessible
			STATUS current
			DESCRIPTION
				"An entry in the table."
			INDEX { extremeWingCfgDhcpSvrName, extremeWingCfgDhcpSvrPoolName }
			::= { extremeWingCfgDhcpSvrPoolTable 1 }

		
		ExtremeWingCfgDhcpSvrPoolEntry ::=
			SEQUENCE { 
				extremeWingCfgDhcpSvrPoolName
					ExtremeWingIdentifier,
				extremeWingCfgDhcpSvrPoolNetwork
					IpAddress,
				extremeWingCfgDhcpSvrPoolDomainName
					DisplayString,
				extremeWingCfgDhcpSvrPoolNetbiosNodeType
					DisplayString,
				extremeWingCfgDhcpSvrPoolBootfile
					DisplayString,
				extremeWingCfgDhcpSvrPoolLeaseTime
					Unsigned32,
				extremeWingCfgDhcpSvrPoolBootpNextServer
					DisplayString,
				extremeWingCfgDhcpSvrPoolUpdateDns
					DisplayString,
				extremeWingCfgDhcpSvrPoolDdnsDomainName
					DisplayString,
				extremeWingCfgDhcpSvrPoolDdnsTtl
					Unsigned32,
				extremeWingCfgDhcpSvrPoolDdnsMultiUserClass
					TruthValue,
				extremeWingCfgDhcpSvrPoolUnicastEnable
					TruthValue
			 }

		-- 1.3.6.1.4.1.1916.2.131.50.1.3.15.4.1.1
		extremeWingCfgDhcpSvrPoolName OBJECT-TYPE
			SYNTAX ExtremeWingIdentifier
			MAX-ACCESS read-only
			STATUS current
			DESCRIPTION
				"Name of the IP pool from which IP addresses can be issued to
				DHCP client requests.
				
				XPath: /extremeWing-config/dhcp_server_policy[name=key1]/dhcp_pools[name=key2]/name"
			::= { extremeWingCfgDhcpSvrPoolEntry 1 }

		
		-- 1.3.6.1.4.1.1916.2.131.50.1.3.15.4.1.3
		extremeWingCfgDhcpSvrPoolNetwork OBJECT-TYPE
			SYNTAX IpAddress
			MAX-ACCESS read-write
			STATUS current
			DESCRIPTION
				"Network address for the clients.
				
				XPath: /extremeWing-config/dhcp_server_policy[name=key1]/dhcp_pools[name=key2]/network"
			::= { extremeWingCfgDhcpSvrPoolEntry 3 }

		
		-- 1.3.6.1.4.1.1916.2.131.50.1.3.15.4.1.4
		extremeWingCfgDhcpSvrPoolDomainName OBJECT-TYPE
			SYNTAX DisplayString (SIZE (1..255))
			MAX-ACCESS read-write
			STATUS current
			DESCRIPTION
				"
				
				XPath: /extremeWing-config/dhcp_server_policy[name=key1]/dhcp_pools[name=key2]/domain_name"
			::= { extremeWingCfgDhcpSvrPoolEntry 4 }

		
		-- 1.3.6.1.4.1.1916.2.131.50.1.3.15.4.1.5
		extremeWingCfgDhcpSvrPoolNetbiosNodeType OBJECT-TYPE
			SYNTAX DisplayString
			MAX-ACCESS read-write
			STATUS current
			DESCRIPTION
				"
				Values:
				none
				broadcast
				peer-to-peer
				mixed
				hybrid
				
				XPath: /extremeWing-config/dhcp_server_policy[name=key1]/dhcp_pools[name=key2]/netbios_node_type"
			DEFVAL { "undefined" }
			::= { extremeWingCfgDhcpSvrPoolEntry 5 }

		
		-- 1.3.6.1.4.1.1916.2.131.50.1.3.15.4.1.6
		extremeWingCfgDhcpSvrPoolBootfile OBJECT-TYPE
			SYNTAX DisplayString
			MAX-ACCESS read-write
			STATUS current
			DESCRIPTION
				"
				
				XPath: /extremeWing-config/dhcp_server_policy[name=key1]/dhcp_pools[name=key2]/bootfile"
			::= { extremeWingCfgDhcpSvrPoolEntry 6 }

		
		-- 1.3.6.1.4.1.1916.2.131.50.1.3.15.4.1.7
		extremeWingCfgDhcpSvrPoolLeaseTime OBJECT-TYPE
			SYNTAX Unsigned32 (1..31622399)
			UNITS "seconds"
			MAX-ACCESS read-write
			STATUS current
			DESCRIPTION
				"The time an IP address is reserved for re-connection after
				its last use.  Address lease time ranges from 1 second to
				1 year (or infinite if unset).
				
				XPath: /extremeWing-config/dhcp_server_policy[name=key1]/dhcp_pools[name=key2]/lease_time"
			DEFVAL { 86400 }
			::= { extremeWingCfgDhcpSvrPoolEntry 7 }

		
		-- 1.3.6.1.4.1.1916.2.131.50.1.3.15.4.1.8
		extremeWingCfgDhcpSvrPoolBootpNextServer OBJECT-TYPE
			SYNTAX DisplayString
			MAX-ACCESS read-write
			STATUS current
			DESCRIPTION
				"Next server in the boot process.
				
				XPath: /extremeWing-config/dhcp_server_policy[name=key1]/dhcp_pools[name=key2]/bootp_next_server"
			::= { extremeWingCfgDhcpSvrPoolEntry 8 }

		
		-- 1.3.6.1.4.1.1916.2.131.50.1.3.15.4.1.9
		extremeWingCfgDhcpSvrPoolUpdateDns OBJECT-TYPE
			SYNTAX DisplayString
			MAX-ACCESS read-write
			STATUS current
			DESCRIPTION
				"
				Values:
				noUpdate
				serverUpdate
				clientUpdate
				
				XPath: /extremeWing-config/dhcp_server_policy[name=key1]/dhcp_pools[name=key2]/update_dns"
			DEFVAL { "noUpdate" }
			::= { extremeWingCfgDhcpSvrPoolEntry 9 }

		
		-- 1.3.6.1.4.1.1916.2.131.50.1.3.15.4.1.10
		extremeWingCfgDhcpSvrPoolDdnsDomainName OBJECT-TYPE
			SYNTAX DisplayString
			MAX-ACCESS read-write
			STATUS current
			DESCRIPTION
				"Domain name used for DDNS Updates.
				
				XPath: /extremeWing-config/dhcp_server_policy[name=key1]/dhcp_pools[name=key2]/ddns_domain_name"
			::= { extremeWingCfgDhcpSvrPoolEntry 10 }

		
		-- 1.3.6.1.4.1.1916.2.131.50.1.3.15.4.1.11
		extremeWingCfgDhcpSvrPoolDdnsTtl OBJECT-TYPE
			SYNTAX Unsigned32 (1..864000)
			MAX-ACCESS read-write
			STATUS current
			DESCRIPTION
				"Time-to-Live (TTL) value used for DDNS updates.
				
				XPath: /extremeWing-config/dhcp_server_policy[name=key1]/dhcp_pools[name=key2]/ddns_ttl"
			::= { extremeWingCfgDhcpSvrPoolEntry 11 }

		
		-- 1.3.6.1.4.1.1916.2.131.50.1.3.15.4.1.12
		extremeWingCfgDhcpSvrPoolDdnsMultiUserClass OBJECT-TYPE
			SYNTAX TruthValue
			MAX-ACCESS read-write
			STATUS current
			DESCRIPTION
				"Enable/disable DDNS multi user class.
				
				XPath: /extremeWing-config/dhcp_server_policy[name=key1]/dhcp_pools[name=key2]/ddns_multi_user_class"
			DEFVAL { false }
			::= { extremeWingCfgDhcpSvrPoolEntry 12 }

		
		-- 1.3.6.1.4.1.1916.2.131.50.1.3.15.4.1.13
		extremeWingCfgDhcpSvrPoolUnicastEnable OBJECT-TYPE
			SYNTAX TruthValue
			MAX-ACCESS read-write
			STATUS current
			DESCRIPTION
				"Enable unicast for DHCP Offer and ACK.
				
				XPath: /extremeWing-config/dhcp_server_policy[name=key1]/dhcp_pools[name=key2]/unicast_enable"
			DEFVAL { false }
			::= { extremeWingCfgDhcpSvrPoolEntry 13 }


		-- 1.3.6.1.4.1.1916.2.131.50.1.3.15.10
		extremeWingCfgDhcpSvrActCriteriaTable OBJECT-TYPE
			SYNTAX SEQUENCE OF ExtremeWingCfgDhcpSvrActCriteriaEntry
			MAX-ACCESS not-accessible
			STATUS current
			DESCRIPTION
				"Description."
			::= { extremeWingCfgDhcpSvr 10 }

		
		-- 1.3.6.1.4.1.1916.2.131.50.1.3.15.10.1
		extremeWingCfgDhcpSvrActCriteriaEntry OBJECT-TYPE
			SYNTAX ExtremeWingCfgDhcpSvrActCriteriaEntry
			MAX-ACCESS not-accessible
			STATUS current
			DESCRIPTION
				"Description."
			INDEX { extremeWingCfgDhcpSvrName }
			::= { extremeWingCfgDhcpSvrActCriteriaTable 1 }

		
		ExtremeWingCfgDhcpSvrActCriteriaEntry ::=
			SEQUENCE { 
				extremeWingCfgDhcpSvrActCriteriaCriteria
					DisplayString
			 }

		-- 1.3.6.1.4.1.1916.2.131.50.1.3.15.10.1.1
		extremeWingCfgDhcpSvrActCriteriaCriteria OBJECT-TYPE
			SYNTAX DisplayString
			MAX-ACCESS read-write
			STATUS current
			DESCRIPTION
				"Criteria to allow dhcp deamon to run
				vrrp-master
				cluster-master
				rf-domain-manager
				 	
				XPath: /extremeWing-config/dhcp_server_policy[name=key1]/dhcp_server_activation_criteria/criteria"
			::= { extremeWingCfgDhcpSvrActCriteriaEntry 1 }

		
		
-- /extremeWing-config/profile
		-- 1.3.6.1.4.1.1916.2.131.50.1.3.16
		extremeWingCfgProf OBJECT IDENTIFIER ::= { extremeWingConfig 16 }

		
		-- 1.3.6.1.4.1.1916.2.131.50.1.3.16.1
		extremeWingCfgProfTable OBJECT-TYPE
			SYNTAX SEQUENCE OF ExtremeWingCfgProfEntry
			MAX-ACCESS not-accessible
			STATUS current
			DESCRIPTION
				"
				
				/extremeWing-config/profile"
			::= { extremeWingCfgProf 1 }

		
		-- 1.3.6.1.4.1.1916.2.131.50.1.3.16.1.1
		extremeWingCfgProfEntry OBJECT-TYPE
			SYNTAX ExtremeWingCfgProfEntry
			MAX-ACCESS not-accessible
			STATUS current
			DESCRIPTION
				"An entry in the table."
			INDEX { extremeWingCfgProfName }
			::= { extremeWingCfgProfTable 1 }

		
		ExtremeWingCfgProfEntry ::=
			SEQUENCE { 
				extremeWingCfgProfName
					ExtremeWingIdentifier,
				extremeWingCfgProfType
					DisplayString,
				extremeWingCfgProfDomainLookup
					TruthValue,
				extremeWingCfgProfDomainName
					DisplayString,
				extremeWingCfgProfArpTimeout
					Unsigned32,
				extremeWingCfgProfApIpAddr
					IpAddress,
				extremeWingCfgProfAutoConfUpdate
					TruthValue,
				extremeWingCfgProfAutoFwUpdate
					TruthValue,
				extremeWingCfgProfAutoupgradeCount
					Unsigned32,
				extremeWingCfgProfServiceWatchdog
					TruthValue,
				extremeWingCfgProfRadiusServerPolicy
					ExtremeWingIdentifier,
				extremeWingCfgProfDhcpServerPolicy
					ExtremeWingIdentifier,
				extremeWingCfgProfManagementPolicy
					ExtremeWingIdentifier,
				extremeWingCfgProfFirewallPolicy
					ExtremeWingIdentifier,
				extremeWingCfgProfAdvancedWipsPolicy
					ExtremeWingIdentifier,
				extremeWingCfgProfRolePolicy
					ExtremeWingIdentifier,
				extremeWingCfgProfAdoptionPolicy
					ExtremeWingIdentifier,
				extremeWingCfgProfBridgingPolicy
					ExtremeWingIdentifier,
				extremeWingCfgProfEventSystemPolicy
					ExtremeWingIdentifier,
				extremeWingCfgProfRoutingPolicy
					ExtremeWingIdentifier,
				extremeWingCfgProfRfDomainMgrCapable
					TruthValue,
				extremeWingCfgProfRfDomainMgrPriority
					Unsigned32,
				extremeWingCfgProfDhcpcSendHostname
					TruthValue,
				extremeWingCfgProfDhcpcPersistentLease
					TruthValue,
				extremeWingCfgProfDnsServerForward
					TruthValue,
				extremeWingCfgProfBridgeAgingTime
					Unsigned32,
				extremeWingCfgProfLogging
					TruthValue,
				extremeWingCfgProfAggregationTime
					Unsigned32,
				extremeWingCfgProfConsole
					DisplayString,
				extremeWingCfgProfBuffered
					DisplayString,
				extremeWingCfgProfSyslog
					DisplayString,
				extremeWingCfgProfFacility
					DisplayString,
				extremeWingCfgProfEvents
					TruthValue,
				extremeWingCfgProfEventsForward
					TruthValue,
                                extremeWingCfgProfLed
                                        TruthValue,
				extremeWingCfgProfRemoteLogging
					DisplayString,
				extremeWingCfgProfPowerConfig3afOption
					DisplayString,
				extremeWingCfgProfPowerConfig3atOption
					DisplayString,
				extremeWingCfgProfPowerConfigMode
					DisplayString,
				extremeWingCfgProfCriticalResourcePolicy
					ExtremeWingIdentifier,
                                extremeWingCfgProfControllerApSupported
                                        TruthValue,
				extremeWingCfgProfControllerVlan
					Unsigned32,
				extremeWingCfgProfControllerGroup
					DisplayString,
				extremeWingCfgProfPreferredControllerGroup
					DisplayString,
				extremeWingCfgProfIpRouting
					TruthValue,
				extremeWingCfgProfLearnStagingConfig
					TruthValue,
				extremeWingCfgProfTunnelController
					DisplayString,
				extremeWingCfgProfPreferredTunnelController
					DisplayString,
				extremeWingCfgProfDot1xSysAuthCtrl
					TruthValue,
				extremeWingCfgProfDot1xGuestVlanCtrl
					TruthValue,
				extremeWingCfgProfDot1xAaaPolicy
					ExtremeWingIdentifier,
				extremeWingCfgProfRaidAlarmEnable
					TruthValue
			 }

		-- 1.3.6.1.4.1.1916.2.131.50.1.3.16.1.1.1
		extremeWingCfgProfName OBJECT-TYPE
			SYNTAX ExtremeWingIdentifier
			MAX-ACCESS read-only
			STATUS current
			DESCRIPTION
				"
				
				XPath: /extremeWing-config/profile[name=key1]/name"
			::= { extremeWingCfgProfEntry 1 }

		
		-- 1.3.6.1.4.1.1916.2.131.50.1.3.16.1.1.3
		extremeWingCfgProfType OBJECT-TYPE
			SYNTAX DisplayString
			MAX-ACCESS read-write
			STATUS current
			DESCRIPTION
				"
				Values:
				NX9000
				WM3700
				WM3600
				WM3400
				AP4700
				AP4600
				AP4021
				AP4521
				AP4511
				AP4532
				
				XPath: /extremeWing-config/profile[name=key1]/type"
			::= { extremeWingCfgProfEntry 3 }

		
		-- 1.3.6.1.4.1.1916.2.131.50.1.3.16.1.1.4
		extremeWingCfgProfDomainLookup OBJECT-TYPE
			SYNTAX TruthValue
			MAX-ACCESS read-write
			STATUS current
			DESCRIPTION
				"Domain name lookup (DNS resolution) services
				
				XPath: /extremeWing-config/profile[name=key1]/domain_lookup"
			DEFVAL { true }
			::= { extremeWingCfgProfEntry 4 }

		
		-- 1.3.6.1.4.1.1916.2.131.50.1.3.16.1.1.5
		extremeWingCfgProfDomainName OBJECT-TYPE
			SYNTAX DisplayString (SIZE (0..64))
			MAX-ACCESS read-write
			STATUS current
			DESCRIPTION
				"Default domain-name to be used when resolving DNS names
				
				XPath: /extremeWing-config/profile[name=key1]/domain_name"
			DEFVAL { "" }
			::= { extremeWingCfgProfEntry 5 }

		
		-- 1.3.6.1.4.1.1916.2.131.50.1.3.16.1.1.6
		extremeWingCfgProfArpTimeout OBJECT-TYPE
			SYNTAX Unsigned32 (15..86400)
			UNITS "seconds"
			MAX-ACCESS read-write
			STATUS current
			DESCRIPTION
				"ARP entry timeout
				
				XPath: /extremeWing-config/profile[name=key1]/arp_timeout"
			DEFVAL { 3600 }
			::= { extremeWingCfgProfEntry 6 }

		
		-- 1.3.6.1.4.1.1916.2.131.50.1.3.16.1.1.7
		extremeWingCfgProfApIpAddr OBJECT-TYPE
			SYNTAX IpAddress 
			MAX-ACCESS read-write
			STATUS current
			DESCRIPTION
				"Ip address for legacy AP adoption.
				
				XPath: /extremeWing-config/profile[name=key1]/ap_ip_address"
			::= { extremeWingCfgProfEntry 7 }

		
		-- 1.3.6.1.4.1.1916.2.131.50.1.3.16.1.1.8
		extremeWingCfgProfAutoConfUpdate OBJECT-TYPE
			SYNTAX TruthValue
			MAX-ACCESS read-write
			STATUS current
			DESCRIPTION
				"Autoinstall configuration update from external location based
				on DHCP options.
				
				XPath: /extremeWing-config/profile[name=key1]/auto_conf_update"
			DEFVAL { false }
			::= { extremeWingCfgProfEntry 8 }

		
		-- 1.3.6.1.4.1.1916.2.131.50.1.3.16.1.1.9
		extremeWingCfgProfAutoFwUpdate OBJECT-TYPE
			SYNTAX TruthValue
			MAX-ACCESS read-write
			STATUS current
			DESCRIPTION
				"Autoinstall firmware upgrade from external location based on
				DHCP options.
				
				XPath: /extremeWing-config/profile[name=key1]/auto_fw_update"
			DEFVAL { false }
			::= { extremeWingCfgProfEntry 9 }

		
		-- 1.3.6.1.4.1.1916.2.131.50.1.3.16.1.1.11
		extremeWingCfgProfAutoupgradeCount OBJECT-TYPE
			SYNTAX Unsigned32 (1..20)
			UNITS "APs"
			MAX-ACCESS read-write
			STATUS current
			DESCRIPTION
				"The number of APs that can be upgraded concurrently.
				
				XPath: /extremeWing-config/profile[name=key1]/autoupgrade_count"
			DEFVAL { 10 }
			::= { extremeWingCfgProfEntry 11 }

		
		-- 1.3.6.1.4.1.1916.2.131.50.1.3.16.1.1.12
		extremeWingCfgProfServiceWatchdog OBJECT-TYPE
			SYNTAX TruthValue
			MAX-ACCESS read-write
			STATUS current
			DESCRIPTION
				"
				
				XPath: /extremeWing-config/profile[name=key1]/service_watchdog"
			DEFVAL { true }
			::= { extremeWingCfgProfEntry 12 }

		
		-- 1.3.6.1.4.1.1916.2.131.50.1.3.16.1.1.13
		extremeWingCfgProfRadiusServerPolicy OBJECT-TYPE
			SYNTAX ExtremeWingIdentifier
			MAX-ACCESS read-write
			STATUS current
			DESCRIPTION
				"
				
				XPath: /extremeWing-config/profile[name=key1]/radius_server_policy"
			::= { extremeWingCfgProfEntry 13 }

		
		-- 1.3.6.1.4.1.1916.2.131.50.1.3.16.1.1.14
		extremeWingCfgProfDhcpServerPolicy OBJECT-TYPE
			SYNTAX ExtremeWingIdentifier
			MAX-ACCESS read-write
			STATUS current
			DESCRIPTION
				"
				
				XPath: /extremeWing-config/profile[name=key1]/dhcp_server_policy"
			::= { extremeWingCfgProfEntry 14 }

		
		-- 1.3.6.1.4.1.1916.2.131.50.1.3.16.1.1.15
		extremeWingCfgProfManagementPolicy OBJECT-TYPE
			SYNTAX ExtremeWingIdentifier
			MAX-ACCESS read-write
			STATUS current
			DESCRIPTION
				"
				
				XPath: /extremeWing-config/profile[name=key1]/management_policy"
			::= { extremeWingCfgProfEntry 15 }

		
		-- 1.3.6.1.4.1.1916.2.131.50.1.3.16.1.1.16
		extremeWingCfgProfFirewallPolicy OBJECT-TYPE
			SYNTAX ExtremeWingIdentifier
			MAX-ACCESS read-write
			STATUS current
			DESCRIPTION
				"
				
				XPath: /extremeWing-config/profile[name=key1]/firewall_policy"
			::= { extremeWingCfgProfEntry 16 }

		
		-- 1.3.6.1.4.1.1916.2.131.50.1.3.16.1.1.17
		extremeWingCfgProfAdvancedWipsPolicy OBJECT-TYPE
			SYNTAX ExtremeWingIdentifier
			MAX-ACCESS read-write
			STATUS current
			DESCRIPTION
				"
				
				XPath: /extremeWing-config/profile[name=key1]/advanced_wips_policy"
			::= { extremeWingCfgProfEntry 17 }

		
		-- 1.3.6.1.4.1.1916.2.131.50.1.3.16.1.1.18
		extremeWingCfgProfRolePolicy OBJECT-TYPE
			SYNTAX ExtremeWingIdentifier
			MAX-ACCESS read-write
			STATUS current
			DESCRIPTION
				"
				
				XPath: /extremeWing-config/profile[name=key1]/role_policy"
			::= { extremeWingCfgProfEntry 18 }

		
		-- 1.3.6.1.4.1.1916.2.131.50.1.3.16.1.1.19
		extremeWingCfgProfAdoptionPolicy OBJECT-TYPE
			SYNTAX ExtremeWingIdentifier
			MAX-ACCESS read-write
			STATUS current
			DESCRIPTION
				"
				
				XPath: /extremeWing-config/profile[name=key1]/adoption_policy"
			::= { extremeWingCfgProfEntry 19 }

		
		-- 1.3.6.1.4.1.1916.2.131.50.1.3.16.1.1.20
		extremeWingCfgProfBridgingPolicy OBJECT-TYPE
			SYNTAX ExtremeWingIdentifier
			MAX-ACCESS read-write
			STATUS current
			DESCRIPTION
				"
				
				XPath: /extremeWing-config/profile[name=key1]/bridging_policy"
			::= { extremeWingCfgProfEntry 20 }

		
		-- 1.3.6.1.4.1.1916.2.131.50.1.3.16.1.1.21
		extremeWingCfgProfEventSystemPolicy OBJECT-TYPE
			SYNTAX ExtremeWingIdentifier
			MAX-ACCESS read-write
			STATUS current
			DESCRIPTION
				"
				
				XPath: /extremeWing-config/profile[name=key1]/event_system_policy"
			::= { extremeWingCfgProfEntry 21 }

		
		-- 1.3.6.1.4.1.1916.2.131.50.1.3.16.1.1.22
		extremeWingCfgProfRoutingPolicy OBJECT-TYPE
			SYNTAX ExtremeWingIdentifier
			MAX-ACCESS read-write
			STATUS current
			DESCRIPTION
				"
				
				XPath: /extremeWing-config/profile[name=key1]/routing_policy"
			::= { extremeWingCfgProfEntry 22 }

		
		-- 1.3.6.1.4.1.1916.2.131.50.1.3.16.1.1.23
		extremeWingCfgProfRfDomainMgrCapable OBJECT-TYPE
			SYNTAX TruthValue
			MAX-ACCESS read-write
			STATUS current
			DESCRIPTION
				"whether this device is capable of being the rf-domain manager
				within a particular rf-domain
				
				XPath: /extremeWing-config/profile[name=key1]/rf_domain_mgr_capable"
			DEFVAL { true }
			::= { extremeWingCfgProfEntry 23 }

		
		-- 1.3.6.1.4.1.1916.2.131.50.1.3.16.1.1.24
		extremeWingCfgProfRfDomainMgrPriority OBJECT-TYPE
			SYNTAX Unsigned32 (1..255)
			MAX-ACCESS read-write
			STATUS current
			DESCRIPTION
				"The priority of this device compared to others in becoming
				an rf-domain manager. A larger value indicates a
				higher priority is given to the device in
				the rf-domain manager election process
				
				XPath: /extremeWing-config/profile[name=key1]/rf_domain_mgr_priority"
			::= { extremeWingCfgProfEntry 24 }

		
		-- 1.3.6.1.4.1.1916.2.131.50.1.3.16.1.1.25
		extremeWingCfgProfDhcpcSendHostname OBJECT-TYPE
			SYNTAX TruthValue
			MAX-ACCESS read-write
			STATUS current
			DESCRIPTION
				"Include hostname in DHCP request.
				
				XPath: /extremeWing-config/profile[name=key1]/dhcpc_send_hostname"
			DEFVAL { true }
			::= { extremeWingCfgProfEntry 25 }

		
		-- 1.3.6.1.4.1.1916.2.131.50.1.3.16.1.1.26
		extremeWingCfgProfDhcpcPersistentLease OBJECT-TYPE
			SYNTAX TruthValue
			MAX-ACCESS read-write
			STATUS current
			DESCRIPTION
				"Retain last lease across reboot if DHCP server is unreachable
				
				XPath: /extremeWing-config/profile[name=key1]/dhcpc_persistent_lease"
			DEFVAL { true }
			::= { extremeWingCfgProfEntry 26 }

		
		-- 1.3.6.1.4.1.1916.2.131.50.1.3.16.1.1.27
		extremeWingCfgProfDnsServerForward OBJECT-TYPE
			SYNTAX TruthValue
			MAX-ACCESS read-write
			STATUS current
			DESCRIPTION
				"
				
				XPath: /extremeWing-config/profile[name=key1]/dns_server_forward"
			DEFVAL { false }
			::= { extremeWingCfgProfEntry 27 }

		
		-- 1.3.6.1.4.1.1916.2.131.50.1.3.16.1.1.28
		extremeWingCfgProfBridgeAgingTime OBJECT-TYPE
			SYNTAX Unsigned32 (0 | 10..1000000)
			UNITS "seconds"
			MAX-ACCESS read-write
			STATUS current
			DESCRIPTION
				"Aging time from 10 sec to 1000000 sec or disabled (when value=0).
				
				XPath: /extremeWing-config/profile[name=key1]/bridge_aging_time"
			DEFVAL { 300 }
			::= { extremeWingCfgProfEntry 28 }

		
		-- 1.3.6.1.4.1.1916.2.131.50.1.3.16.1.1.29
		extremeWingCfgProfLogging OBJECT-TYPE
			SYNTAX TruthValue
			MAX-ACCESS read-write
			STATUS current
			DESCRIPTION
				"Enable logging of system messages.
				
				XPath: /extremeWing-config/profile[name=key1]/logging"
			DEFVAL { false }
			::= { extremeWingCfgProfEntry 29 }

		
		-- 1.3.6.1.4.1.1916.2.131.50.1.3.16.1.1.30
		extremeWingCfgProfAggregationTime OBJECT-TYPE
			SYNTAX Unsigned32 (0..60)
			UNITS "seconds"
			MAX-ACCESS read-write
			STATUS current
			DESCRIPTION
				"Set number of seconds for aggregating repeated messages.
				
				XPath: /extremeWing-config/profile[name=key1]/aggregation_time"
			DEFVAL { 0 }
			::= { extremeWingCfgProfEntry 30 }

		
		-- 1.3.6.1.4.1.1916.2.131.50.1.3.16.1.1.31
		extremeWingCfgProfConsole OBJECT-TYPE
			SYNTAX DisplayString
			MAX-ACCESS read-write
			STATUS current
			DESCRIPTION
				"Set console logging level.
				
				Values:
				emergencies
				alerts
				critical
				errors
				warnings
				notifications
				informational
				debugging
				none
				
				XPath: /extremeWing-config/profile[name=key1]/console"
			DEFVAL { "warnings" }
			::= { extremeWingCfgProfEntry 31 }

		
		-- 1.3.6.1.4.1.1916.2.131.50.1.3.16.1.1.32
		extremeWingCfgProfBuffered OBJECT-TYPE
			SYNTAX DisplayString
			MAX-ACCESS read-write
			STATUS current
			DESCRIPTION
				"Set buffered logging level.
				
				Values:
				emergencies
				alerts
				critical
				errors
				warnings
				notifications
				informational
				debugging
				none
				
				XPath: /extremeWing-config/profile[name=key1]/buffered"
			DEFVAL { "warnings" }
			::= { extremeWingCfgProfEntry 32 }

		
		-- 1.3.6.1.4.1.1916.2.131.50.1.3.16.1.1.33
		extremeWingCfgProfSyslog OBJECT-TYPE
			SYNTAX DisplayString
			MAX-ACCESS read-write
			STATUS current
			DESCRIPTION
				"Set syslog logging level.
				
				Values:
				emergencies
				alerts
				critical
				errors
				warnings
				notifications
				informational
				debugging
				none
				
				XPath: /extremeWing-config/profile[name=key1]/syslog"
			DEFVAL { "warnings" }
			::= { extremeWingCfgProfEntry 33 }

		
		-- 1.3.6.1.4.1.1916.2.131.50.1.3.16.1.1.34
		extremeWingCfgProfFacility OBJECT-TYPE
			SYNTAX DisplayString
			MAX-ACCESS read-write
			STATUS current
			DESCRIPTION
				"Syslog facility for log messages sent to syslog server.
				
				Values:
				local0
				local1
				local2
				local3
				local4
				local5
				local6
				local7
				
				XPath: /extremeWing-config/profile[name=key1]/facility"
			DEFVAL { "local7" }
			::= { extremeWingCfgProfEntry 34 }

		
		-- 1.3.6.1.4.1.1916.2.131.50.1.3.16.1.1.35
		extremeWingCfgProfEvents OBJECT-TYPE
			SYNTAX TruthValue
			MAX-ACCESS read-write
			STATUS current
			DESCRIPTION
				"Enable generation of system events.
				
				XPath: /extremeWing-config/profile[name=key1]/events"
			DEFVAL { true }
			::= { extremeWingCfgProfEntry 35 }

		
		-- 1.3.6.1.4.1.1916.2.131.50.1.3.16.1.1.36
		extremeWingCfgProfEventsForward OBJECT-TYPE
			SYNTAX TruthValue
			MAX-ACCESS read-write
			STATUS current
			DESCRIPTION
				"Enable forwarding of system events to a controller or
				cluster member.
				
				XPath: /extremeWing-config/profile[name=key1]/events_forward"
			DEFVAL { true }
			::= { extremeWingCfgProfEntry 36 }

		
		-- 1.3.6.1.4.1.1916.2.131.50.1.3.16.1.1.37
		extremeWingCfgProfLed OBJECT-TYPE
			SYNTAX TruthValue
			MAX-ACCESS read-write
			STATUS current
			DESCRIPTION
				"Turn on/off LEDs on the AP.
				
				XPath: /extremeWing-config/profile[name=key1]/led"
			DEFVAL { true }
			::= { extremeWingCfgProfEntry 37 }

		
		
		-- 1.3.6.1.4.1.1916.2.131.50.1.3.16.1.1.38
		extremeWingCfgProfRemoteLogging OBJECT-TYPE
			SYNTAX DisplayString
			MAX-ACCESS read-write
			STATUS current
			DESCRIPTION
				"Set logging level for forwarding of log messages to
				controller.
				
				Values:
				emergencies
				alerts
				critical
				errors
				warnings
				notifications
				informational
				debugging
				none
				
				XPath: /extremeWing-config/profile[name=key1]/remote_logging"
			DEFVAL { "errors" }
			::= { extremeWingCfgProfEntry 38 }

		
		-- 1.3.6.1.4.1.1916.2.131.50.1.3.16.1.1.39
		extremeWingCfgProfPowerConfig3afOption OBJECT-TYPE
			SYNTAX DisplayString
			MAX-ACCESS read-write
			STATUS current
			DESCRIPTION
				"
				Values:
				range
				throughput
				
				XPath: /extremeWing-config/profile[name=key1]/power_config_3af_option"
			DEFVAL { "throughput" }
			::= { extremeWingCfgProfEntry 39 }

		
		-- 1.3.6.1.4.1.1916.2.131.50.1.3.16.1.1.40
		extremeWingCfgProfPowerConfig3atOption OBJECT-TYPE
			SYNTAX DisplayString
			MAX-ACCESS read-write
			STATUS current
			DESCRIPTION
				"
				Values:
				range
				throughput
				
				XPath: /extremeWing-config/profile[name=key1]/power_config_3at_option"
			DEFVAL { "throughput" }
			::= { extremeWingCfgProfEntry 40 }

		
		-- 1.3.6.1.4.1.1916.2.131.50.1.3.16.1.1.41
		extremeWingCfgProfPowerConfigMode OBJECT-TYPE
			SYNTAX DisplayString
			MAX-ACCESS read-write
			STATUS current
			DESCRIPTION
				"If power mode is 3af then ap will come up in 3af config
				no matter what power level is.
				
				Values:
				auto
				3af
				
				XPath: /extremeWing-config/profile[name=key1]/power_config_mode"
			DEFVAL { "auto" }
			::= { extremeWingCfgProfEntry 41 }

		
		-- 1.3.6.1.4.1.1916.2.131.50.1.3.16.1.1.42
		extremeWingCfgProfCriticalResourcePolicy OBJECT-TYPE
			SYNTAX ExtremeWingIdentifier
			MAX-ACCESS read-write
			STATUS current
			DESCRIPTION
				"
				
				XPath: /extremeWing-config/profile[name=key1]/critical_resource_policy"
			::= { extremeWingCfgProfEntry 42 }

		
		-- 1.3.6.1.4.1.1916.2.131.50.1.3.16.1.1.43
		extremeWingCfgProfControllerApSupported OBJECT-TYPE
			SYNTAX TruthValue
			MAX-ACCESS read-write
			STATUS current
			DESCRIPTION
				"Controller-AP supported on this device when true.
				
				XPath: /extremeWing-config/profile[name=key1]/controller_ap_supported"
			DEFVAL { false }
			::= { extremeWingCfgProfEntry 43 }

		
		-- 1.3.6.1.4.1.1916.2.131.50.1.3.16.1.1.44
		extremeWingCfgProfControllerVlan OBJECT-TYPE
			SYNTAX Unsigned32 (1..4094)
			MAX-ACCESS read-write
			STATUS current
			DESCRIPTION
				"VLAN on which a controller is reachable
				
				XPath: /extremeWing-config/profile[name=key1]/controller_vlan"
			::= { extremeWingCfgProfEntry 44 }

		
		-- 1.3.6.1.4.1.1916.2.131.50.1.3.16.1.1.45
		extremeWingCfgProfControllerGroup OBJECT-TYPE
			SYNTAX DisplayString (SIZE (64))
			MAX-ACCESS read-write
			STATUS current
			DESCRIPTION
				"Controller group this controller belongs to
				
				XPath: /extremeWing-config/profile[name=key1]/controller_group"
			::= { extremeWingCfgProfEntry 45 }

		
		-- 1.3.6.1.4.1.1916.2.131.50.1.3.16.1.1.46
		extremeWingCfgProfPreferredControllerGroup OBJECT-TYPE
			SYNTAX DisplayString (SIZE (64))
			MAX-ACCESS read-write
			STATUS current
			DESCRIPTION
				"Controller group this system will prefer for adoption
				
				XPath: /extremeWing-config/profile[name=key1]/preferred_controller_group"
			::= { extremeWingCfgProfEntry 46 }

		
		-- 1.3.6.1.4.1.1916.2.131.50.1.3.16.1.1.47
		extremeWingCfgProfIpRouting OBJECT-TYPE
			SYNTAX TruthValue
			MAX-ACCESS read-write
			STATUS current
			DESCRIPTION
				"IP Routing
				
				XPath: /extremeWing-config/profile[name=key1]/ip_routing"
			DEFVAL { true }
			::= { extremeWingCfgProfEntry 47 }

		
		-- 1.3.6.1.4.1.1916.2.131.50.1.3.16.1.1.48
		extremeWingCfgProfLearnStagingConfig OBJECT-TYPE
			SYNTAX TruthValue
			MAX-ACCESS read-write
			STATUS current
			DESCRIPTION
				"Learn and save network configuration of new devices that
				come for adoption
				
				XPath: /extremeWing-config/profile[name=key1]/learn_staging_config"
			DEFVAL { true }
			::= { extremeWingCfgProfEntry 48 }

		
		-- 1.3.6.1.4.1.1916.2.131.50.1.3.16.1.1.49
		extremeWingCfgProfTunnelController OBJECT-TYPE
			SYNTAX DisplayString
			MAX-ACCESS read-write
			STATUS current
			DESCRIPTION
				"Name of this tunneled-wlan-controller.
				
				XPath: /extremeWing-config/profile[name=key1]/tunnel_controller"
			::= { extremeWingCfgProfEntry 49 }

		
		-- 1.3.6.1.4.1.1916.2.131.50.1.3.16.1.1.50
		extremeWingCfgProfPreferredTunnelController OBJECT-TYPE
			SYNTAX DisplayString
			MAX-ACCESS read-write
			STATUS current
			DESCRIPTION
				"Controller this AP will prefer to tunnel tunnelled-wlan a.k.a extended-vlan traffic to.
				
				XPath: /extremeWing-config/profile[name=key1]/preferred_tunnel_controller"
			::= { extremeWingCfgProfEntry 50 }

		
		-- 1.3.6.1.4.1.1916.2.131.50.1.3.16.1.1.51
		extremeWingCfgProfDot1xSysAuthCtrl OBJECT-TYPE
			SYNTAX TruthValue
			MAX-ACCESS read-write
			STATUS current
			DESCRIPTION
				"Globally enable 802.1x authentication
				
				XPath: /extremeWing-config/profile[name=key1]/dot1x_sys_auth_ctrl"
			DEFVAL { false }
			::= { extremeWingCfgProfEntry 51 }

		
		-- 1.3.6.1.4.1.1916.2.131.50.1.3.16.1.1.52
		extremeWingCfgProfDot1xGuestVlanCtrl OBJECT-TYPE
			SYNTAX TruthValue
			MAX-ACCESS read-write
			STATUS current
			DESCRIPTION
				"Globally enable 802.1x guest vlans
				
				XPath: /extremeWing-config/profile[name=key1]/dot1x_guest_vlan_ctrl"
			DEFVAL { false }
			::= { extremeWingCfgProfEntry 52 }

		
		-- 1.3.6.1.4.1.1916.2.131.50.1.3.16.1.1.53
		extremeWingCfgProfDot1xAaaPolicy OBJECT-TYPE
			SYNTAX ExtremeWingIdentifier
			MAX-ACCESS read-write
			STATUS current
			DESCRIPTION
				"AAA Authentication policy for 802.1x Authentication
				
				XPath: /extremeWing-config/profile[name=key1]/dot1x_aaa_policy"
			::= { extremeWingCfgProfEntry 53 }

		-- 1.3.6.1.4.1.1916.2.131.50.1.3.16.1.1.55
		extremeWingCfgProfRaidAlarmEnable OBJECT-TYPE
			SYNTAX TruthValue
			MAX-ACCESS read-write
			STATUS current
			DESCRIPTION
				"The chassis alarm will sound on RAID degrade events.
				XPath: /extremeWing-config/profile[name=key1]/raid_alarm_enable"
			DEFVAL { true }
			::= { extremeWingCfgProfEntry 55 }

		
-- /extremeWing-config/profile/interface
		-- 1.3.6.1.4.1.1916.2.131.50.1.3.16.2
		extremeWingCfgProfIf OBJECT IDENTIFIER ::= { extremeWingCfgProf 2 }

		
		-- 1.3.6.1.4.1.1916.2.131.50.1.3.16.2.1
		extremeWingCfgProfIfTable OBJECT-TYPE
			SYNTAX SEQUENCE OF ExtremeWingCfgProfIfEntry
			MAX-ACCESS not-accessible
			STATUS current
			DESCRIPTION
				"
				
				/extremeWing-config/profile/interface"
			::= { extremeWingCfgProfIf 1 }

		
		-- 1.3.6.1.4.1.1916.2.131.50.1.3.16.2.1.1
		extremeWingCfgProfIfEntry OBJECT-TYPE
			SYNTAX ExtremeWingCfgProfIfEntry
			MAX-ACCESS not-accessible
			STATUS current
			DESCRIPTION
				"An entry in the table."
			INDEX { extremeWingCfgProfName, extremeWingCfgProfIfName }
			::= { extremeWingCfgProfIfTable 1 }

		
		ExtremeWingCfgProfIfEntry ::=
			SEQUENCE { 
				extremeWingCfgProfIfName
					ExtremeWingIdentifier,
				extremeWingCfgProfIfDescription
					DisplayString,
				extremeWingCfgProfIfType
					DisplayString,
				extremeWingCfgProfIfShutdown
					TruthValue,
				extremeWingCfgProfIfIpInAcl
					ExtremeWingIdentifier,
				extremeWingCfgProfIfMacInAcl
					ExtremeWingIdentifier
			 }

		-- 1.3.6.1.4.1.1916.2.131.50.1.3.16.2.1.1.1
		extremeWingCfgProfIfName OBJECT-TYPE
			SYNTAX ExtremeWingIdentifier
			MAX-ACCESS read-only
			STATUS current
			DESCRIPTION
				"
				
				XPath: /extremeWing-config/profile[name=key1]/interface[name=key2]/name"
			::= { extremeWingCfgProfIfEntry 1 }

		
		-- 1.3.6.1.4.1.1916.2.131.50.1.3.16.2.1.1.3
		extremeWingCfgProfIfDescription OBJECT-TYPE
			SYNTAX DisplayString
			MAX-ACCESS read-write
			STATUS current
			DESCRIPTION
				"
				
				XPath: /extremeWing-config/profile[name=key1]/interface[name=key2]/description"
			::= { extremeWingCfgProfIfEntry 3 }

		
		-- 1.3.6.1.4.1.1916.2.131.50.1.3.16.2.1.1.4
		extremeWingCfgProfIfType OBJECT-TYPE
			SYNTAX DisplayString
			MAX-ACCESS read-write
			STATUS current
			DESCRIPTION
				"Type of the network interface
				
				Values:
				ethernet
				vlan
				radio
				port_channel
				wwan
				
				XPath: /extremeWing-config/profile[name=key1]/interface[name=key2]/type"
			::= { extremeWingCfgProfIfEntry 4 }

		
		-- 1.3.6.1.4.1.1916.2.131.50.1.3.16.2.1.1.5
		extremeWingCfgProfIfShutdown OBJECT-TYPE
			SYNTAX TruthValue
			MAX-ACCESS read-write
			STATUS current
			DESCRIPTION
				"
				
				XPath: /extremeWing-config/profile[name=key1]/interface[name=key2]/shutdown"
			DEFVAL { false }
			::= { extremeWingCfgProfIfEntry 5 }

		
		-- 1.3.6.1.4.1.1916.2.131.50.1.3.16.2.1.1.6
		extremeWingCfgProfIfIpInAcl OBJECT-TYPE
			SYNTAX ExtremeWingIdentifier
			MAX-ACCESS read-write
			STATUS current
			DESCRIPTION
				"
				
				XPath: /extremeWing-config/profile[name=key1]/interface[name=key2]/ip_in_acl"
			::= { extremeWingCfgProfIfEntry 6 }

		
		-- 1.3.6.1.4.1.1916.2.131.50.1.3.16.2.1.1.7
		extremeWingCfgProfIfMacInAcl OBJECT-TYPE
			SYNTAX ExtremeWingIdentifier
			MAX-ACCESS read-write
			STATUS current
			DESCRIPTION
				"
				
				XPath: /extremeWing-config/profile[name=key1]/interface[name=key2]/mac_in_acl"
			::= { extremeWingCfgProfIfEntry 7 }

		
		-- 1.3.6.1.4.1.1916.2.131.50.1.3.16.2.2
		extremeWingCfgProfIfEthTable OBJECT-TYPE
			SYNTAX SEQUENCE OF ExtremeWingCfgProfIfEthEntry
			MAX-ACCESS not-accessible
			STATUS current
			DESCRIPTION
				"
				
				/extremeWing-config/profile/interface"
			::= { extremeWingCfgProfIf 2 }

		
		-- 1.3.6.1.4.1.1916.2.131.50.1.3.16.2.2.1
		extremeWingCfgProfIfEthEntry OBJECT-TYPE
			SYNTAX ExtremeWingCfgProfIfEthEntry
			MAX-ACCESS not-accessible
			STATUS current
			DESCRIPTION
				"An entry in the table."
			INDEX { extremeWingCfgProfName, extremeWingCfgProfIfName }
			::= { extremeWingCfgProfIfEthTable 1 }

		
		ExtremeWingCfgProfIfEthEntry ::=
			SEQUENCE { 
				extremeWingCfgProfIfEthSpeed
					DisplayString,
				extremeWingCfgProfIfEthDuplex
					DisplayString,
				extremeWingCfgProfIfEthSwitchportMode
					DisplayString,
				extremeWingCfgProfIfEthSwitchportNativeVlan
					Unsigned32,
				extremeWingCfgProfIfEthSwitchportNativeVlanTagged
					TruthValue,
				extremeWingCfgProfIfEthArpTrust
					TruthValue,
				extremeWingCfgProfIfEthDhcpTrust
					TruthValue,
				extremeWingCfgProfIfEthArpHeaderMismatchValidation
					TruthValue,
				extremeWingCfgProfIfEthQosTrustDscp
					TruthValue,
				extremeWingCfgProfIfEthQosTrust802dot1p
					TruthValue,
				extremeWingCfgProfIfEthStaticChannelGroup
					Unsigned32,
				extremeWingCfgProfIfEthPoeSupported
					TruthValue,
				extremeWingCfgProfIfEthPoePower
					TruthValue,
				extremeWingCfgProfIfEthPoeLimit
					Unsigned32,
				extremeWingCfgProfIfEthPoePriority
					DisplayString,
				extremeWingCfgProfIfEthDot1xSupported
					TruthValue,
				extremeWingCfgProfIfEthDot1xEnable
					TruthValue,
				extremeWingCfgProfIfEthDot1xUsername
					DisplayString,
				extremeWingCfgProfIfEthDot1xPassword
					DisplayString,
				extremeWingCfgProfIfEthCdpReceive
					TruthValue,
				extremeWingCfgProfIfEthCdpTransmit
					TruthValue,
				extremeWingCfgProfIfEthLldpReceive
					TruthValue,
				extremeWingCfgProfIfEthLldpTransmit
					TruthValue,
				extremeWingCfgProfIfEthPortChannelLoadBalance
					DisplayString
			 }

		-- 1.3.6.1.4.1.1916.2.131.50.1.3.16.2.2.1.1
		extremeWingCfgProfIfEthSpeed OBJECT-TYPE
			SYNTAX DisplayString
			MAX-ACCESS read-write
			STATUS current
			DESCRIPTION
				"
				Values:
				10
				100
				1000
				auto
				
				XPath: /extremeWing-config/profile[name=key1]/interface[name=key2]/speed"
			DEFVAL { "auto" }
			::= { extremeWingCfgProfIfEthEntry 1 }

		
		-- 1.3.6.1.4.1.1916.2.131.50.1.3.16.2.2.1.2
		extremeWingCfgProfIfEthDuplex OBJECT-TYPE
			SYNTAX DisplayString
			MAX-ACCESS read-write
			STATUS current
			DESCRIPTION
				"
				Values:
				half
				full
				auto
				
				XPath: /extremeWing-config/profile[name=key1]/interface[name=key2]/duplex"
			DEFVAL { "auto" }
			::= { extremeWingCfgProfIfEthEntry 2 }

		
		-- 1.3.6.1.4.1.1916.2.131.50.1.3.16.2.2.1.3
		extremeWingCfgProfIfEthSwitchportMode OBJECT-TYPE
			SYNTAX DisplayString
			MAX-ACCESS read-write
			STATUS current
			DESCRIPTION
				"Mode of the Layer 2 interface.
				
				Values:
				access
				trunk
				
				XPath: /extremeWing-config/profile[name=key1]/interface[name=key2]/switchport/mode"
			DEFVAL { "access" }
			::= { extremeWingCfgProfIfEthEntry 3 }

		
		-- 1.3.6.1.4.1.1916.2.131.50.1.3.16.2.2.1.4
		extremeWingCfgProfIfEthSwitchportNativeVlan OBJECT-TYPE
			SYNTAX Unsigned32 (1..4094)
			MAX-ACCESS read-write
			STATUS current
			DESCRIPTION
				"Native VLAN for classifying untagged traffic.
				
				XPath: /extremeWing-config/profile[name=key1]/interface[name=key2]/switchport/native_vlan"
			DEFVAL { 1 }
			::= { extremeWingCfgProfIfEthEntry 4 }

		
		-- 1.3.6.1.4.1.1916.2.131.50.1.3.16.2.2.1.5
		extremeWingCfgProfIfEthSwitchportNativeVlanTagged OBJECT-TYPE
			SYNTAX TruthValue
			MAX-ACCESS read-write
			STATUS current
			DESCRIPTION
				"Tag the native VLAN.
				
				XPath: /extremeWing-config/profile[name=key1]/interface[name=key2]/switchport/native_vlan_tagged"
			DEFVAL { false }
			::= { extremeWingCfgProfIfEthEntry 5 }

		
		-- 1.3.6.1.4.1.1916.2.131.50.1.3.16.2.2.1.6
		extremeWingCfgProfIfEthArpTrust OBJECT-TYPE
			SYNTAX TruthValue
			MAX-ACCESS read-write
			STATUS current
			DESCRIPTION
				"Trust ARP request on this port.
				
				XPath: /extremeWing-config/profile[name=key1]/interface[name=key2]/arp_trust"
			DEFVAL { false }
			::= { extremeWingCfgProfIfEthEntry 6 }

		
		-- 1.3.6.1.4.1.1916.2.131.50.1.3.16.2.2.1.7
		extremeWingCfgProfIfEthDhcpTrust OBJECT-TYPE
			SYNTAX TruthValue
			MAX-ACCESS read-write
			STATUS current
			DESCRIPTION
				"Trust DHCP responses on this port
				
				XPath: /extremeWing-config/profile[name=key1]/interface[name=key2]/dhcp_trust"
			DEFVAL { true }
			::= { extremeWingCfgProfIfEthEntry 7 }

		
		-- 1.3.6.1.4.1.1916.2.131.50.1.3.16.2.2.1.8
		extremeWingCfgProfIfEthArpHeaderMismatchValidation OBJECT-TYPE
			SYNTAX TruthValue
			MAX-ACCESS read-write
			STATUS current
			DESCRIPTION
				"Check mismatch for source MAC in ARP header and ethernet header.
				
				XPath: /extremeWing-config/profile[name=key1]/interface[name=key2]/arp_header_mismatch_validation"
			DEFVAL { false }
			::= { extremeWingCfgProfIfEthEntry 8 }

		
		-- 1.3.6.1.4.1.1916.2.131.50.1.3.16.2.2.1.9
		extremeWingCfgProfIfEthQosTrustDscp OBJECT-TYPE
			SYNTAX TruthValue
			MAX-ACCESS read-write
			STATUS current
			DESCRIPTION
				"Trust IP DSCP values on this port.
				
				XPath: /extremeWing-config/profile[name=key1]/interface[name=key2]/qos_trust_dscp"
			DEFVAL { true }
			::= { extremeWingCfgProfIfEthEntry 9 }

		
		-- 1.3.6.1.4.1.1916.2.131.50.1.3.16.2.2.1.10
		extremeWingCfgProfIfEthQosTrust802dot1p OBJECT-TYPE
			SYNTAX TruthValue
			MAX-ACCESS read-write
			STATUS current
			DESCRIPTION
				"Trust 802.1p COS values on this port.
				
				XPath: /extremeWing-config/profile[name=key1]/interface[name=key2]/qos_trust_802dot1p"
			DEFVAL { true }
			::= { extremeWingCfgProfIfEthEntry 10 }

		
		-- 1.3.6.1.4.1.1916.2.131.50.1.3.16.2.2.1.11
		extremeWingCfgProfIfEthStaticChannelGroup OBJECT-TYPE
			SYNTAX Unsigned32 (1..4)
			MAX-ACCESS read-write
			STATUS current
			DESCRIPTION
				"Channel group to which the port belongs.
				
				XPath: /extremeWing-config/profile[name=key1]/interface[name=key2]/static_channel_group"
			::= { extremeWingCfgProfIfEthEntry 11 }

		
		-- 1.3.6.1.4.1.1916.2.131.50.1.3.16.2.2.1.12
		extremeWingCfgProfIfEthPoeSupported OBJECT-TYPE
			SYNTAX TruthValue
			MAX-ACCESS read-write
			STATUS current
			DESCRIPTION
				"POE supported on this port when true.
				
				XPath: /extremeWing-config/profile[name=key1]/interface[name=key2]/poe_supported"
			DEFVAL { false }
			::= { extremeWingCfgProfIfEthEntry 12 }

		
		-- 1.3.6.1.4.1.1916.2.131.50.1.3.16.2.2.1.13
		extremeWingCfgProfIfEthPoePower OBJECT-TYPE
			SYNTAX TruthValue
			MAX-ACCESS read-write
			STATUS current
			DESCRIPTION
				"Enable/Disable POE Power.
				
				XPath: /extremeWing-config/profile[name=key1]/interface[name=key2]/poe_power"
			DEFVAL { true }
			::= { extremeWingCfgProfIfEthEntry 13 }

		
		-- 1.3.6.1.4.1.1916.2.131.50.1.3.16.2.2.1.14
		extremeWingCfgProfIfEthPoeLimit OBJECT-TYPE
			SYNTAX Unsigned32 (0..40)
			UNITS "watts"
			MAX-ACCESS read-write
			STATUS current
			DESCRIPTION
				"
				
				XPath: /extremeWing-config/profile[name=key1]/interface[name=key2]/poe_limit"
			DEFVAL { 0 }
			::= { extremeWingCfgProfIfEthEntry 14 }

		
		-- 1.3.6.1.4.1.1916.2.131.50.1.3.16.2.2.1.15
		extremeWingCfgProfIfEthPoePriority OBJECT-TYPE
			SYNTAX DisplayString
			MAX-ACCESS read-write
			STATUS current
			DESCRIPTION
				"
				Values:
				critical
				high
				low
				
				XPath: /extremeWing-config/profile[name=key1]/interface[name=key2]/poe_priority"
			DEFVAL { "low" }
			::= { extremeWingCfgProfIfEthEntry 15 }

		
		-- 1.3.6.1.4.1.1916.2.131.50.1.3.16.2.2.1.16
		extremeWingCfgProfIfEthDot1xSupported OBJECT-TYPE
			SYNTAX TruthValue
			MAX-ACCESS read-write
			STATUS current
			DESCRIPTION
				"Dot1x supported on port when enabled.
				
				XPath: /extremeWing-config/profile[name=key1]/interface[name=key2]/dot1x_supported"
			DEFVAL { false }
			::= { extremeWingCfgProfIfEthEntry 16 }

		
		-- 1.3.6.1.4.1.1916.2.131.50.1.3.16.2.2.1.17
		extremeWingCfgProfIfEthDot1xEnable OBJECT-TYPE
			SYNTAX TruthValue
			MAX-ACCESS read-write
			STATUS current
			DESCRIPTION
				"
				
				XPath: /extremeWing-config/profile[name=key1]/interface[name=key2]/dot1x/enable"
			DEFVAL { false }
			::= { extremeWingCfgProfIfEthEntry 17 }

		
		-- 1.3.6.1.4.1.1916.2.131.50.1.3.16.2.2.1.18
		extremeWingCfgProfIfEthDot1xUsername OBJECT-TYPE
			SYNTAX DisplayString (SIZE (1..32))
			MAX-ACCESS read-write
			STATUS current
			DESCRIPTION
				"
				
				XPath: /extremeWing-config/profile[name=key1]/interface[name=key2]/dot1x/username"
			::= { extremeWingCfgProfIfEthEntry 18 }

		
		-- 1.3.6.1.4.1.1916.2.131.50.1.3.16.2.2.1.19
		extremeWingCfgProfIfEthDot1xPassword OBJECT-TYPE
			SYNTAX DisplayString
			MAX-ACCESS read-write
			STATUS current
			DESCRIPTION
				"
				
				XPath: /extremeWing-config/profile[name=key1]/interface[name=key2]/dot1x/password"
			::= { extremeWingCfgProfIfEthEntry 19 }

		
		-- 1.3.6.1.4.1.1916.2.131.50.1.3.16.2.2.1.20
		extremeWingCfgProfIfEthCdpReceive OBJECT-TYPE
			SYNTAX TruthValue
			MAX-ACCESS read-write
			STATUS current
			DESCRIPTION
				"Snoop CDP on port
				
				XPath: /extremeWing-config/profile[name=key1]/interface[name=key2]/cdp_receive"
			DEFVAL { true }
			::= { extremeWingCfgProfIfEthEntry 20 }

		
		-- 1.3.6.1.4.1.1916.2.131.50.1.3.16.2.2.1.21
		extremeWingCfgProfIfEthCdpTransmit OBJECT-TYPE
			SYNTAX TruthValue
			MAX-ACCESS read-write
			STATUS current
			DESCRIPTION
				"Transmit CDP packets on port
				
				XPath: /extremeWing-config/profile[name=key1]/interface[name=key2]/cdp_transmit"
			DEFVAL { true }
			::= { extremeWingCfgProfIfEthEntry 21 }

		
		-- 1.3.6.1.4.1.1916.2.131.50.1.3.16.2.2.1.22
		extremeWingCfgProfIfEthLldpReceive OBJECT-TYPE
			SYNTAX TruthValue
			MAX-ACCESS read-write
			STATUS current
			DESCRIPTION
				"Snoop LLDP on port
				
				XPath: /extremeWing-config/profile[name=key1]/interface[name=key2]/lldp_receive"
			DEFVAL { true }
			::= { extremeWingCfgProfIfEthEntry 22 }

		
		-- 1.3.6.1.4.1.1916.2.131.50.1.3.16.2.2.1.23
		extremeWingCfgProfIfEthLldpTransmit OBJECT-TYPE
			SYNTAX TruthValue
			MAX-ACCESS read-write
			STATUS current
			DESCRIPTION
				"Transmit LLDP PDUs on port
				
				XPath: /extremeWing-config/profile[name=key1]/interface[name=key2]/lldp_transmit"
			DEFVAL { true }
			::= { extremeWingCfgProfIfEthEntry 23 }

		
		-- 1.3.6.1.4.1.1916.2.131.50.1.3.16.2.2.1.24
		extremeWingCfgProfIfEthPortChannelLoadBalance OBJECT-TYPE
			SYNTAX DisplayString
			MAX-ACCESS read-write
			STATUS current
			DESCRIPTION
				"
				Values:
				src-dst-ip
				src-dst-mac
				
				XPath: /extremeWing-config/profile[name=key1]/interface[name=key2]/port_channel_load_balance"
			DEFVAL { "src-dst-ip" }
			::= { extremeWingCfgProfIfEthEntry 24 }

		
		-- 1.3.6.1.4.1.1916.2.131.50.1.3.16.2.3
		extremeWingCfgProfIfVlanTable OBJECT-TYPE
			SYNTAX SEQUENCE OF ExtremeWingCfgProfIfVlanEntry
			MAX-ACCESS not-accessible
			STATUS current
			DESCRIPTION
				"
				
				/extremeWing-config/profile/interface"
			::= { extremeWingCfgProfIf 3 }

		
		-- 1.3.6.1.4.1.1916.2.131.50.1.3.16.2.3.1
		extremeWingCfgProfIfVlanEntry OBJECT-TYPE
			SYNTAX ExtremeWingCfgProfIfVlanEntry
			MAX-ACCESS not-accessible
			STATUS current
			DESCRIPTION
				"An entry in the table."
			INDEX { extremeWingCfgProfName, extremeWingCfgProfIfName }
			::= { extremeWingCfgProfIfVlanTable 1 }

		
		ExtremeWingCfgProfIfVlanEntry ::=
			SEQUENCE { 
				extremeWingCfgProfIfVlanVlan
					Unsigned32,
				extremeWingCfgProfIfVlanDhcpcOptAll
					TruthValue,
				extremeWingCfgProfIfVlanNatDirection
					DisplayString,
				extremeWingCfgProfIfVlanCryptoMap
					ExtremeWingIdentifier,
				extremeWingCfgProfIfVlanDhcpRelayIncoming
					TruthValue,
				extremeWingCfgProfIfVlanOspfAuth
					DisplayString,
				extremeWingCfgProfIfVlanOspfAuthKey
					DisplayString,
				extremeWingCfgProfIfVlanOspfNetworkType
					DisplayString,
				extremeWingCfgProfIfVlanOspfPriority
					Unsigned32
			 }

		-- 1.3.6.1.4.1.1916.2.131.50.1.3.16.2.3.1.1
		extremeWingCfgProfIfVlanVlan OBJECT-TYPE
			SYNTAX Unsigned32 (1..4094)
			MAX-ACCESS read-write
			STATUS current
			DESCRIPTION
				"
				
				XPath: /extremeWing-config/profile[name=key1]/interface[name=key2]/vlan"
			::= { extremeWingCfgProfIfVlanEntry 1 }

		
		-- 1.3.6.1.4.1.1916.2.131.50.1.3.16.2.3.1.2
		extremeWingCfgProfIfVlanDhcpcOptAll OBJECT-TYPE
			SYNTAX TruthValue
			MAX-ACCESS read-write
			STATUS current
			DESCRIPTION
				"Learn default gateway, name servers, domain name on this
				interface.
				
				XPath: /extremeWing-config/profile[name=key1]/interface[name=key2]/dhcpc_opt_all"
			DEFVAL { false }
			::= { extremeWingCfgProfIfVlanEntry 2 }

		
		-- 1.3.6.1.4.1.1916.2.131.50.1.3.16.2.3.1.3
		extremeWingCfgProfIfVlanNatDirection OBJECT-TYPE
			SYNTAX DisplayString
			MAX-ACCESS read-write
			STATUS current
			DESCRIPTION
				"
				
				Values:
				inside
				outside
				none
				
				XPath: /extremeWing-config/profile[name=key1]/interface[name=key2]/nat_direction"
			DEFVAL { "none" }
			::= { extremeWingCfgProfIfVlanEntry 3 }

		
		-- 1.3.6.1.4.1.1916.2.131.50.1.3.16.2.3.1.4
		extremeWingCfgProfIfVlanCryptoMap OBJECT-TYPE
			SYNTAX ExtremeWingIdentifier
			MAX-ACCESS read-write
			STATUS current
			DESCRIPTION
				"Attach an already configured crypto map to this interface.
				
				XPath: /extremeWing-config/profile[name=key1]/interface[name=key2]/crypto_map"
			::= { extremeWingCfgProfIfVlanEntry 4 }

		
		-- 1.3.6.1.4.1.1916.2.131.50.1.3.16.2.3.1.5
		extremeWingCfgProfIfVlanDhcpRelayIncoming OBJECT-TYPE
			SYNTAX TruthValue
			MAX-ACCESS read-write
			STATUS current
			DESCRIPTION
				"Allow on-board DHCP server to respond to relayed DHCP packets
				on this interface
				
				XPath: /extremeWing-config/profile[name=key1]/interface[name=key2]/dhcp_relay_incoming"
			DEFVAL { false }
			::= { extremeWingCfgProfIfVlanEntry 5 }

		
		-- 1.3.6.1.4.1.1916.2.131.50.1.3.16.2.3.1.6
		extremeWingCfgProfIfVlanOspfAuth OBJECT-TYPE
			SYNTAX DisplayString
			MAX-ACCESS read-write
			STATUS current
			DESCRIPTION
				"OSPF authentication type
				
				Values:
				simple-password,
				message-digest,
                                null,
				none
				
				XPath: /extremeWing-config/profile[name=key1]/interface[name=key2]/ospf_authentication"
			DEFVAL { "none" }
			::= { extremeWingCfgProfIfVlanEntry 6 }

		
		-- 1.3.6.1.4.1.1916.2.131.50.1.3.16.2.3.1.7
		extremeWingCfgProfIfVlanOspfAuthKey OBJECT-TYPE
			SYNTAX DisplayString (SIZE (0..8))
			MAX-ACCESS read-write
			STATUS current
			DESCRIPTION
				"Simple auth key for OSPF.
				
				XPath: /extremeWing-config/profile[name=key1]/interface[name=key2]/ospf_auth_key"
			::= { extremeWingCfgProfIfVlanEntry 7 }

		
		-- 1.3.6.1.4.1.1916.2.131.50.1.3.16.2.3.1.8
		extremeWingCfgProfIfVlanOspfNetworkType OBJECT-TYPE
			SYNTAX DisplayString
			MAX-ACCESS read-write
			STATUS current
			DESCRIPTION
				"
				Values:
				broadcast
				non-broadcast
				point-to-point
				point-to-multipoint
				
				XPath: /extremeWing-config/profile[name=key1]/interface[name=key2]/ospf_network_type"
			DEFVAL { "broadcast" }
			::= { extremeWingCfgProfIfVlanEntry 8 }

		
		-- 1.3.6.1.4.1.1916.2.131.50.1.3.16.2.3.1.9
		extremeWingCfgProfIfVlanOspfPriority OBJECT-TYPE
			SYNTAX Unsigned32 (0..255)
			MAX-ACCESS read-write
			STATUS current
			DESCRIPTION
				"
				XPath: /extremeWing-config/profile[name=key1]/interface[name=key2]/ospf_priority"
			DEFVAL { 0 }
			::= { extremeWingCfgProfIfVlanEntry 9 }

		
		-- 1.3.6.1.4.1.1916.2.131.50.1.3.16.2.6
		extremeWingCfgProfIfRadioTable OBJECT-TYPE
			SYNTAX SEQUENCE OF ExtremeWingCfgProfIfRadioEntry
			MAX-ACCESS not-accessible
			STATUS current
			DESCRIPTION
				"
				
				/extremeWing-config/profile/interface"
			::= { extremeWingCfgProfIf 6 }

		
		-- 1.3.6.1.4.1.1916.2.131.50.1.3.16.2.6.1
		extremeWingCfgProfIfRadioEntry OBJECT-TYPE
			SYNTAX ExtremeWingCfgProfIfRadioEntry
			MAX-ACCESS not-accessible
			STATUS current
			DESCRIPTION
				"An entry in the table."
			INDEX { extremeWingCfgProfName, extremeWingCfgProfIfName }
			::= { extremeWingCfgProfIfRadioTable 1 }

		
		ExtremeWingCfgProfIfRadioEntry ::=
			SEQUENCE { 
				extremeWingCfgProfIfRadioRfMode
					DisplayString,
				extremeWingCfgProfIfRadioChannel
					DisplayString,
				extremeWingCfgProfIfRadioPower
					Unsigned32,
				extremeWingCfgProfIfRadioPlacement
					DisplayString,
				extremeWingCfgProfIfRadioBeaconInterval
					DisplayString,
				extremeWingCfgProfIfRadioRtsThreshold
					Unsigned32,
				extremeWingCfgProfIfRadioOffChannelScan
					TruthValue,
				extremeWingCfgProfIfRadioPreambleShort
					TruthValue,
				extremeWingCfgProfIfRadioGuardInterval
					DisplayString,
				extremeWingCfgProfIfRadioAmpduMode
					DisplayString,
				extremeWingCfgProfIfRadioAmsduMode
					DisplayString,
				extremeWingCfgProfIfRadioRifsMode
					DisplayString,
				extremeWingCfgProfIfRadioAmpduMaxAggrSizeRx
					DisplayString,
				extremeWingCfgProfIfRadioAmpduMaxAggrSizeTx
					Unsigned32,
				extremeWingCfgProfIfRadioAmpduMinSpacing
					DisplayString,
				extremeWingCfgProfIfRadioAntennaMode
					DisplayString,
				extremeWingCfgProfIfRadioNonUnicastForwarding
					DisplayString,
				extremeWingCfgProfIfRadioDynamicChainSelection
					TruthValue,
				extremeWingCfgProfIfRadioLockRfMode
					TruthValue,
				extremeWingCfgProfIfRadioSnifferRedirHost
					IpAddress,
				extremeWingCfgProfIfRadioSnifferRedirChannel
					DisplayString,
				extremeWingCfgProfIfRadioMesh
					DisplayString,
				extremeWingCfgProfIfRadioMeshLinks
					Unsigned32,
				extremeWingCfgProfIfRadioProbeResponseRetry
					TruthValue,
				extremeWingCfgProfIfRadioProbeResponseRate
					DisplayString,
				extremeWingCfgProfIfRadioMaxClients
					Unsigned32,
				extremeWingCfgProfIfRadioRadioTapMode
					DisplayString,
				extremeWingCfgProfIfRadioWirelessClientPower
					Unsigned32,
				extremeWingCfgProfIfRadioLoadBalLfCount
					Unsigned32,
				extremeWingCfgProfIfRadioLoadBalLfThroughput
					Unsigned32,
				extremeWingCfgProfIfRadioLoadBalWmCount
					Unsigned32,
				extremeWingCfgProfIfRadioLoadBalWmTput
					Unsigned32,
				extremeWingCfgProfIfRadioAssocAcl
					ExtremeWingIdentifier,
				extremeWingCfgProfIfRadioQosPolicy
					ExtremeWingIdentifier,
                                extremeWingCfgProfIfRadioAntennaDowntilt
                                        TruthValue,
                                extremeWingCfgProfIfRadioExtendedRange
                                        Unsigned32
			 }

		-- 1.3.6.1.4.1.1916.2.131.50.1.3.16.2.6.1.1
		extremeWingCfgProfIfRadioRfMode OBJECT-TYPE
			SYNTAX DisplayString
			MAX-ACCESS read-write
			STATUS current
			DESCRIPTION
				"
				
				Values:
				2.4GHz-wlan
				5GHz-wlan
				sensor
				
				Notes:
				On a WM3400 the radio-mode of radio1 can only be 2.4|sensor.
				radio2 can only be 5|sensor(so the 2.4-wlan and 5-wlan modes
				cant be interchanged) 
				
				On an AP4700 radio3 can only be sensor. It can never be
				2.4-wlan/5-wlan 
				
				XPath: /extremeWing-config/profile[name=key1]/interface[name=key2]/rf_mode"
			::= { extremeWingCfgProfIfRadioEntry 1 }

		
		-- 1.3.6.1.4.1.1916.2.131.50.1.3.16.2.6.1.2
		extremeWingCfgProfIfRadioChannel OBJECT-TYPE
			SYNTAX DisplayString
			MAX-ACCESS read-write
			STATUS current
			DESCRIPTION
				"Channel of operation for this radio.
				
				Values:
				1, 1w, 2, 2w, 3, 3w, 4, 4w, 5, 5w, 6, 6w, 7, 7w, 8, 8w, 9, 
				9w, 10, 10w, 11, 11w, 12, 12w, 13, 13w, 14, 36, 36w, 
				36ww, 40, 40w, 40ww, 44, 44w, 44ww, 48, 48w, 48ww, 52, 
				52w, 52ww, 56, 56w, 56ww, 60, 60w, 60ww, 64, 64w, 64ww, 
				74, 100, 100w, 100ww, 104, 104w, 104ww, 108, 108w, 108ww, 
				112, 112w, 112ww, 116, 116w, 116ww, 120, 120w, 120ww, 124, 
				124w, 124ww, 128, 128w, 128ww, 132, 132w, 136, 136w, 140, 
				149, 149w, 149ww, 153, 153w, 153ww, 157, 157w, 157ww, 161, 
				161w, 161ww, 165, 34, 38, 42, 46, 21, 25, 184, 184w, 188, 
				188w, 192, 192w, 196, 196w, smart, acs
	
				
				When 'rf_mode' is set to '2.4GHz-wlan', valid channels are
				'1' through '14' and 'smart'.
				
				When 'rf_mode' is set to '5GHz-wlan', '1' through '14'
				are not allowed. Rest of the channels (including 'smart' are
				allowed)
				
				When 'rf_mode' is set to 'sensor', 'channel' setting
				is ignored.
				
				XPath: /extremeWing-config/profile[name=key1]/interface[name=key2]/channel"
			DEFVAL { "smart" }
			::= { extremeWingCfgProfIfRadioEntry 2 }

		
		-- 1.3.6.1.4.1.1916.2.131.50.1.3.16.2.6.1.3
		extremeWingCfgProfIfRadioPower OBJECT-TYPE
			SYNTAX Unsigned32 (0..27)
			UNITS "dBm"
			MAX-ACCESS read-write
			STATUS current
			DESCRIPTION
				"Transmit power of the radio.  A setting of 0 indicates
				Smart RF is managing the power.
				
				XPath: /extremeWing-config/profile[name=key1]/interface[name=key2]/power"
			DEFVAL { 20 }
			::= { extremeWingCfgProfIfRadioEntry 3 }

		
		-- 1.3.6.1.4.1.1916.2.131.50.1.3.16.2.6.1.4
		extremeWingCfgProfIfRadioPlacement OBJECT-TYPE
			SYNTAX DisplayString
			MAX-ACCESS read-write
			STATUS current
			DESCRIPTION
				"Location where this radio is operating.
				
				Values:
				indoor
				outdoor
				
				XPath: /extremeWing-config/profile[name=key1]/interface[name=key2]/placement"
			DEFVAL { "indoor" }
			::= { extremeWingCfgProfIfRadioEntry 4 }

		
		-- 1.3.6.1.4.1.1916.2.131.50.1.3.16.2.6.1.5
		extremeWingCfgProfIfRadioBeaconInterval OBJECT-TYPE
			SYNTAX DisplayString
			UNITS "milliseconds"
			MAX-ACCESS read-write
			STATUS current
			DESCRIPTION
				"Interval between radio beacons.
				
				Values:
				50
				100
				200
				
				XPath: /extremeWing-config/profile[name=key1]/interface[name=key2]/beacon_interval"
			DEFVAL { "100" }
			::= { extremeWingCfgProfIfRadioEntry 5 }

		
		-- 1.3.6.1.4.1.1916.2.131.50.1.3.16.2.6.1.6
		extremeWingCfgProfIfRadioRtsThreshold OBJECT-TYPE
			SYNTAX Unsigned32 (0..65536)
			UNITS "bytes"
			MAX-ACCESS read-write
			STATUS current
			DESCRIPTION
				"Ready to Send threshold on this radio.
				
				XPath: /extremeWing-config/profile[name=key1]/interface[name=key2]/rts_threshold"
			DEFVAL { 65536 }
			::= { extremeWingCfgProfIfRadioEntry 6 }

		
		-- 1.3.6.1.4.1.1916.2.131.50.1.3.16.2.6.1.7
		extremeWingCfgProfIfRadioOffChannelScan OBJECT-TYPE
			SYNTAX TruthValue
			MAX-ACCESS read-write
			STATUS current
			DESCRIPTION
				"Enable off-channel scanning on this radio.
				
				XPath: /extremeWing-config/profile[name=key1]/interface[name=key2]/off_channel_scan"
			DEFVAL { false }
			::= { extremeWingCfgProfIfRadioEntry 7 }

		
		-- 1.3.6.1.4.1.1916.2.131.50.1.3.16.2.6.1.8
		extremeWingCfgProfIfRadioPreambleShort OBJECT-TYPE
			SYNTAX TruthValue
			MAX-ACCESS read-write
			STATUS current
			DESCRIPTION
				"Configure use of short preamble.
				
				XPath: /extremeWing-config/profile[name=key1]/interface[name=key2]/preamble_short"
			DEFVAL { false }
			::= { extremeWingCfgProfIfRadioEntry 8 }

		
		-- 1.3.6.1.4.1.1916.2.131.50.1.3.16.2.6.1.9
		extremeWingCfgProfIfRadioGuardInterval OBJECT-TYPE
			SYNTAX DisplayString
			MAX-ACCESS read-write
			STATUS current
			DESCRIPTION
				"802.11n guard interval.
				
				Values:
				any
				long
				
				XPath: /extremeWing-config/profile[name=key1]/interface[name=key2]/guard_interval"
			DEFVAL { "any" }
			::= { extremeWingCfgProfIfRadioEntry 9 }

		
		-- 1.3.6.1.4.1.1916.2.131.50.1.3.16.2.6.1.10
		extremeWingCfgProfIfRadioAmpduMode OBJECT-TYPE
			SYNTAX DisplayString
			MAX-ACCESS read-write
			STATUS current
			DESCRIPTION
				"Mode in which A-MPDU will be supported.
				
				Values:
				tx-only
				rx-only
				tx-rx
				none
				
				XPath: /extremeWing-config/profile[name=key1]/interface[name=key2]/ampdu_mode"
			DEFVAL { "tx-rx" }
			::= { extremeWingCfgProfIfRadioEntry 10 }

		
		-- 1.3.6.1.4.1.1916.2.131.50.1.3.16.2.6.1.11
		extremeWingCfgProfIfRadioAmsduMode OBJECT-TYPE
			SYNTAX DisplayString
			MAX-ACCESS read-write
			STATUS current
			DESCRIPTION
				"Mode in which A-MSDU will be supported.
				
				Values:
				rx-only
				tx-rx
				
				XPath: /extremeWing-config/profile[name=key1]/interface[name=key2]/amsdu_mode"
			DEFVAL { "rx-only" }
			::= { extremeWingCfgProfIfRadioEntry 11 }

		
		-- 1.3.6.1.4.1.1916.2.131.50.1.3.16.2.6.1.12
		extremeWingCfgProfIfRadioRifsMode OBJECT-TYPE
			SYNTAX DisplayString
			MAX-ACCESS read-write
			STATUS current
			DESCRIPTION
				"Modes in which RIFS will be supported.
				
				Values:
				tx-only
				rx-only
				tx-rx
				none
				
				XPath: /extremeWing-config/profile[name=key1]/interface[name=key2]/rifs_mode"
			DEFVAL { "tx-rx" }
			::= { extremeWingCfgProfIfRadioEntry 12 }

		
		-- 1.3.6.1.4.1.1916.2.131.50.1.3.16.2.6.1.13
		extremeWingCfgProfIfRadioAmpduMaxAggrSizeRx OBJECT-TYPE
			SYNTAX DisplayString
			UNITS "bytes"
			MAX-ACCESS read-write
			STATUS current
			DESCRIPTION
				"Advertised maximum limit on A-MPDU aggregated received frames.
				
				Values:
				8191
				16383
				32767
				65535
				
				XPath: /extremeWing-config/profile[name=key1]/interface[name=key2]/ampdu_max_aggr_size_rx"
			DEFVAL { "65535" }
			::= { extremeWingCfgProfIfRadioEntry 13 }

		
		-- 1.3.6.1.4.1.1916.2.131.50.1.3.16.2.6.1.14
		extremeWingCfgProfIfRadioAmpduMaxAggrSizeTx OBJECT-TYPE
			SYNTAX Unsigned32 (0..65535)
			UNITS "bytes"
			MAX-ACCESS read-write
			STATUS current
			DESCRIPTION
				"Limit on A-MPDU aggregated transmitted frames.
				
				XPath: /extremeWing-config/profile[name=key1]/interface[name=key2]/ampdu_max_aggr_size_tx"
			DEFVAL { 65535 }
			::= { extremeWingCfgProfIfRadioEntry 14 }

		
		-- 1.3.6.1.4.1.1916.2.131.50.1.3.16.2.6.1.15
		extremeWingCfgProfIfRadioAmpduMinSpacing OBJECT-TYPE
			SYNTAX DisplayString
			UNITS "microseconds"
			MAX-ACCESS read-write
			STATUS current
			DESCRIPTION
				"Minimum gap between A-MPDU frames (in microseconds).
				
				Values:
				0
				1
				2
				4
				8
				16
				
				XPath: /extremeWing-config/profile[name=key1]/interface[name=key2]/ampdu_min_spacing"
			DEFVAL { "4" }
			::= { extremeWingCfgProfIfRadioEntry 15 }

		
		-- 1.3.6.1.4.1.1916.2.131.50.1.3.16.2.6.1.16
		extremeWingCfgProfIfRadioAntennaMode OBJECT-TYPE
			SYNTAX DisplayString
			MAX-ACCESS read-write
			STATUS current
			DESCRIPTION
				"Number of transmit and receive antennas on the radio. 1x1 implies only the A antenna; 1x3 implies A for Tx and all three for Rx; default depends on the AP type, the type of power (802.3af etc), etc.
				
				Values:
				1x1
				1xALL
				2x2
				default
				
				XPath: /extremeWing-config/profile[name=key1]/interface[name=key2]/antenna_mode"
			DEFVAL { "default" }
			::= { extremeWingCfgProfIfRadioEntry 16 }

		
		-- 1.3.6.1.4.1.1916.2.131.50.1.3.16.2.6.1.17
		extremeWingCfgProfIfRadioNonUnicastForwarding OBJECT-TYPE
			SYNTAX DisplayString
			MAX-ACCESS read-write
			STATUS current
			DESCRIPTION
				"Whether broadcast and multicast packets should always follow
				DTIM, or do so only if some wireless clients are in
				power-save mode.
				
				Values:
				follow-dtim
				power-save-aware
				
				XPath: /extremeWing-config/profile[name=key1]/interface[name=key2]/non_unicast_forwarding"
			DEFVAL { "follow-dtim" }
			::= { extremeWingCfgProfIfRadioEntry 17 }

		
		-- 1.3.6.1.4.1.1916.2.131.50.1.3.16.2.6.1.18
		extremeWingCfgProfIfRadioDynamicChainSelection OBJECT-TYPE
			SYNTAX TruthValue
			MAX-ACCESS read-write
			STATUS current
			DESCRIPTION
				"Whether the radio should dynamically change the number of
				transmit chains used (use a single chain/antenna for frames
				at non-11n data-rates).
				
				XPath: /extremeWing-config/profile[name=key1]/interface[name=key2]/dynamic_chain_selection"
			DEFVAL { false }
			::= { extremeWingCfgProfIfRadioEntry 18 }

		
		-- 1.3.6.1.4.1.1916.2.131.50.1.3.16.2.6.1.19
		extremeWingCfgProfIfRadioLockRfMode OBJECT-TYPE
			SYNTAX TruthValue
			MAX-ACCESS read-write
			STATUS current
			DESCRIPTION
				"Lock Smart RF mode of operation for this radio.
				
				XPath: /extremeWing-config/profile[name=key1]/interface[name=key2]/lock_rf_mode"
			DEFVAL { false }
			::= { extremeWingCfgProfIfRadioEntry 19 }

		
		-- 1.3.6.1.4.1.1916.2.131.50.1.3.16.2.6.1.20
		extremeWingCfgProfIfRadioSnifferRedirHost OBJECT-TYPE
			SYNTAX IpAddress
			MAX-ACCESS read-write
			STATUS current
			DESCRIPTION
				"Address of host to which captured packets are redirected.
				
				XPath: /extremeWing-config/profile[name=key1]/interface[name=key2]/sniffer_redirect/host"
			::= { extremeWingCfgProfIfRadioEntry 20 }

		
		-- 1.3.6.1.4.1.1916.2.131.50.1.3.16.2.6.1.21
		extremeWingCfgProfIfRadioSnifferRedirChannel OBJECT-TYPE
			SYNTAX DisplayString
			MAX-ACCESS read-write
			STATUS current
			DESCRIPTION
				"Channel on which to capture packets.
				
				Values:
				1, 1+, 2, 2+, 3, 3+, 4, 4+, 5, 5+, 5-, 6, 6+, 6-, 7, 7+, 7-,
				8, 8+, 8-, 9, 9+, 9-, 10, 10-, 11, 11-, 12, 12-, 13, 13-, 14,
				36, 36+, 40, 40-, 44, 44+, 48, 48-, 52, 52+, 56, 56-, 60, 60+,
				64, 64-, 100, 100+, 104, 104-, 108, 108+, 112, 112-, 116,
				116+, 120, 120-, 124, 124+, 128, 128-, 132, 132+, 136, 136-,
				140, 149, 149+, 153, 153-, 157, 157+, 161, 161-, 165, 34, 38,
				42, and 46
				
				XPath: /extremeWing-config/profile[name=key1]/interface[name=key2]/sniffer_redirect/channel"
			DEFVAL { "1" }
			::= { extremeWingCfgProfIfRadioEntry 21 }

		
		-- 1.3.6.1.4.1.1916.2.131.50.1.3.16.2.6.1.22
		extremeWingCfgProfIfRadioMesh OBJECT-TYPE
			SYNTAX DisplayString
			MAX-ACCESS read-write
			STATUS current
			DESCRIPTION
				"Client operation scans for Mesh Portals, or nodes that have
				connectivity to Portals, and connects through them. 
				Portal operation begins beaconing immediately and accepting
				connections from other Mesh nodes.  Generally the Portal node
				is connected to the wired network.
				
				Values:
				disabled
				portal
				client
				
				XPath: /extremeWing-config/profile[name=key1]/interface[name=key2]/mesh"
			DEFVAL { "disabled" }
			::= { extremeWingCfgProfIfRadioEntry 22 }

		
		-- 1.3.6.1.4.1.1916.2.131.50.1.3.16.2.6.1.23
		extremeWingCfgProfIfRadioMeshLinks OBJECT-TYPE
			SYNTAX Unsigned32 (1..6)
			MAX-ACCESS read-write
			STATUS current
			DESCRIPTION
				"Maximum number of Mesh links that this radio will attempt to
				create.
				
				XPath: /extremeWing-config/profile[name=key1]/interface[name=key2]/mesh_links"
			DEFVAL { 3 }
			::= { extremeWingCfgProfIfRadioEntry 23 }

		
		-- 1.3.6.1.4.1.1916.2.131.50.1.3.16.2.6.1.24
		extremeWingCfgProfIfRadioProbeResponseRetry OBJECT-TYPE
			SYNTAX TruthValue
			MAX-ACCESS read-write
			STATUS current
			DESCRIPTION
				"Whether Probe-Responses are retried on the air if they are
				not acknowledged by the wireless client
				
				XPath: /extremeWing-config/profile[name=key1]/interface[name=key2]/probe_response_retry"
			DEFVAL { true }
			::= { extremeWingCfgProfIfRadioEntry 24 }

		
		-- 1.3.6.1.4.1.1916.2.131.50.1.3.16.2.6.1.25
		extremeWingCfgProfIfRadioProbeResponseRate OBJECT-TYPE
			SYNTAX DisplayString
			MAX-ACCESS read-write
			STATUS current
			DESCRIPTION
				"The data transmission rate used for sending Probe Responses
				
				Values:
				follow-probe-request
				highest-basic
				lowest-basic
				
				XPath: /extremeWing-config/profile[name=key1]/interface[name=key2]/probe_response_rate"
			DEFVAL { "follow-probe-request" }
			::= { extremeWingCfgProfIfRadioEntry 25 }

		
		-- 1.3.6.1.4.1.1916.2.131.50.1.3.16.2.6.1.26
		extremeWingCfgProfIfRadioMaxClients OBJECT-TYPE
			SYNTAX Unsigned32 (0..256)
			MAX-ACCESS read-write
			STATUS current
			DESCRIPTION
				"The maximum number of clients allowed to associate
				with this radio
				
				XPath: /extremeWing-config/profile[name=key1]/interface[name=key2]/max_clients"
			DEFVAL { 256 }
			::= { extremeWingCfgProfIfRadioEntry 26 }

		
		-- 1.3.6.1.4.1.1916.2.131.50.1.3.16.2.6.1.27
		extremeWingCfgProfIfRadioRadioTapMode OBJECT-TYPE
			SYNTAX DisplayString
			MAX-ACCESS read-write
			STATUS current
			DESCRIPTION
				"Radio tap mode of operation
				
				Values:
				off
				inline
				promiscuous
				
				Note:
				Radio tap can be enabled only on wlan radio and in 5.1,
				only when another radio on AP is sensor.
				
				XPath: /extremeWing-config/profile[name=key1]/interface[name=key2]/radio_tap_mode"
			DEFVAL { "off" }
			::= { extremeWingCfgProfIfRadioEntry 27 }

		
		-- 1.3.6.1.4.1.1916.2.131.50.1.3.16.2.6.1.28
		extremeWingCfgProfIfRadioWirelessClientPower OBJECT-TYPE
			SYNTAX Unsigned32 (0..20)
			UNITS "dBm"
			MAX-ACCESS read-write
			STATUS current
			DESCRIPTION
				"Transmit power indicated to wireless clients for transmission.
				
				XPath: /extremeWing-config/profile[name=key1]/interface[name=key2]/wireless_client_power"
			::= { extremeWingCfgProfIfRadioEntry 28 }

		
		-- 1.3.6.1.4.1.1916.2.131.50.1.3.16.2.6.1.29
		extremeWingCfgProfIfRadioLoadBalLfCount OBJECT-TYPE
			SYNTAX Unsigned32 (0..10)
			MAX-ACCESS read-write
			STATUS current
			DESCRIPTION
				"Consider the number of Wireless Clients in determining
				the load on an AP.  High numbers indicate a higher weight
				assigned to the criteria. 0 implies that count is
				not considered.
				
				XPath: /extremeWing-config/profile[name=key1]/interface[name=key2]/load_balance_lf_count"
			DEFVAL { 10 }
			::= { extremeWingCfgProfIfRadioEntry 29 }

		
		-- 1.3.6.1.4.1.1916.2.131.50.1.3.16.2.6.1.30
		extremeWingCfgProfIfRadioLoadBalLfThroughput OBJECT-TYPE
			SYNTAX Unsigned32 (0..10)
			MAX-ACCESS read-write
			STATUS current
			DESCRIPTION
				"Consider the throughput of traffic in determining the load
				on an AP.  High numbers indicate a higher weight assigned
				to the criteria.  0 implies that throughput is not considered.
				
				XPath: /extremeWing-config/profile[name=key1]/interface[name=key2]/load_balance_lf_throughput"
			DEFVAL { 0 }
			::= { extremeWingCfgProfIfRadioEntry 30 }

		
		-- 1.3.6.1.4.1.1916.2.131.50.1.3.16.2.6.1.31
		extremeWingCfgProfIfRadioLoadBalWmCount OBJECT-TYPE
			SYNTAX Unsigned32 (1..255)
			MAX-ACCESS read-write
			STATUS current
			DESCRIPTION
				"The number of clients that can associate with a radio before
				load-balancing would be triggered
				
				XPath: /extremeWing-config/profile[name=key1]/interface[name=key2]/load_balance_wm_count"
			DEFVAL { 10 }
			::= { extremeWingCfgProfIfRadioEntry 31 }

		
		-- 1.3.6.1.4.1.1916.2.131.50.1.3.16.2.6.1.32
		extremeWingCfgProfIfRadioLoadBalWmTput OBJECT-TYPE
			SYNTAX Unsigned32 (1..1000)
			MAX-ACCESS read-write
			STATUS current
			DESCRIPTION
				"When the average throughput of a radio exceeds this threshold
				(in Mbps) load balancing would be triggered
				
				XPath: /extremeWing-config/profile[name=key1]/interface[name=key2]/load_balance_wm_tput_mbps"
			DEFVAL { 10 }
			::= { extremeWingCfgProfIfRadioEntry 32 }

		
		-- 1.3.6.1.4.1.1916.2.131.50.1.3.16.2.6.1.33
		extremeWingCfgProfIfRadioAssocAcl OBJECT-TYPE
			SYNTAX ExtremeWingIdentifier
			MAX-ACCESS read-write
			STATUS current
			DESCRIPTION
				"
				
				XPath: /extremeWing-config/profile[name=key1]/interface[name=key2]/assoc_acl"
			::= { extremeWingCfgProfIfRadioEntry 33 }

		
		-- 1.3.6.1.4.1.1916.2.131.50.1.3.16.2.6.1.34
		extremeWingCfgProfIfRadioQosPolicy OBJECT-TYPE
			SYNTAX ExtremeWingIdentifier
			MAX-ACCESS read-write
			STATUS current
			DESCRIPTION
				"
				
				XPath: /extremeWing-config/profile[name=key1]/interface[name=key2]/qos_policy"
			::= { extremeWingCfgProfIfRadioEntry 34 }

                -- 1.3.6.1.4.1.1916.2.131.50.1.3.16.2.6.1.35
                extremeWingCfgProfIfRadioAntennaDowntilt OBJECT-TYPE
                        SYNTAX TruthValue
                        MAX-ACCESS read-write
                        STATUS current
                        DESCRIPTION
                                "Whether the radio should enable ADEPT antenna modes.
 
                                XPath: /extremeWing-config/profile[name=key1]/interface[name=key2]/antenna_downtilt"
                        DEFVAL { false }
                        ::= { extremeWingCfgProfIfRadioEntry 35 }
 
 
                -- 1.3.6.1.4.1.1916.2.131.50.1.3.16.2.6.1.36
                extremeWingCfgProfIfRadioExtendedRange OBJECT-TYPE
                        SYNTAX Unsigned32
                        MAX-ACCESS read-write
                        STATUS current
                        DESCRIPTION
                                "Configure extended rate selection.
			
				Default Value
                                for 2.4 Ghz : 7 Kilometer
                                    5 GHz   : 2 Kilometer
                                XPath: /extremeWing-config/profile[name=key1]/interface[name=key2]/extended_range"
                        DEFVAL { "kilometer" }
                        ::= { extremeWingCfgProfIfRadioEntry 36 }

		-- 1.3.6.1.4.1.1916.2.131.50.1.3.16.2.7
		extremeWingCfgProfIfRadioBssmapTable OBJECT-TYPE
			SYNTAX SEQUENCE OF ExtremeWingCfgProfIfRadioBssmapEntry
			MAX-ACCESS not-accessible
			STATUS current
			DESCRIPTION
				"
				
				/extremeWing-config/profile/interface/wlanbssmap"
			::= { extremeWingCfgProfIf 7 }

		
		-- 1.3.6.1.4.1.1916.2.131.50.1.3.16.2.7.1
		extremeWingCfgProfIfRadioBssmapEntry OBJECT-TYPE
			SYNTAX ExtremeWingCfgProfIfRadioBssmapEntry
			MAX-ACCESS not-accessible
			STATUS current
			DESCRIPTION
				"An entry in the table."
			INDEX { extremeWingCfgProfName, extremeWingCfgProfIfName, extremeWingCfgProfIfRadioBssmapWlan }
			::= { extremeWingCfgProfIfRadioBssmapTable 1 }

		
		ExtremeWingCfgProfIfRadioBssmapEntry ::=
			SEQUENCE { 
				extremeWingCfgProfIfRadioBssmapWlan
					ExtremeWingIdentifier,
				extremeWingCfgProfIfRadioBssmapBss
					Unsigned32,
				extremeWingCfgProfIfRadioBssmapPrimary
					TruthValue
			 }

		-- 1.3.6.1.4.1.1916.2.131.50.1.3.16.2.7.1.1
		extremeWingCfgProfIfRadioBssmapWlan OBJECT-TYPE
			SYNTAX ExtremeWingIdentifier
			MAX-ACCESS read-only
			STATUS current
			DESCRIPTION
				"
				
				XPath: /extremeWing-config/profile[name=key1]/interface[name=key2]/wlanbssmap[wlan=key3]/wlan"
			::= { extremeWingCfgProfIfRadioBssmapEntry 1 }

		
		-- 1.3.6.1.4.1.1916.2.131.50.1.3.16.2.7.1.3
		extremeWingCfgProfIfRadioBssmapBss OBJECT-TYPE
			SYNTAX Unsigned32 (1..16)
			MAX-ACCESS read-write
			STATUS current
			DESCRIPTION
				"<1-16>  The bss number (4 for ap300)
				
				XPath: /extremeWing-config/profile[name=key1]/interface[name=key2]/wlanbssmap[wlan=key3]/bss"
			::= { extremeWingCfgProfIfRadioBssmapEntry 3 }

		
		-- 1.3.6.1.4.1.1916.2.131.50.1.3.16.2.7.1.4
		extremeWingCfgProfIfRadioBssmapPrimary OBJECT-TYPE
			SYNTAX TruthValue
			MAX-ACCESS read-write
			STATUS current
			DESCRIPTION
				"
				
				XPath: /extremeWing-config/profile[name=key1]/interface[name=key2]/wlanbssmap[wlan=key3]/primary"
			::= { extremeWingCfgProfIfRadioBssmapEntry 4 }

		
		-- 1.3.6.1.4.1.1916.2.131.50.1.3.16.2.9
		extremeWingCfgProfIfSpanTreeTable OBJECT-TYPE
			SYNTAX SEQUENCE OF ExtremeWingCfgProfIfSpanTreeEntry
			MAX-ACCESS not-accessible
			STATUS current
			DESCRIPTION
				"Interface Spanning Tree configuration
				
				/extremeWing-config/profile/interface/spanningtree"
			::= { extremeWingCfgProfIf 9 }

		
		-- 1.3.6.1.4.1.1916.2.131.50.1.3.16.2.9.1
		extremeWingCfgProfIfSpanTreeEntry OBJECT-TYPE
			SYNTAX ExtremeWingCfgProfIfSpanTreeEntry
			MAX-ACCESS not-accessible
			STATUS current
			DESCRIPTION
				"An entry in the table."
			INDEX { extremeWingCfgProfName, extremeWingCfgProfIfName }
			::= { extremeWingCfgProfIfSpanTreeTable 1 }

		
		ExtremeWingCfgProfIfSpanTreeEntry ::=
			SEQUENCE { 
				extremeWingCfgProfIfSpanTreeLinkType
					DisplayString,
				extremeWingCfgProfIfSpanTreePortfast
					TruthValue,
				extremeWingCfgProfIfSpanTreeEdgeport
					TruthValue,
				extremeWingCfgProfIfSpanTreeBpduguard
					DisplayString,
				extremeWingCfgProfIfSpanTreeBpdufilter
					DisplayString,
				extremeWingCfgProfIfSpanTreePortCiscoInterop
					DisplayString,
				extremeWingCfgProfIfSpanTreeForceVersion
					Unsigned32,
				extremeWingCfgProfIfSpanTreeGuard
					DisplayString
			 }

		-- 1.3.6.1.4.1.1916.2.131.50.1.3.16.2.9.1.1
		extremeWingCfgProfIfSpanTreeLinkType OBJECT-TYPE
			SYNTAX DisplayString
			MAX-ACCESS read-write
			STATUS current
			DESCRIPTION
				"Point-to-point enables rapid transition.  Shared disables
				rapid transition.
				
				Values:
				point-to-point
				shared
				
				XPath: /extremeWing-config/profile[name=key1]/interface[name=key2]/spanningtree/link_type"
			DEFVAL { "point-to-point" }
			::= { extremeWingCfgProfIfSpanTreeEntry 1 }

		
		-- 1.3.6.1.4.1.1916.2.131.50.1.3.16.2.9.1.2
		extremeWingCfgProfIfSpanTreePortfast OBJECT-TYPE
			SYNTAX TruthValue
			MAX-ACCESS read-write
			STATUS current
			DESCRIPTION
				"Enable fast transitions.
				
				XPath: /extremeWing-config/profile[name=key1]/interface[name=key2]/spanningtree/portfast"
			DEFVAL { false }
			::= { extremeWingCfgProfIfSpanTreeEntry 2 }

		
		-- 1.3.6.1.4.1.1916.2.131.50.1.3.16.2.9.1.3
		extremeWingCfgProfIfSpanTreeEdgeport OBJECT-TYPE
			SYNTAX TruthValue
			MAX-ACCESS read-write
			STATUS current
			DESCRIPTION
				"Enable the port as an edge port.
				
				XPath: /extremeWing-config/profile[name=key1]/interface[name=key2]/spanningtree/edgeport"
			DEFVAL { false }
			::= { extremeWingCfgProfIfSpanTreeEntry 3 }

		
		-- 1.3.6.1.4.1.1916.2.131.50.1.3.16.2.9.1.4
		extremeWingCfgProfIfSpanTreeBpduguard OBJECT-TYPE
			SYNTAX DisplayString
			MAX-ACCESS read-write
			STATUS current
			DESCRIPTION
				"Guard the port against reception of BPDUs.
				
				Values:
				none
				enable
				disable
				
				XPath: /extremeWing-config/profile[name=key1]/interface[name=key2]/spanningtree/bpduguard"
			DEFVAL { "none" }
			::= { extremeWingCfgProfIfSpanTreeEntry 4 }

		
		-- 1.3.6.1.4.1.1916.2.131.50.1.3.16.2.9.1.5
		extremeWingCfgProfIfSpanTreeBpdufilter OBJECT-TYPE
			SYNTAX DisplayString
			MAX-ACCESS read-write
			STATUS current
			DESCRIPTION
				"Set the PortFast BPDU filter for the port.  Enabling the BPDU
				filter ensures that PortFast enabled ports do not transmit or
				receive BPDUs.
				
				Values:
				none
				enable
				disable
				
				XPath: /extremeWing-config/profile[name=key1]/interface[name=key2]/spanningtree/bpdufilter"
			DEFVAL { "none" }
			::= { extremeWingCfgProfIfSpanTreeEntry 5 }

		
		-- 1.3.6.1.4.1.1916.2.131.50.1.3.16.2.9.1.6
		extremeWingCfgProfIfSpanTreePortCiscoInterop OBJECT-TYPE
			SYNTAX DisplayString
			MAX-ACCESS read-write
			STATUS current
			DESCRIPTION
				"Enable interoperability with Cisco's version of MSTP,
				which is incompatible with standard MSTP.
				
				Values:
				enable
				disable
				
				XPath: /extremeWing-config/profile[name=key1]/interface[name=key2]/spanningtree/port_cisco_interop"
			DEFVAL { "disable" }
			::= { extremeWingCfgProfIfSpanTreeEntry 6 }

		
		-- 1.3.6.1.4.1.1916.2.131.50.1.3.16.2.9.1.7
		extremeWingCfgProfIfSpanTreeForceVersion OBJECT-TYPE
			SYNTAX Unsigned32 (0..3)
			MAX-ACCESS read-write
			STATUS current
			DESCRIPTION
				"Version identifier where 0=STP, 1=Not Supported, 2=RSTP,
				3=MSTP.
				
				XPath: /extremeWing-config/profile[name=key1]/interface[name=key2]/spanningtree/force_version"
			DEFVAL { 3 }
			::= { extremeWingCfgProfIfSpanTreeEntry 7 }

		
		-- 1.3.6.1.4.1.1916.2.131.50.1.3.16.2.9.1.8
		extremeWingCfgProfIfSpanTreeGuard OBJECT-TYPE
			SYNTAX DisplayString
			MAX-ACCESS read-write
			STATUS current
			DESCRIPTION
				"Setting 'root' disables reception of superior BPDUs.
				
				Values:
				none
				root
				
				XPath: /extremeWing-config/profile[name=key1]/interface[name=key2]/spanningtree/guard"
			DEFVAL { "none" }
			::= { extremeWingCfgProfIfSpanTreeEntry 8 }

		
		-- 1.3.6.1.4.1.1916.2.131.50.1.3.16.2.12
		extremeWingCfgProfIfWwanTable OBJECT-TYPE
			SYNTAX SEQUENCE OF ExtremeWingCfgProfIfWwanEntry
			MAX-ACCESS not-accessible
			STATUS current
			DESCRIPTION
				"
				
				/extremeWing-config/profile/interface"
			::= { extremeWingCfgProfIf 12 }

		
		-- 1.3.6.1.4.1.1916.2.131.50.1.3.16.2.12.1
		extremeWingCfgProfIfWwanEntry OBJECT-TYPE
			SYNTAX ExtremeWingCfgProfIfWwanEntry
			MAX-ACCESS not-accessible
			STATUS current
			DESCRIPTION
				"An entry in the table."
			INDEX { extremeWingCfgProfName, extremeWingCfgProfIfName }
			::= { extremeWingCfgProfIfWwanTable 1 }

		
		ExtremeWingCfgProfIfWwanEntry ::=
			SEQUENCE { 
				extremeWingCfgProfIfWwanApn
					DisplayString,
				extremeWingCfgProfIfWwanAuth
					DisplayString,
				extremeWingCfgProfIfWwanUser
					DisplayString,
				extremeWingCfgProfIfWwanPwd
					DisplayString,
				extremeWingCfgProfIfWwanDefaultRoutePriority
					Unsigned32
			 }

		-- 1.3.6.1.4.1.1916.2.131.50.1.3.16.2.12.1.2
		extremeWingCfgProfIfWwanApn OBJECT-TYPE
			SYNTAX DisplayString (SIZE (0..25))
			MAX-ACCESS read-write
			STATUS current
			DESCRIPTION
				"Access Point Name.
				
				XPath: /extremeWing-config/profile[name=key1]/interface[name=key2]/apn"
			DEFVAL { "" }
			::= { extremeWingCfgProfIfWwanEntry 2 }

		
		-- 1.3.6.1.4.1.1916.2.131.50.1.3.16.2.12.1.3
		extremeWingCfgProfIfWwanAuth OBJECT-TYPE
			SYNTAX DisplayString
			MAX-ACCESS read-write
			STATUS current
			DESCRIPTION
				"Authentication Type.
				
				Values:
				pap,
				chap,
				mschap,
				mschap-v2
				
				XPath: /extremeWing-config/profile[name=key1]/interface[name=key2]/auth"
			DEFVAL { "chap" }
			::= { extremeWingCfgProfIfWwanEntry 3 }

		
		-- 1.3.6.1.4.1.1916.2.131.50.1.3.16.2.12.1.4
		extremeWingCfgProfIfWwanUser OBJECT-TYPE
			SYNTAX DisplayString (SIZE (0..32))
			MAX-ACCESS read-write
			STATUS current
			DESCRIPTION
				"User Name.
				
				XPath: /extremeWing-config/profile[name=key1]/interface[name=key2]/user"
			DEFVAL { "" }
			::= { extremeWingCfgProfIfWwanEntry 4 }

		
		-- 1.3.6.1.4.1.1916.2.131.50.1.3.16.2.12.1.5
		extremeWingCfgProfIfWwanPwd OBJECT-TYPE
			SYNTAX DisplayString (SIZE (0..30))
			MAX-ACCESS read-write
			STATUS current
			DESCRIPTION
				"Password.
				
				XPath: /extremeWing-config/profile[name=key1]/interface[name=key2]/pwd"
			DEFVAL { "" }
			::= { extremeWingCfgProfIfWwanEntry 5 }

		
		-- 1.3.6.1.4.1.1916.2.131.50.1.3.16.2.12.1.6
		extremeWingCfgProfIfWwanDefaultRoutePriority OBJECT-TYPE
			SYNTAX Unsigned32 (1..8000)
			MAX-ACCESS read-write
			STATUS current
			DESCRIPTION
				"Priority for the default route learnt via Wireless WAN
				XPath: /extremeWing-config/profile[name=key1]/interface[name=key2]/wwan_default_route_priority"
			DEFVAL { 3000 }
			::= { extremeWingCfgProfIfWwanEntry 6 }

		
		-- 1.3.6.1.4.1.1916.2.131.50.1.3.16.2.13
		extremeWingCfgProfIfVlanOspfTable OBJECT-TYPE
			SYNTAX SEQUENCE OF ExtremeWingCfgProfIfVlanOspfEntry
			MAX-ACCESS not-accessible
			STATUS current
			DESCRIPTION
				"
				
				/extremeWing-config/profile/interface"
			::= { extremeWingCfgProfIf 13 }

		
		-- 1.3.6.1.4.1.1916.2.131.50.1.3.16.2.13.1
		extremeWingCfgProfIfVlanOspfEntry OBJECT-TYPE
			SYNTAX ExtremeWingCfgProfIfVlanOspfEntry
			MAX-ACCESS not-accessible
			STATUS current
			DESCRIPTION
				"An entry in the table."
			INDEX { extremeWingCfgProfName, extremeWingCfgProfIfName }
			::= { extremeWingCfgProfIfVlanOspfTable 1 }

		
		ExtremeWingCfgProfIfVlanOspfEntry ::=
			SEQUENCE { 
				extremeWingCfgProfIfVlanOspfOspfAuthentication
					DisplayString,
				extremeWingCfgProfIfVlanOspfOspfAuthKey
					DisplayString,
				extremeWingCfgProfIfVlanOspfOspfPriority
					Unsigned32,
				extremeWingCfgProfIfVlanOspfOspfCost
					Unsigned32,
				extremeWingCfgProfIfVlanOspfOspfBandWidth
					Unsigned32
			 }

		-- 1.3.6.1.4.1.1916.2.131.50.1.3.16.2.13.1.1
		extremeWingCfgProfIfVlanOspfOspfAuthentication OBJECT-TYPE
			SYNTAX DisplayString
			MAX-ACCESS read-write
			STATUS current
			DESCRIPTION
				"OSPF authentication type
				
				Values:
				simple-password,
				message-digest,
                                null,
				none
				
				XPath: /extremeWing-config/profile[name=key1]/interface[name=key2]/ospf_authentication"
			DEFVAL { "none" }
			::= { extremeWingCfgProfIfVlanOspfEntry 1 }

		
		-- 1.3.6.1.4.1.1916.2.131.50.1.3.16.2.13.1.2
		extremeWingCfgProfIfVlanOspfOspfAuthKey OBJECT-TYPE
			SYNTAX DisplayString
			MAX-ACCESS read-write
			STATUS current
			DESCRIPTION
				"Simple auth key for OSPF.
				
				XPath: /extremeWing-config/profile[name=key1]/interface[name=key2]/ospf_auth_key"
			::= { extremeWingCfgProfIfVlanOspfEntry 2 }

		
		-- 1.3.6.1.4.1.1916.2.131.50.1.3.16.2.13.1.3
		extremeWingCfgProfIfVlanOspfOspfPriority OBJECT-TYPE
			SYNTAX Unsigned32 (0..255)
			MAX-ACCESS read-write
			STATUS current
			DESCRIPTION
				"OSPF priority used in DR election
				
				XPath: /extremeWing-config/profile[name=key1]/interface[name=key2]/ospf_priority"
			DEFVAL { 0 }
			::= { extremeWingCfgProfIfVlanOspfEntry 3 }

		
		-- 1.3.6.1.4.1.1916.2.131.50.1.3.16.2.13.1.4
		extremeWingCfgProfIfVlanOspfOspfCost OBJECT-TYPE
			SYNTAX Unsigned32 (1..65535)
			MAX-ACCESS read-write
			STATUS current
			DESCRIPTION
				"Cost of this OSPF interface
				
				XPath: /extremeWing-config/profile[name=key1]/interface[name=key2]/ospf_cost"
			DEFVAL { 10 }
			::= { extremeWingCfgProfIfVlanOspfEntry 4 }

		
		-- 1.3.6.1.4.1.1916.2.131.50.1.3.16.2.13.1.5
		extremeWingCfgProfIfVlanOspfOspfBandWidth OBJECT-TYPE
			SYNTAX Unsigned32 (1..10000000)
			MAX-ACCESS read-write
			STATUS current
			DESCRIPTION
				"Bandwidth of the interface in Kbps.
				
				XPath: /extremeWing-config/profile[name=key1]/interface[name=key2]/bandwidth"
			::= { extremeWingCfgProfIfVlanOspfEntry 5 }

		
		-- 1.3.6.1.4.1.1916.2.131.50.1.3.16.2.14
		extremeWingCfgProfIfVlanOspfMsgDigestTable OBJECT-TYPE
			SYNTAX SEQUENCE OF ExtremeWingCfgProfIfVlanOspfMsgDigestEntry
			MAX-ACCESS not-accessible
			STATUS current
			DESCRIPTION
				"
				
				/extremeWing-config/profile/interface/ospf_message_digest_key"
			::= { extremeWingCfgProfIf 14 }

		
		-- 1.3.6.1.4.1.1916.2.131.50.1.3.16.2.14.1
		extremeWingCfgProfIfVlanOspfMsgDigestEntry OBJECT-TYPE
			SYNTAX ExtremeWingCfgProfIfVlanOspfMsgDigestEntry
			MAX-ACCESS not-accessible
			STATUS current
			DESCRIPTION
				"An entry in the table."
			INDEX { extremeWingCfgProfName, extremeWingCfgProfIfName, extremeWingCfgProfIfVlanOspfMsgDigestKeyId }
			::= { extremeWingCfgProfIfVlanOspfMsgDigestTable 1 }

		
		ExtremeWingCfgProfIfVlanOspfMsgDigestEntry ::=
			SEQUENCE { 
				extremeWingCfgProfIfVlanOspfMsgDigestKeyId
					Unsigned32,
				extremeWingCfgProfIfVlanOspfMsgDigestMessageDigest
					DisplayString
			 }

		-- 1.3.6.1.4.1.1916.2.131.50.1.3.16.2.14.1.1
		extremeWingCfgProfIfVlanOspfMsgDigestKeyId OBJECT-TYPE
			SYNTAX Unsigned32 (1..255)
			MAX-ACCESS read-only
			STATUS current
			DESCRIPTION
				"OSPF message digest auth key ID.
				
				XPath: /extremeWing-config/profile[name=key1]/interface[name=key2]/ospf_message_digest_key[key_id=key3]/key_id"
			::= { extremeWingCfgProfIfVlanOspfMsgDigestEntry 1 }

		
		-- 1.3.6.1.4.1.1916.2.131.50.1.3.16.2.14.1.3
		extremeWingCfgProfIfVlanOspfMsgDigestMessageDigest OBJECT-TYPE
			SYNTAX DisplayString
			MAX-ACCESS read-write
			STATUS current
			DESCRIPTION
				"OSPF message digest key.
				
				XPath: /extremeWing-config/profile[name=key1]/interface[name=key2]/ospf_message_digest_key[key_id=key3]/message_digest"
			::= { extremeWingCfgProfIfVlanOspfMsgDigestEntry 3 }

		
		-- 1.3.6.1.4.1.1916.2.131.50.1.3.16.2.15
		extremeWingCfgProfIfPppoeTable OBJECT-TYPE
			SYNTAX SEQUENCE OF ExtremeWingCfgProfIfPppoeEntry
			MAX-ACCESS not-accessible
			STATUS current
			DESCRIPTION
				"
				
				/extremeWing-config/profile/interface"
			::= { extremeWingCfgProfIf 15 }

		
		-- 1.3.6.1.4.1.1916.2.131.50.1.3.16.2.15.1
		extremeWingCfgProfIfPppoeEntry OBJECT-TYPE
			SYNTAX ExtremeWingCfgProfIfPppoeEntry
			MAX-ACCESS not-accessible
			STATUS current
			DESCRIPTION
				"An entry in the table."
			INDEX { extremeWingCfgProfName, extremeWingCfgProfIfName }
			::= { extremeWingCfgProfIfPppoeTable 1 }

		
		ExtremeWingCfgProfIfPppoeEntry ::=
			SEQUENCE { 
				extremeWingCfgProfIfPppoeAuthType
					DisplayString,
				extremeWingCfgProfIfPppoeIdleTime
					Unsigned32,
				extremeWingCfgProfIfPppoeKeepalive
					TruthValue,
				extremeWingCfgProfIfPppoeUsername
					DisplayString,
				extremeWingCfgProfIfPppoePassword
					DisplayString,
				extremeWingCfgProfIfPppoeService
					DisplayString,
				extremeWingCfgProfIfPppoeLocalnetVlan
					Unsigned32,
				extremeWingCfgProfIfPppoeMtu
					Unsigned32,
				extremeWingCfgProfIfPppoeDefaultRoutePriority
					Unsigned32,
				extremeWingCfgProfIfPppoeIp
					IpAddress
			 }

		-- 1.3.6.1.4.1.1916.2.131.50.1.3.16.2.15.1.1
		extremeWingCfgProfIfPppoeAuthType OBJECT-TYPE
			SYNTAX DisplayString
			MAX-ACCESS read-write
			STATUS current
			DESCRIPTION
				"PPPoE Client authentication type.
				
				Values:
				none,
				chap,
				mschap,
				mschap-v2,
				pap
				
				XPath: /extremeWing-config/profile[name=key1]/interface[name=key2]/auth-type"
			DEFVAL { "pap" }
			::= { extremeWingCfgProfIfPppoeEntry 1 }

		
		-- 1.3.6.1.4.1.1916.2.131.50.1.3.16.2.15.1.2
		extremeWingCfgProfIfPppoeIdleTime OBJECT-TYPE
			SYNTAX Unsigned32 (1..65535)
			UNITS "seconds"
			MAX-ACCESS read-write
			STATUS current
			DESCRIPTION
				"PPPoE client Idle Timeout.
				
				XPath: /extremeWing-config/profile[name=key1]/interface[name=key2]/idle-time"
			DEFVAL { 600 }
			::= { extremeWingCfgProfIfPppoeEntry 2 }

		
		-- 1.3.6.1.4.1.1916.2.131.50.1.3.16.2.15.1.3
		extremeWingCfgProfIfPppoeKeepalive OBJECT-TYPE
			SYNTAX TruthValue
			MAX-ACCESS read-write
			STATUS current
			DESCRIPTION
				"PPPoE client keep-alive mode.
				
				XPath: /extremeWing-config/profile[name=key1]/interface[name=key2]/keepalive"
			DEFVAL { false }
			::= { extremeWingCfgProfIfPppoeEntry 3 }

		
		-- 1.3.6.1.4.1.1916.2.131.50.1.3.16.2.15.1.4
		extremeWingCfgProfIfPppoeUsername OBJECT-TYPE
			SYNTAX DisplayString (SIZE (0..64))
			MAX-ACCESS read-write
			STATUS current
			DESCRIPTION
				"PPPoE client username.
				
				XPath: /extremeWing-config/profile[name=key1]/interface[name=key2]/username"
			DEFVAL { "" }
			::= { extremeWingCfgProfIfPppoeEntry 4 }

		
		-- 1.3.6.1.4.1.1916.2.131.50.1.3.16.2.15.1.5
		extremeWingCfgProfIfPppoePassword OBJECT-TYPE
			SYNTAX DisplayString (SIZE (0..64))
			MAX-ACCESS read-write
			STATUS current
			DESCRIPTION
				"PPPoE client password.
				
				XPath: /extremeWing-config/profile[name=key1]/interface[name=key2]/password"
			DEFVAL { "" }
			::= { extremeWingCfgProfIfPppoeEntry 5 }

		
		-- 1.3.6.1.4.1.1916.2.131.50.1.3.16.2.15.1.6
		extremeWingCfgProfIfPppoeService OBJECT-TYPE
			SYNTAX DisplayString (SIZE (0..128))
			MAX-ACCESS read-write
			STATUS current
			DESCRIPTION
				"PPPoE client service-name.
				
				XPath: /extremeWing-config/profile[name=key1]/interface[name=key2]/service"
			DEFVAL { "" }
			::= { extremeWingCfgProfIfPppoeEntry 6 }

		
		-- 1.3.6.1.4.1.1916.2.131.50.1.3.16.2.15.1.7
		extremeWingCfgProfIfPppoeLocalnetVlan OBJECT-TYPE
			SYNTAX Unsigned32 (1..4094)
			MAX-ACCESS read-write
			STATUS current
			DESCRIPTION
				"PPPoE client local network(vlan) connected to DSL modem.
				
				XPath: /extremeWing-config/profile[name=key1]/interface[name=key2]/localnet_vlan"
			DEFVAL { 1 }
			::= { extremeWingCfgProfIfPppoeEntry 7 }

		
		-- 1.3.6.1.4.1.1916.2.131.50.1.3.16.2.15.1.8
		extremeWingCfgProfIfPppoeMtu OBJECT-TYPE
			SYNTAX Unsigned32 (500..1492)
			MAX-ACCESS read-write
			STATUS current
			DESCRIPTION
				"PPPoE client Maximum Transmission Unit(MTU).
				
				XPath: /extremeWing-config/profile[name=key1]/interface[name=key2]/mtu"
			DEFVAL { 1492 }
			::= { extremeWingCfgProfIfPppoeEntry 8 }

		
		-- 1.3.6.1.4.1.1916.2.131.50.1.3.16.2.15.1.9
		extremeWingCfgProfIfPppoeDefaultRoutePriority OBJECT-TYPE
			SYNTAX Unsigned32 (1..8000)
			MAX-ACCESS read-write
			STATUS current
			DESCRIPTION
				"Priority for the default route learnt via PPPoE
				
				XPath: /extremeWing-config/profile[name=key1]/interface[name=key2]/pppoe_default_route_priority"
			DEFVAL { 2000 }
			::= { extremeWingCfgProfIfPppoeEntry 9 }

		
		-- 1.3.6.1.4.1.1916.2.131.50.1.3.16.2.15.1.10
		extremeWingCfgProfIfPppoeIp OBJECT-TYPE
			SYNTAX IpAddress
			MAX-ACCESS read-write
			STATUS current
			DESCRIPTION
				"PPPoE client IP address.
				
				XPath: /extremeWing-config/profile[name=key1]/interface[name=key2]/ip"
			DEFVAL { '00000000'h }
			::= { extremeWingCfgProfIfPppoeEntry 10 }

		
		-- 1.3.6.1.4.1.1916.2.131.50.1.3.16.2.16
		extremeWingCfgProfIfT1E1Table OBJECT-TYPE
			SYNTAX SEQUENCE OF ExtremeWingCfgProfIfT1E1Entry
			MAX-ACCESS not-accessible
			STATUS current
			DESCRIPTION
				"T1 or E1 interface (switched interface) configuration.
				
				/extremeWing-config/profile/interface"
			::= { extremeWingCfgProfIf 16 }

		
		-- 1.3.6.1.4.1.1916.2.131.50.1.3.16.2.16.1
		extremeWingCfgProfIfT1E1Entry OBJECT-TYPE
			SYNTAX ExtremeWingCfgProfIfT1E1Entry
			MAX-ACCESS not-accessible
			STATUS current
			DESCRIPTION
				"An entry in the table."
			INDEX { extremeWingCfgProfName, extremeWingCfgProfIfName }
			::= { extremeWingCfgProfIfT1E1Table 1 }

		
		ExtremeWingCfgProfIfT1E1Entry ::=
			SEQUENCE { 
				extremeWingCfgProfIfT1E1Media
					DisplayString,
				extremeWingCfgProfIfT1E1ClockMode
					DisplayString,
				extremeWingCfgProfIfT1E1HighImpedance
					DisplayString,
				extremeWingCfgProfIfT1E1LineBuildOut
					DisplayString,
				extremeWingCfgProfIfT1E1LineEncoding
					DisplayString,
				extremeWingCfgProfIfT1E1RxSensitivityLevel
					DisplayString
			 }

		-- 1.3.6.1.4.1.1916.2.131.50.1.3.16.2.16.1.1
		extremeWingCfgProfIfT1E1Media OBJECT-TYPE
			SYNTAX DisplayString
			MAX-ACCESS read-write
			STATUS current
			DESCRIPTION
				"The media type for the physical interface
				
				Values:
				t1
				e1
				
				XPath: /extremeWing-config/profile[name=key1]/interface[name=key2]/media"
			DEFVAL { "t1" }
			::= { extremeWingCfgProfIfT1E1Entry 1 }

		
		-- 1.3.6.1.4.1.1916.2.131.50.1.3.16.2.16.1.2
		extremeWingCfgProfIfT1E1ClockMode OBJECT-TYPE
			SYNTAX DisplayString
			MAX-ACCESS read-write
			STATUS current
			DESCRIPTION
				"The mode for the clock
				
				Values:
				normal
				master
				
				XPath: /extremeWing-config/profile[name=key1]/interface[name=key2]/clock_mode"
			DEFVAL { "normal" }
			::= { extremeWingCfgProfIfT1E1Entry 2 }

		
		-- 1.3.6.1.4.1.1916.2.131.50.1.3.16.2.16.1.3
		extremeWingCfgProfIfT1E1HighImpedance OBJECT-TYPE
			SYNTAX DisplayString
			MAX-ACCESS read-write
			STATUS current
			DESCRIPTION
				"High impedance mode
				
				Values:
				disable
				enable
				
				XPath: /extremeWing-config/profile[name=key1]/interface[name=key2]/high_impedance"
			DEFVAL { "disable" }
			::= { extremeWingCfgProfIfT1E1Entry 3 }

		
		-- 1.3.6.1.4.1.1916.2.131.50.1.3.16.2.16.1.4
		extremeWingCfgProfIfT1E1LineBuildOut OBJECT-TYPE
			SYNTAX DisplayString
			MAX-ACCESS read-write
			STATUS current
			DESCRIPTION
				"Line build out in decibels (dB) or feet (ft)
				
				Values:
				0-110ft
				0dB
				110-220ft
				15dB
				22.5dB
				220-330ft
				330-440ft
				440-550ft
				550-660ft
				7.5dB
				
				XPath: /extremeWing-config/profile[name=key1]/interface[name=key2]/line_build_out"
			DEFVAL { "0dB" }
			::= { extremeWingCfgProfIfT1E1Entry 4 }

		
		-- 1.3.6.1.4.1.1916.2.131.50.1.3.16.2.16.1.5
		extremeWingCfgProfIfT1E1LineEncoding OBJECT-TYPE
			SYNTAX DisplayString
			MAX-ACCESS read-write
			STATUS current
			DESCRIPTION
				"Line encoding type
				
				Values:
				ami
				b8zs
				
				XPath: /extremeWing-config/profile[name=key1]/interface[name=key2]/line_encoding"
			DEFVAL { "b8zs" }
			::= { extremeWingCfgProfIfT1E1Entry 5 }

		
		-- 1.3.6.1.4.1.1916.2.131.50.1.3.16.2.16.1.6
		extremeWingCfgProfIfT1E1RxSensitivityLevel OBJECT-TYPE
			SYNTAX DisplayString
			MAX-ACCESS read-write
			STATUS current
			DESCRIPTION
				"Receive sensitivity level in decibels
				
				Values:
				12dB
				18dB
				30dB
				36dB
				
				XPath: /extremeWing-config/profile[name=key1]/interface[name=key2]/rx_sensitivity_level"
			DEFVAL { "36dB" }
			::= { extremeWingCfgProfIfT1E1Entry 6 }

		
		-- 1.3.6.1.4.1.1916.2.131.50.1.3.16.2.17
		extremeWingCfgProfIfSerialTable OBJECT-TYPE
			SYNTAX SEQUENCE OF ExtremeWingCfgProfIfSerialEntry
			MAX-ACCESS not-accessible
			STATUS current
			DESCRIPTION
				"Serial interface (virtual interface) configuration.
				
				/extremeWing-config/profile/interface"
			::= { extremeWingCfgProfIf 17 }

		
		-- 1.3.6.1.4.1.1916.2.131.50.1.3.16.2.17.1
		extremeWingCfgProfIfSerialEntry OBJECT-TYPE
			SYNTAX ExtremeWingCfgProfIfSerialEntry
			MAX-ACCESS not-accessible
			STATUS current
			DESCRIPTION
				"An entry in the table."
			INDEX { extremeWingCfgProfName, extremeWingCfgProfIfName }
			::= { extremeWingCfgProfIfSerialTable 1 }

		
		ExtremeWingCfgProfIfSerialEntry ::=
			SEQUENCE { 
				extremeWingCfgProfIfSerialAuthentication
					DisplayString,
				extremeWingCfgProfIfSerialEncapsulation
					DisplayString,
				extremeWingCfgProfIfSerialLocalIpAddress
					DisplayString,
				extremeWingCfgProfIfSerialUsername
					DisplayString,
				extremeWingCfgProfIfSerialPassword
					DisplayString,
				extremeWingCfgProfIfSerialRemoteIpSubnet
					DisplayString
			 }

		-- 1.3.6.1.4.1.1916.2.131.50.1.3.16.2.17.1.1
		extremeWingCfgProfIfSerialAuthentication OBJECT-TYPE
			SYNTAX DisplayString
			MAX-ACCESS read-write
			STATUS current
			DESCRIPTION
				"Type of authentication
				
				Values:
				none
				pap
				chap
				
				XPath: /extremeWing-config/profile[name=key1]/interface[name=key2]/authentication"
			DEFVAL { "none" }
			::= { extremeWingCfgProfIfSerialEntry 1 }

		
		-- 1.3.6.1.4.1.1916.2.131.50.1.3.16.2.17.1.2
		extremeWingCfgProfIfSerialEncapsulation OBJECT-TYPE
			SYNTAX DisplayString
			MAX-ACCESS read-write
			STATUS current
			DESCRIPTION
				"The type of traffic that this group handles
				
				Values:
				chdlc
				hdlc
				ppp
				
				XPath: /extremeWing-config/profile[name=key1]/interface[name=key2]/encapsulation"
			DEFVAL { "ppp" }
			::= { extremeWingCfgProfIfSerialEntry 2 }

		
		-- 1.3.6.1.4.1.1916.2.131.50.1.3.16.2.17.1.3
		extremeWingCfgProfIfSerialLocalIpAddress OBJECT-TYPE
			SYNTAX DisplayString
			MAX-ACCESS read-write
			STATUS current
			DESCRIPTION
				"IP address assigned to the local system
				
				XPath: /extremeWing-config/profile[name=key1]/interface[name=key2]/local_ip_address"
			DEFVAL { "" }
			::= { extremeWingCfgProfIfSerialEntry 3 }

		
		-- 1.3.6.1.4.1.1916.2.131.50.1.3.16.2.17.1.4
		extremeWingCfgProfIfSerialUsername OBJECT-TYPE
			SYNTAX DisplayString (SIZE (0..32))
			MAX-ACCESS read-write
			STATUS current
			DESCRIPTION
				"Username provided by the service provider
				
				XPath: /extremeWing-config/profile[name=key1]/interface[name=key2]/username"
			DEFVAL { "" }
			::= { extremeWingCfgProfIfSerialEntry 4 }

		
		-- 1.3.6.1.4.1.1916.2.131.50.1.3.16.2.17.1.5
		extremeWingCfgProfIfSerialPassword OBJECT-TYPE
			SYNTAX DisplayString (SIZE (0..32))
			MAX-ACCESS read-write
			STATUS current
			DESCRIPTION
				"Password provided by the service provider
				
				XPath: /extremeWing-config/profile[name=key1]/interface[name=key2]/password"
			DEFVAL { "" }
			::= { extremeWingCfgProfIfSerialEntry 5 }

		
		-- 1.3.6.1.4.1.1916.2.131.50.1.3.16.2.17.1.6
		extremeWingCfgProfIfSerialRemoteIpSubnet OBJECT-TYPE
			SYNTAX DisplayString
			MAX-ACCESS read-write
			STATUS current
			DESCRIPTION
				"IP subnet assigned to the remote system along with subnet
				in CIDR notation - A.B.C.D/M
				
				XPath: /extremeWing-config/profile[name=key1]/interface[name=key2]/remote_ip_subnet"
			DEFVAL { "" }
			::= { extremeWingCfgProfIfSerialEntry 6 }

		
		-- 1.3.6.1.4.1.1916.2.131.50.1.3.16.2.18
		extremeWingCfgProfIfDot1xAuthTable OBJECT-TYPE
			SYNTAX SEQUENCE OF ExtremeWingCfgProfIfDot1xAuthEntry
			MAX-ACCESS not-accessible
			STATUS current
			DESCRIPTION
				"
				
				/extremeWing-config/profile/interface"
			::= { extremeWingCfgProfIf 18 }

		
		-- 1.3.6.1.4.1.1916.2.131.50.1.3.16.2.18.1
		extremeWingCfgProfIfDot1xAuthEntry OBJECT-TYPE
			SYNTAX ExtremeWingCfgProfIfDot1xAuthEntry
			MAX-ACCESS not-accessible
			STATUS current
			DESCRIPTION
				"An entry in the table."
			INDEX { extremeWingCfgProfName, extremeWingCfgProfIfName }
			::= { extremeWingCfgProfIfDot1xAuthTable 1 }

		
		ExtremeWingCfgProfIfDot1xAuthEntry ::=
			SEQUENCE { 
				extremeWingCfgProfIfDot1xAuthHostMode
					DisplayString,
				extremeWingCfgProfIfDot1xAuthGuestVlan
					Unsigned32,
				extremeWingCfgProfIfDot1xAuthPortControl
					DisplayString,
				extremeWingCfgProfIfDot1xAuthReauthenticate
					TruthValue,
				extremeWingCfgProfIfDot1xAuthMaxReauthCount
					Unsigned32,
				extremeWingCfgProfIfDot1xAuthMaxReq
					Unsigned32,
				extremeWingCfgProfIfDot1xAuthQuietPeriod
					Unsigned32,
				extremeWingCfgProfIfDot1xAuthReauthPeriod
					Unsigned32
			 }

		-- 1.3.6.1.4.1.1916.2.131.50.1.3.16.2.18.1.1
		extremeWingCfgProfIfDot1xAuthHostMode OBJECT-TYPE
			SYNTAX DisplayString
			MAX-ACCESS read-write
			STATUS current
			DESCRIPTION
				"Single or multi-host mode.
				
				Values:
				single-host,
				multi-host
				
				XPath: /extremeWing-config/profile[name=key1]/interface[name=key2]/host_mode"
			DEFVAL { "single-host" }
			::= { extremeWingCfgProfIfDot1xAuthEntry 1 }

		
		-- 1.3.6.1.4.1.1916.2.131.50.1.3.16.2.18.1.2
		extremeWingCfgProfIfDot1xAuthGuestVlan OBJECT-TYPE
			SYNTAX Unsigned32 (1..4094)
			MAX-ACCESS read-write
			STATUS current
			DESCRIPTION
				"Vlan onto which traffic is bridged if port is unauthorized and guest vlan is globally enabled
				
				XPath: /extremeWing-config/profile[name=key1]/interface[name=key2]/guest_vlan"
			::= { extremeWingCfgProfIfDot1xAuthEntry 2 }

		
		-- 1.3.6.1.4.1.1916.2.131.50.1.3.16.2.18.1.3
		extremeWingCfgProfIfDot1xAuthPortControl OBJECT-TYPE
			SYNTAX DisplayString
			MAX-ACCESS read-write
			STATUS current
			DESCRIPTION
				"Set 802.1x port state
				
				Values:
				auto,
				force-authorized,
				force-unauthorized
				
				XPath: /extremeWing-config/profile[name=key1]/interface[name=key2]/port_control"
			DEFVAL { "force-authorized" }
			::= { extremeWingCfgProfIfDot1xAuthEntry 3 }

		
		-- 1.3.6.1.4.1.1916.2.131.50.1.3.16.2.18.1.4
		extremeWingCfgProfIfDot1xAuthReauthenticate OBJECT-TYPE
			SYNTAX TruthValue
			MAX-ACCESS read-write
			STATUS current
			DESCRIPTION
				"Enable 802.1x re-authentication
				
				XPath: /extremeWing-config/profile[name=key1]/interface[name=key2]/reauthenticate"
			DEFVAL { false }
			::= { extremeWingCfgProfIfDot1xAuthEntry 4 }

		
		-- 1.3.6.1.4.1.1916.2.131.50.1.3.16.2.18.1.5
		extremeWingCfgProfIfDot1xAuthMaxReauthCount OBJECT-TYPE
			SYNTAX Unsigned32 (1..10)
			MAX-ACCESS read-write
			STATUS current
			DESCRIPTION
				"Number of reauthentication attempts before a port is moved to unauthorized
				
				XPath: /extremeWing-config/profile[name=key1]/interface[name=key2]/max_reauth_count"
			DEFVAL { 2 }
			::= { extremeWingCfgProfIfDot1xAuthEntry 5 }

		
		-- 1.3.6.1.4.1.1916.2.131.50.1.3.16.2.18.1.6
		extremeWingCfgProfIfDot1xAuthMaxReq OBJECT-TYPE
			SYNTAX Unsigned32 (1..10)
			MAX-ACCESS read-write
			STATUS current
			DESCRIPTION
				"Number of times 802.1x will retry authentication with the Radius Server before giving up and returning failed to the supplicant.
				
				XPath: /extremeWing-config/profile[name=key1]/interface[name=key2]/max_req"
			DEFVAL { 2 }
			::= { extremeWingCfgProfIfDot1xAuthEntry 6 }

		
		-- 1.3.6.1.4.1.1916.2.131.50.1.3.16.2.18.1.7
		extremeWingCfgProfIfDot1xAuthQuietPeriod OBJECT-TYPE
			SYNTAX Unsigned32 (1..65535)
			MAX-ACCESS read-write
			STATUS current
			DESCRIPTION
				"Time in seconds 802.1x will wait after authentication fails
				
				XPath: /extremeWing-config/profile[name=key1]/interface[name=key2]/quiet_period"
			DEFVAL { 60 }
			::= { extremeWingCfgProfIfDot1xAuthEntry 7 }

		
		-- 1.3.6.1.4.1.1916.2.131.50.1.3.16.2.18.1.8
		extremeWingCfgProfIfDot1xAuthReauthPeriod OBJECT-TYPE
			SYNTAX Unsigned32 (1..65535)
			MAX-ACCESS read-write
			STATUS current
			DESCRIPTION
				"Time in seconds until port is reauthenicated
				
				XPath: /extremeWing-config/profile[name=key1]/interface[name=key2]/reauth_period"
			DEFVAL { 60 }
			::= { extremeWingCfgProfIfDot1xAuthEntry 8 }

		
		-- 1.3.6.1.4.1.1916.2.131.50.1.3.16.2.19
		extremeWingCfgProfIfMeshpointBssmapTable OBJECT-TYPE
			SYNTAX SEQUENCE OF ExtremeWingCfgProfIfMeshpointBssmapEntry
			MAX-ACCESS not-accessible
			STATUS current
			DESCRIPTION
				"
				
				/extremeWing-config/profile/interface/meshpoint"
			::= { extremeWingCfgProfIf 19 }

		
		-- 1.3.6.1.4.1.1916.2.131.50.1.3.16.2.19.1
		extremeWingCfgProfIfMeshpointBssmapEntry OBJECT-TYPE
			SYNTAX ExtremeWingCfgProfIfMeshpointBssmapEntry
			MAX-ACCESS not-accessible
			STATUS current
			DESCRIPTION
				"An entry in the table."
			INDEX { extremeWingCfgProfName, extremeWingCfgProfIfName, extremeWingCfgProfIfMeshpointBssmapMeshpoint }
			::= { extremeWingCfgProfIfMeshpointBssmapTable 1 }

		
		ExtremeWingCfgProfIfMeshpointBssmapEntry ::=
			SEQUENCE { 
				extremeWingCfgProfIfMeshpointBssmapMeshpoint
					ExtremeWingIdentifier,
				extremeWingCfgProfIfMeshpointBssmapBss
					Unsigned32
			 }

		-- 1.3.6.1.4.1.1916.2.131.50.1.3.16.2.19.1.1
		extremeWingCfgProfIfMeshpointBssmapMeshpoint OBJECT-TYPE
			SYNTAX ExtremeWingIdentifier
			MAX-ACCESS read-write
			STATUS current
			DESCRIPTION
				"
				
				XPath: /extremeWing-config/profile[name=key1]/interface[name=key2]/meshpoint[meshpoint=key3]/meshpoint"
			::= { extremeWingCfgProfIfMeshpointBssmapEntry 1 }

		
		-- 1.3.6.1.4.1.1916.2.131.50.1.3.16.2.19.1.3
		extremeWingCfgProfIfMeshpointBssmapBss OBJECT-TYPE
			SYNTAX Unsigned32 (1..8)
			MAX-ACCESS read-write
			STATUS current
			DESCRIPTION
				"
				
				XPath: /extremeWing-config/profile[name=key1]/interface[name=key2]/meshpoint[meshpoint=key3]/bss"
			::= { extremeWingCfgProfIfMeshpointBssmapEntry 3 }

		
-- /extremeWing-config/profile/route
		-- 1.3.6.1.4.1.1916.2.131.50.1.3.16.5
		extremeWingCfgProfRoute OBJECT IDENTIFIER ::= { extremeWingCfgProf 5 }

		
		-- 1.3.6.1.4.1.1916.2.131.50.1.3.16.5.1
		extremeWingCfgProfRouteTable OBJECT-TYPE
			SYNTAX SEQUENCE OF ExtremeWingCfgProfRouteEntry
			MAX-ACCESS not-accessible
			STATUS current
			DESCRIPTION
				"Static IPv4 Route Table
				
				/extremeWing-config/profile/route"
			::= { extremeWingCfgProfRoute 1 }

		
		-- 1.3.6.1.4.1.1916.2.131.50.1.3.16.5.1.1
		extremeWingCfgProfRouteEntry OBJECT-TYPE
			SYNTAX ExtremeWingCfgProfRouteEntry
			MAX-ACCESS not-accessible
			STATUS current
			DESCRIPTION
				"An entry in the table."
			INDEX { extremeWingCfgProfName, extremeWingCfgProfRouteNetwork }
			::= { extremeWingCfgProfRouteTable 1 }

		
		ExtremeWingCfgProfRouteEntry ::=
			SEQUENCE { 
				extremeWingCfgProfRouteNetwork
					ExtremeWingIdentifier,
				extremeWingCfgProfRouteGateway
					ExtremeWingIdentifier
			 }

		-- 1.3.6.1.4.1.1916.2.131.50.1.3.16.5.1.1.1
		extremeWingCfgProfRouteNetwork OBJECT-TYPE
			SYNTAX ExtremeWingIdentifier
			MAX-ACCESS read-only
			STATUS current
			DESCRIPTION
				"
				
				XPath: /extremeWing-config/profile[name=key1]/route[network=key2]/network"
			::= { extremeWingCfgProfRouteEntry 1 }

		
		-- 1.3.6.1.4.1.1916.2.131.50.1.3.16.5.1.1.3
		extremeWingCfgProfRouteGateway OBJECT-TYPE
			SYNTAX ExtremeWingIdentifier
			MAX-ACCESS read-only
			STATUS current
			DESCRIPTION
				"
				
				XPath: /extremeWing-config/profile[name=key1]/route[network=key2]/gateway"
			::= { extremeWingCfgProfRouteEntry 3 }

		
-- /extremeWing-config/profile/ntp_server
		-- 1.3.6.1.4.1.1916.2.131.50.1.3.16.6
		extremeWingCfgProfNtpSvr OBJECT IDENTIFIER ::= { extremeWingCfgProf 6 }

		
		-- 1.3.6.1.4.1.1916.2.131.50.1.3.16.6.1
		extremeWingCfgProfNtpSvrTable OBJECT-TYPE
			SYNTAX SEQUENCE OF ExtremeWingCfgProfNtpSvrEntry
			MAX-ACCESS not-accessible
			STATUS current
			DESCRIPTION
				"
				
				/extremeWing-config/profile/ntp_server"
			::= { extremeWingCfgProfNtpSvr 1 }

		
		-- 1.3.6.1.4.1.1916.2.131.50.1.3.16.6.1.1
		extremeWingCfgProfNtpSvrEntry OBJECT-TYPE
			SYNTAX ExtremeWingCfgProfNtpSvrEntry
			MAX-ACCESS not-accessible
			STATUS current
			DESCRIPTION
				"An entry in the table."
			INDEX { extremeWingCfgProfName, extremeWingCfgProfNtpSvrServerIp }
			::= { extremeWingCfgProfNtpSvrTable 1 }

		
		ExtremeWingCfgProfNtpSvrEntry ::=
			SEQUENCE { 
				extremeWingCfgProfNtpSvrServerIp
					ExtremeWingIdentifier,
				extremeWingCfgProfNtpSvrAuthenkey
					Unsigned32,
				extremeWingCfgProfNtpSvrAutokey
					TruthValue,
				extremeWingCfgProfNtpSvrKeyStr
					DisplayString,
				extremeWingCfgProfNtpSvrPrefer
					TruthValue,
				extremeWingCfgProfNtpSvrVersion
					Unsigned32
			 }

		-- 1.3.6.1.4.1.1916.2.131.50.1.3.16.6.1.1.1
		extremeWingCfgProfNtpSvrServerIp OBJECT-TYPE
			SYNTAX ExtremeWingIdentifier
			MAX-ACCESS read-only
			STATUS current
			DESCRIPTION
				"ntp server ip address
				
				XPath: /extremeWing-config/profile[name=key1]/ntp_server[serverip=key2]/serverip"
			::= { extremeWingCfgProfNtpSvrEntry 1 }

		
		-- 1.3.6.1.4.1.1916.2.131.50.1.3.16.6.1.1.3
		extremeWingCfgProfNtpSvrAuthenkey OBJECT-TYPE
			SYNTAX Unsigned32 (0..65534)
			MAX-ACCESS read-write
			STATUS current
			DESCRIPTION
				"authentication peer key number
				
				XPath: /extremeWing-config/profile[name=key1]/ntp_server[serverip=key2]/authenkey"
			DEFVAL { 0 }
			::= { extremeWingCfgProfNtpSvrEntry 3 }

		
		-- 1.3.6.1.4.1.1916.2.131.50.1.3.16.6.1.1.4
		extremeWingCfgProfNtpSvrAutokey OBJECT-TYPE
			SYNTAX TruthValue
			MAX-ACCESS read-write
			STATUS current
			DESCRIPTION
				"enable/disable autokey configuration
				
				XPath: /extremeWing-config/profile[name=key1]/ntp_server[serverip=key2]/autokey"
			DEFVAL { false }
			::= { extremeWingCfgProfNtpSvrEntry 4 }

		
		-- 1.3.6.1.4.1.1916.2.131.50.1.3.16.6.1.1.5
		extremeWingCfgProfNtpSvrKeyStr OBJECT-TYPE
			SYNTAX DisplayString (SIZE (64))
			MAX-ACCESS read-write
			STATUS current
			DESCRIPTION
				"authentication key, valid when autokey is false
				
				XPath: /extremeWing-config/profile[name=key1]/ntp_server[serverip=key2]/key_str"
			::= { extremeWingCfgProfNtpSvrEntry 5 }

		
		-- 1.3.6.1.4.1.1916.2.131.50.1.3.16.6.1.1.6
		extremeWingCfgProfNtpSvrPrefer OBJECT-TYPE
			SYNTAX TruthValue
			MAX-ACCESS read-write
			STATUS current
			DESCRIPTION
				"whether this ntp server is preferred or not
				
				XPath: /extremeWing-config/profile[name=key1]/ntp_server[serverip=key2]/prefer"
			DEFVAL { false }
			::= { extremeWingCfgProfNtpSvrEntry 6 }

		
		-- 1.3.6.1.4.1.1916.2.131.50.1.3.16.6.1.1.7
		extremeWingCfgProfNtpSvrVersion OBJECT-TYPE
			SYNTAX Unsigned32 (0..4)
			MAX-ACCESS read-write
			STATUS current
			DESCRIPTION
				"the version number of this ntp server (1-4, 0:ignore)
				
				XPath: /extremeWing-config/profile[name=key1]/ntp_server[serverip=key2]/version"
			DEFVAL { 0 }
			::= { extremeWingCfgProfNtpSvrEntry 7 }

		
-- /extremeWing-config/profile/bridge_vlan
		-- 1.3.6.1.4.1.1916.2.131.50.1.3.16.7
		extremeWingCfgProfBridgeVlan OBJECT IDENTIFIER ::= { extremeWingCfgProf 7 }

		
		-- 1.3.6.1.4.1.1916.2.131.50.1.3.16.7.1
		extremeWingCfgProfBridgeVlanTable OBJECT-TYPE
			SYNTAX SEQUENCE OF ExtremeWingCfgProfBridgeVlanEntry
			MAX-ACCESS not-accessible
			STATUS current
			DESCRIPTION
				"
				
				/extremeWing-config/profile/bridge_vlan"
			::= { extremeWingCfgProfBridgeVlan 1 }

		
		-- 1.3.6.1.4.1.1916.2.131.50.1.3.16.7.1.1
		extremeWingCfgProfBridgeVlanEntry OBJECT-TYPE
			SYNTAX ExtremeWingCfgProfBridgeVlanEntry
			MAX-ACCESS not-accessible
			STATUS current
			DESCRIPTION
				"An entry in the table."
			INDEX { extremeWingCfgProfName, extremeWingCfgProfBridgeVlanId }
			::= { extremeWingCfgProfBridgeVlanTable 1 }

		
		ExtremeWingCfgProfBridgeVlanEntry ::=
			SEQUENCE { 
				extremeWingCfgProfBridgeVlanId
					Unsigned32,
				extremeWingCfgProfBridgeVlanDesc
					DisplayString,
				extremeWingCfgProfBridgeVlanEdgeVlan
					TruthValue,
				extremeWingCfgProfBridgeVlanBridgingMode
					DisplayString,
				extremeWingCfgProfBridgeVlanIpArpTrust
					TruthValue,
				extremeWingCfgProfBridgeVlanIpDhcpTrust
					TruthValue,
				extremeWingCfgProfBridgeVlanTunnelMacOutAcl
					ExtremeWingIdentifier,
				extremeWingCfgProfBridgeVlanTunnelIpOutAcl
					ExtremeWingIdentifier,
				extremeWingCfgProfBridgeVlanTunnelOverLevel2
					TruthValue
			 }

		-- 1.3.6.1.4.1.1916.2.131.50.1.3.16.7.1.1.1
		extremeWingCfgProfBridgeVlanId OBJECT-TYPE
			SYNTAX Unsigned32 (1..4095)
			MAX-ACCESS read-only
			STATUS current
			DESCRIPTION
				"
				
				XPath: /extremeWing-config/profile[name=key1]/bridge_vlan[vlan=key2]/vlan"
			::= { extremeWingCfgProfBridgeVlanEntry 1 }

		
		-- 1.3.6.1.4.1.1916.2.131.50.1.3.16.7.1.1.3
		extremeWingCfgProfBridgeVlanDesc OBJECT-TYPE
			SYNTAX DisplayString (SIZE (64))
			MAX-ACCESS read-write
			STATUS current
			DESCRIPTION
				"
				
				XPath: /extremeWing-config/profile[name=key1]/bridge_vlan[vlan=key2]/description"
			::= { extremeWingCfgProfBridgeVlanEntry 3 }

		
		-- 1.3.6.1.4.1.1916.2.131.50.1.3.16.7.1.1.4
		extremeWingCfgProfBridgeVlanEdgeVlan OBJECT-TYPE
			SYNTAX TruthValue
			MAX-ACCESS read-write
			STATUS current
			DESCRIPTION
				"
				
				XPath: /extremeWing-config/profile[name=key1]/bridge_vlan[vlan=key2]/edge_vlan"
			DEFVAL { true }
			::= { extremeWingCfgProfBridgeVlanEntry 4 }

		
		-- 1.3.6.1.4.1.1916.2.131.50.1.3.16.7.1.1.5
		extremeWingCfgProfBridgeVlanBridgingMode OBJECT-TYPE
			SYNTAX DisplayString
			MAX-ACCESS read-write
			STATUS current
			DESCRIPTION
				"
				
				Values:
				auto,
				local,
				tunnel,
				isolated-tunnel
				
				XPath: /extremeWing-config/profile[name=key1]/bridge_vlan[vlan=key2]/bridging_mode"
			DEFVAL { "auto" }
			::= { extremeWingCfgProfBridgeVlanEntry 5 }

		
		-- 1.3.6.1.4.1.1916.2.131.50.1.3.16.7.1.1.6
		extremeWingCfgProfBridgeVlanIpArpTrust OBJECT-TYPE
			SYNTAX TruthValue
			MAX-ACCESS read-write
			STATUS current
			DESCRIPTION
				"
				
				XPath: /extremeWing-config/profile[name=key1]/bridge_vlan[vlan=key2]/ip_arp_trust"
			DEFVAL { false }
			::= { extremeWingCfgProfBridgeVlanEntry 6 }

		
		-- 1.3.6.1.4.1.1916.2.131.50.1.3.16.7.1.1.7
		extremeWingCfgProfBridgeVlanIpDhcpTrust OBJECT-TYPE
			SYNTAX TruthValue
			MAX-ACCESS read-write
			STATUS current
			DESCRIPTION
				"
				
				XPath: /extremeWing-config/profile[name=key1]/bridge_vlan[vlan=key2]/ip_dhcp_trust"
			DEFVAL { false }
			::= { extremeWingCfgProfBridgeVlanEntry 7 }

		
		-- 1.3.6.1.4.1.1916.2.131.50.1.3.16.7.1.1.8
		extremeWingCfgProfBridgeVlanTunnelMacOutAcl OBJECT-TYPE
			SYNTAX ExtremeWingIdentifier
			MAX-ACCESS read-write
			STATUS current
			DESCRIPTION
				"
				
				XPath: /extremeWing-config/profile[name=key1]/bridge_vlan[vlan=key2]/tunnel_mac_out_acl"
			::= { extremeWingCfgProfBridgeVlanEntry 8 }

		
		-- 1.3.6.1.4.1.1916.2.131.50.1.3.16.7.1.1.9
		extremeWingCfgProfBridgeVlanTunnelIpOutAcl OBJECT-TYPE
			SYNTAX ExtremeWingIdentifier
			MAX-ACCESS read-write
			STATUS current
			DESCRIPTION
				"
				
				XPath: /extremeWing-config/profile[name=key1]/bridge_vlan[vlan=key2]/tunnel_ip_out_acl"
			::= { extremeWingCfgProfBridgeVlanEntry 9 }


		-- 1.3.6.1.4.1.1916.2.131.50.1.3.16.7.1.1.10
		extremeWingCfgProfBridgeVlanTunnelOverLevel2 OBJECT-TYPE
			SYNTAX TruthValue
			MAX-ACCESS read-write
			STATUS current
			DESCRIPTION
				"Allow extended VLAN traffic to be tunneled over level 2 links
				XPath: /extremeWing-config/profile[name=key1]/bridge_vlan[vlan=key2]/tunnel_over_level2
				"
			DEFVAL { false }
			::= { extremeWingCfgProfBridgeVlanEntry 10 }


		-- 1.3.6.1.4.1.1916.2.131.50.1.3.16.7.2
		extremeWingCfgProfBridgeVlanIgsTable OBJECT-TYPE
			SYNTAX SEQUENCE OF ExtremeWingCfgProfBridgeVlanIgsEntry
			MAX-ACCESS not-accessible
			STATUS current
			DESCRIPTION
				"
				
				/extremeWing-config/profile/bridge_vlan"
			::= { extremeWingCfgProfBridgeVlan 2 }

		
		-- 1.3.6.1.4.1.1916.2.131.50.1.3.16.7.2.1
		extremeWingCfgProfBridgeVlanIgsEntry OBJECT-TYPE
			SYNTAX ExtremeWingCfgProfBridgeVlanIgsEntry
			MAX-ACCESS not-accessible
			STATUS current
			DESCRIPTION
				"An entry in the table."
			INDEX { extremeWingCfgProfName, extremeWingCfgProfBridgeVlanId }
			::= { extremeWingCfgProfBridgeVlanIgsTable 1 }

		
		ExtremeWingCfgProfBridgeVlanIgsEntry ::=
			SEQUENCE { 
				extremeWingCfgProfBridgeVlanIgsIpIgs
					TruthValue,
				extremeWingCfgProfBridgeVlanIgsIpIgsQuerier
					TruthValue,
				extremeWingCfgProfBridgeVlanIgsIpIgsQuerierMaxResponseTime
					Unsigned32,
				extremeWingCfgProfBridgeVlanIgsIpIgsQuerierVersion
					Unsigned32,
				extremeWingCfgProfBridgeVlanIgsIpIgsQuerierAddress
					IpAddress,
				extremeWingCfgProfBridgeVlanIgsIpIgsOtherQuerierTimerExpiry
					Unsigned32,
				extremeWingCfgProfBridgeVlanIgsIpIgsForwardUnknownMcast
					TruthValue,
				extremeWingCfgProfBridgeVlanIgsIpIgsMrouterLearnPimDvmrp
					DisplayString
			 }

		-- 1.3.6.1.4.1.1916.2.131.50.1.3.16.7.2.1.1
		extremeWingCfgProfBridgeVlanIgsIpIgs OBJECT-TYPE
			SYNTAX TruthValue
			MAX-ACCESS read-write
			STATUS current
			DESCRIPTION
				"
				
				XPath: /extremeWing-config/profile[name=key1]/bridge_vlan[vlan=key2]/ip_igs"
			DEFVAL { true }
			::= { extremeWingCfgProfBridgeVlanIgsEntry 1 }

		
		-- 1.3.6.1.4.1.1916.2.131.50.1.3.16.7.2.1.2
		extremeWingCfgProfBridgeVlanIgsIpIgsQuerier OBJECT-TYPE
			SYNTAX TruthValue
			MAX-ACCESS read-write
			STATUS current
			DESCRIPTION
				"
				
				XPath: /extremeWing-config/profile[name=key1]/bridge_vlan[vlan=key2]/ip_igs_querier"
			DEFVAL { false }
			::= { extremeWingCfgProfBridgeVlanIgsEntry 2 }

		
		-- 1.3.6.1.4.1.1916.2.131.50.1.3.16.7.2.1.3
		extremeWingCfgProfBridgeVlanIgsIpIgsQuerierMaxResponseTime OBJECT-TYPE
			SYNTAX Unsigned32 (1..25)
			UNITS "seconds"
			MAX-ACCESS read-only
			STATUS current
			DESCRIPTION
				"
				
				XPath: /extremeWing-config/profile[name=key1]/bridge_vlan[vlan=key2]/ip_igs_querier_max_response_time"
			::= { extremeWingCfgProfBridgeVlanIgsEntry 3 }

		
		-- 1.3.6.1.4.1.1916.2.131.50.1.3.16.7.2.1.4
		extremeWingCfgProfBridgeVlanIgsIpIgsQuerierVersion OBJECT-TYPE
			SYNTAX Unsigned32 (1..3)
			MAX-ACCESS read-only
			STATUS current
			DESCRIPTION
				"
				
				XPath: /extremeWing-config/profile[name=key1]/bridge_vlan[vlan=key2]/ip_igs_querier_version"
			::= { extremeWingCfgProfBridgeVlanIgsEntry 4 }

		
		-- 1.3.6.1.4.1.1916.2.131.50.1.3.16.7.2.1.5
		extremeWingCfgProfBridgeVlanIgsIpIgsQuerierAddress OBJECT-TYPE
			SYNTAX IpAddress
			MAX-ACCESS read-write
			STATUS current
			DESCRIPTION
				"
				
				XPath: /extremeWing-config/profile[name=key1]/bridge_vlan[vlan=key2]/ip_igs_querier_address"
			::= { extremeWingCfgProfBridgeVlanIgsEntry 5 }

		
		-- 1.3.6.1.4.1.1916.2.131.50.1.3.16.7.2.1.6
		extremeWingCfgProfBridgeVlanIgsIpIgsOtherQuerierTimerExpiry OBJECT-TYPE
			SYNTAX Unsigned32 (60..300)
			UNITS "seconds"
			MAX-ACCESS read-only
			STATUS current
			DESCRIPTION
				"
				
				XPath: /extremeWing-config/profile[name=key1]/bridge_vlan[vlan=key2]/ip_igs_other_querier_timer_expiry"
			::= { extremeWingCfgProfBridgeVlanIgsEntry 6 }

		
		-- 1.3.6.1.4.1.1916.2.131.50.1.3.16.7.2.1.7
		extremeWingCfgProfBridgeVlanIgsIpIgsForwardUnknownMcast OBJECT-TYPE
			SYNTAX TruthValue
			MAX-ACCESS read-write
			STATUS current
			DESCRIPTION
				"
				
				XPath: /extremeWing-config/profile[name=key1]/bridge_vlan[vlan=key2]/ip_igs_forward_unknown_mcast"
			DEFVAL { false }
			::= { extremeWingCfgProfBridgeVlanIgsEntry 7 }

		
		-- 1.3.6.1.4.1.1916.2.131.50.1.3.16.7.2.1.8
		extremeWingCfgProfBridgeVlanIgsIpIgsMrouterLearnPimDvmrp OBJECT-TYPE
			SYNTAX DisplayString
			MAX-ACCESS read-write
			STATUS current
			DESCRIPTION
				"Interface name. Eg., ge1 radio1 ...
				
				XPath: /extremeWing-config/profile[name=key1]/bridge_vlan[vlan=key2]/ip_igs_mrouter_learn_pim_dvmrp"
			DEFVAL { "pim-dvmrp" }
			::= { extremeWingCfgProfBridgeVlanIgsEntry 8 }

		
--  /extremeWing-config/profile
		-- 1.3.6.1.4.1.1916.2.131.50.1.3.16.8
		extremeWingCfgProfClst OBJECT IDENTIFIER ::= { extremeWingCfgProf 8 }

		
		-- 1.3.6.1.4.1.1916.2.131.50.1.3.16.8.1
		extremeWingCfgProfClstTable OBJECT-TYPE
			SYNTAX SEQUENCE OF ExtremeWingCfgProfClstEntry
			MAX-ACCESS not-accessible
			STATUS current
			DESCRIPTION
				"SET available only with controller profile
				
				/extremeWing-config/profile"
			::= { extremeWingCfgProfClst 1 }

		
		-- 1.3.6.1.4.1.1916.2.131.50.1.3.16.8.1.1
		extremeWingCfgProfClstEntry OBJECT-TYPE
			SYNTAX ExtremeWingCfgProfClstEntry
			MAX-ACCESS not-accessible
			STATUS current
			DESCRIPTION
				"An entry in the table."
			INDEX { extremeWingCfgProfName }
			::= { extremeWingCfgProfClstTable 1 }

		
		ExtremeWingCfgProfClstEntry ::=
			SEQUENCE { 
				extremeWingCfgProfClstClstName
					ExtremeWingIdentifier,
				extremeWingCfgProfClstClstMemberVlan
					Unsigned32,
				extremeWingCfgProfClstClstMode
					DisplayString,
				extremeWingCfgProfClstClstMasterPriority
					Unsigned32,
				extremeWingCfgProfClstHandleStp
					TruthValue
			 }

		-- 1.3.6.1.4.1.1916.2.131.50.1.3.16.8.1.1.2
		extremeWingCfgProfClstClstName OBJECT-TYPE
			SYNTAX ExtremeWingIdentifier
			MAX-ACCESS read-write
			STATUS current
			DESCRIPTION
				"SET available only with controller profile
				
				XPath: /extremeWing-config/profile[name=key1]/cluster_name"
			::= { extremeWingCfgProfClstEntry 2 }

		
		-- 1.3.6.1.4.1.1916.2.131.50.1.3.16.8.1.1.3
		extremeWingCfgProfClstClstMemberVlan OBJECT-TYPE
			SYNTAX Unsigned32 (1..4094)
			MAX-ACCESS read-write
			STATUS current
			DESCRIPTION
				"VLAN on which cluster members are reachable
				SET available only with controller profile
				
				XPath: /extremeWing-config/profile[name=key1]/cluster_member_vlan"
			::= { extremeWingCfgProfClstEntry 3 }

		
		-- 1.3.6.1.4.1.1916.2.131.50.1.3.16.8.1.1.4
		extremeWingCfgProfClstClstMode OBJECT-TYPE
			SYNTAX DisplayString
			MAX-ACCESS read-write
			STATUS current
			DESCRIPTION
				"Cluster mode of operation.
				
				Values:
				active,
				standby
				
				SET available only with controller profile
				
				XPath: /extremeWing-config/profile[name=key1]/cluster_mode"
			DEFVAL { "active" }
			::= { extremeWingCfgProfClstEntry 4 }

		
		-- 1.3.6.1.4.1.1916.2.131.50.1.3.16.8.1.1.5
		extremeWingCfgProfClstClstMasterPriority OBJECT-TYPE
			SYNTAX Unsigned32 (1..255)
			MAX-ACCESS read-write
			STATUS current
			DESCRIPTION
				"Cluster master priority, lower value takes precedence
				SET available only with controller profile
				
				XPath: /extremeWing-config/profile[name=key1]/cluster_master_priority"
			DEFVAL { 128 }
			::= { extremeWingCfgProfClstEntry 5 }

		
		-- 1.3.6.1.4.1.1916.2.131.50.1.3.16.8.1.1.6
		extremeWingCfgProfClstHandleStp OBJECT-TYPE
			SYNTAX TruthValue
			MAX-ACCESS read-write
			STATUS current
			DESCRIPTION
				"SET available only with controller profile
				
				XPath: /extremeWing-config/profile[name=key1]/handle_stp"
			DEFVAL { false }
			::= { extremeWingCfgProfClstEntry 6 }


-- /extremeWing-config/profile/mint_link_cfg
		-- 1.3.6.1.4.1.1916.2.131.50.1.3.16.9
		extremeWingCfgProfMint OBJECT IDENTIFIER ::= { extremeWingCfgProf 9 }

		
		-- 1.3.6.1.4.1.1916.2.131.50.1.3.16.9.1
		extremeWingCfgProfMintTable OBJECT-TYPE
			SYNTAX SEQUENCE OF ExtremeWingCfgProfMintEntry
			MAX-ACCESS not-accessible
			STATUS current
			DESCRIPTION
				"
				
				/extremeWing-config/profile/mint_link_cfg"
			::= { extremeWingCfgProfMint 1 }

		
		-- 1.3.6.1.4.1.1916.2.131.50.1.3.16.9.1.1
		extremeWingCfgProfMintEntry OBJECT-TYPE
			SYNTAX ExtremeWingCfgProfMintEntry
			MAX-ACCESS not-accessible
			STATUS current
			DESCRIPTION
				"An entry in the table."
			INDEX { extremeWingCfgProfName }
			::= { extremeWingCfgProfMintTable 1 }

		
		ExtremeWingCfgProfMintEntry ::=
			SEQUENCE { 
				extremeWingCfgProfMintLevel1AreaId
					DisplayString,
				extremeWingCfgProfMintSpfLatency
					Unsigned32,
				extremeWingCfgProfMintDisPriorityAdjustment
					Integer32,
				extremeWingCfgProfMintMlcpVlan
					TruthValue,
				extremeWingCfgProfMintMlcpIp
					TruthValue,
				extremeWingCfgProfMintTunnelControllerLoadBalancingLevel1
					TruthValue
			 }

		-- 1.3.6.1.4.1.1916.2.131.50.1.3.16.9.1.1.1
		extremeWingCfgProfMintLevel1AreaId OBJECT-TYPE
			SYNTAX DisplayString
			MAX-ACCESS read-write
			STATUS current
			DESCRIPTION
				"
				
				XPath: /extremeWing-config/profile[name=key1]/mint_link_cfg/mint_level1_area_id"
			::= { extremeWingCfgProfMintEntry 1 }

		
		-- 1.3.6.1.4.1.1916.2.131.50.1.3.16.9.1.1.2
		extremeWingCfgProfMintSpfLatency OBJECT-TYPE
			SYNTAX Unsigned32 (0..60)
			UNITS "seconds"
			MAX-ACCESS read-write
			STATUS current
			DESCRIPTION
				"
				
				XPath: /extremeWing-config/profile[name=key1]/mint_link_cfg/mint_spf_latency"
			::= { extremeWingCfgProfMintEntry 2 }

		
		-- 1.3.6.1.4.1.1916.2.131.50.1.3.16.9.1.1.3
		extremeWingCfgProfMintDisPriorityAdjustment OBJECT-TYPE
			SYNTAX Integer32 (-255..255)
			MAX-ACCESS read-write
			STATUS current
			DESCRIPTION
				"value added to base level DIS priority to influence the DIS election. +1 increases DISiness.
				
				XPath: /extremeWing-config/profile[name=key1]/mint_link_cfg/mint_dis_priority_adjustment"
			DEFVAL { 0 }
			::= { extremeWingCfgProfMintEntry 3 }

		
		-- 1.3.6.1.4.1.1916.2.131.50.1.3.16.9.1.1.4
		extremeWingCfgProfMintMlcpVlan OBJECT-TYPE
			SYNTAX TruthValue
			MAX-ACCESS read-write
			STATUS current
			DESCRIPTION
				"MLCP for automated MiNT VLAN link creation
				
				XPath: /extremeWing-config/profile[name=key1]/mint_link_cfg/mint_mlcp_vlan"
			DEFVAL { true }
			::= { extremeWingCfgProfMintEntry 4 }

		
		-- 1.3.6.1.4.1.1916.2.131.50.1.3.16.9.1.1.5
		extremeWingCfgProfMintMlcpIp OBJECT-TYPE
			SYNTAX TruthValue
			MAX-ACCESS read-write
			STATUS current
			DESCRIPTION
				"MLCP for automated MiNT UDP/IP link creation
				
				XPath: /extremeWing-config/profile[name=key1]/mint_link_cfg/mint_mlcp_ip"
			DEFVAL { true }
			::= { extremeWingCfgProfMintEntry 5 }

		
		-- 1.3.6.1.4.1.1916.2.131.50.1.3.16.9.1.1.6
		extremeWingCfgProfMintTunnelControllerLoadBalancingLevel1 OBJECT-TYPE
			SYNTAX TruthValue
			MAX-ACCESS read-write
			STATUS current
			DESCRIPTION
				"MLCP for automated MiNT UDP/IP link creation
				
				XPath: /extremeWing-config/profile[name=key1]/mint_link_cfg/mint_tunnel_controller_load_balancing_level1"
			::= { extremeWingCfgProfMintEntry 6 }

		
-- /extremeWing-config/profile/dot11_cfg
		-- 1.3.6.1.4.1.1916.2.131.50.1.3.16.10
		extremeWingCfgProfDot11 OBJECT IDENTIFIER ::= { extremeWingCfgProf 10 }

		
		-- 1.3.6.1.4.1.1916.2.131.50.1.3.16.10.1
		extremeWingCfgProfDot11Table OBJECT-TYPE
			SYNTAX SEQUENCE OF ExtremeWingCfgProfDot11Entry
			MAX-ACCESS not-accessible
			STATUS current
			DESCRIPTION
				"802.11 global parameters for this device.
				
				/extremeWing-config/profile/dot11_cfg"
			::= { extremeWingCfgProfDot11 1 }

		
		-- 1.3.6.1.4.1.1916.2.131.50.1.3.16.10.1.1
		extremeWingCfgProfDot11Entry OBJECT-TYPE
			SYNTAX ExtremeWingCfgProfDot11Entry
			MAX-ACCESS not-accessible
			STATUS current
			DESCRIPTION
				"An entry in the table."
			INDEX { extremeWingCfgProfName }
			::= { extremeWingCfgProfDot11Table 1 }

		
		ExtremeWingCfgProfDot11Entry ::=
			SEQUENCE { 
				extremeWingCfgProfDot11WepSharedKeyAuth
					TruthValue,
				extremeWingCfgProfDot11LegacyAutoUpdateAp650
					TruthValue,
				extremeWingCfgProfDot11LegacyAutoUpdateImgAp7131
					DisplayString,
				extremeWingCfgProfDot11LegacyAutoDowngrade
					TruthValue,
				extremeWingCfgProfDot11NasIdentifier
					DisplayString,
				extremeWingCfgProfDot11NasPortId
					DisplayString
			 }

		-- 1.3.6.1.4.1.1916.2.131.50.1.3.16.10.1.1.1
		extremeWingCfgProfDot11WepSharedKeyAuth OBJECT-TYPE
			SYNTAX TruthValue
			MAX-ACCESS read-write
			STATUS current
			DESCRIPTION
				"Whether 802.11 shared key authentication is supported
				with WEP. Note: this method has known security vulnerabilities
				and its use is not recommended unless there are devices
				on the network that are only capable of
				shared-key authentication.
				
				XPath: /extremeWing-config/profile[name=key1]/dot11_cfg/wep_shared_key_auth"
			DEFVAL { false }
			::= { extremeWingCfgProfDot11Entry 1 }

		
		-- 1.3.6.1.4.1.1916.2.131.50.1.3.16.10.1.1.2
		extremeWingCfgProfDot11LegacyAutoUpdateAp650 OBJECT-TYPE
			SYNTAX TruthValue
			MAX-ACCESS read-write
			STATUS current
			DESCRIPTION
				"Whether legacy devices found on the network will automatically
				be updated to supported firmware.
				
				XPath: /extremeWing-config/profile[name=key1]/dot11_cfg/legacy_auto_update_ap650"
			DEFVAL { true }
			::= { extremeWingCfgProfDot11Entry 2 }

		
		-- 1.3.6.1.4.1.1916.2.131.50.1.3.16.10.1.1.3
		extremeWingCfgProfDot11LegacyAutoUpdateImgAp7131 OBJECT-TYPE
			SYNTAX DisplayString (SIZE (0..253))
			MAX-ACCESS read-write
			STATUS current
			DESCRIPTION
				"Path to the AP4700 legacy auto update image.
				
				XPath: /extremeWing-config/profile[name=key1]/dot11_cfg/legacy_auto_update_img_ap7131"
			DEFVAL { "" }
			::= { extremeWingCfgProfDot11Entry 3 }

		
		-- 1.3.6.1.4.1.1916.2.131.50.1.3.16.10.1.1.4
		extremeWingCfgProfDot11LegacyAutoDowngrade OBJECT-TYPE
			SYNTAX TruthValue
			MAX-ACCESS read-write
			STATUS current
			DESCRIPTION
				"Whether the AP4600 will connect to a legacy device and
				downgrade to be compatible with legacy devices.
				
				XPath: /extremeWing-config/profile[name=key1]/dot11_cfg/legacy_auto_downgrade"
			DEFVAL { true }
			::= { extremeWingCfgProfDot11Entry 4 }

		
		-- 1.3.6.1.4.1.1916.2.131.50.1.3.16.10.1.1.5
		extremeWingCfgProfDot11NasIdentifier OBJECT-TYPE
			SYNTAX DisplayString (SIZE (0..253))
			MAX-ACCESS read-write
			STATUS current
			DESCRIPTION
				"The RADIUS NAS-Identifier attribute which typically identifies
				the Access Point or Wireless Controller where the RADIUS
				message originates.
				
				XPath: /extremeWing-config/profile[name=key1]/dot11_cfg/nas_identifier"
			DEFVAL { "" }
			::= { extremeWingCfgProfDot11Entry 5 }

		
		-- 1.3.6.1.4.1.1916.2.131.50.1.3.16.10.1.1.6
		extremeWingCfgProfDot11NasPortId OBJECT-TYPE
			SYNTAX DisplayString (SIZE (0..253))
			MAX-ACCESS read-write
			STATUS current
			DESCRIPTION
				"The RADIUS NAS-Port-Id attribute which typically identifies
				the port of the device where the RADIUS messages originates.
				
				XPath: /extremeWing-config/profile[name=key1]/dot11_cfg/nas_port_id"
			DEFVAL { "" }
			::= { extremeWingCfgProfDot11Entry 6 }

		
-- /extremeWing-config/profile/crl_update_interval
		-- 1.3.6.1.4.1.1916.2.131.50.1.3.16.14
		extremeWingCfgProfCrlUpdate OBJECT IDENTIFIER ::= { extremeWingCfgProf 14 }

		
		-- 1.3.6.1.4.1.1916.2.131.50.1.3.16.14.1
		extremeWingCfgProfCrlUpdateTable OBJECT-TYPE
			SYNTAX SEQUENCE OF ExtremeWingCfgProfCrlUpdateEntry
			MAX-ACCESS not-accessible
			STATUS current
			DESCRIPTION
				"
				
				/extremeWing-config/profile/crl_update_interval"
			::= { extremeWingCfgProfCrlUpdate 1 }

		
		-- 1.3.6.1.4.1.1916.2.131.50.1.3.16.14.1.1
		extremeWingCfgProfCrlUpdateEntry OBJECT-TYPE
			SYNTAX ExtremeWingCfgProfCrlUpdateEntry
			MAX-ACCESS not-accessible
			STATUS current
			DESCRIPTION
				"An entry in the table."
			INDEX { extremeWingCfgProfName, extremeWingCfgProfCrlUpdateTrustpoint }
			::= { extremeWingCfgProfCrlUpdateTable 1 }

		
		ExtremeWingCfgProfCrlUpdateEntry ::=
			SEQUENCE { 
				extremeWingCfgProfCrlUpdateTrustpoint
					ExtremeWingIdentifier,
				extremeWingCfgProfCrlUpdateUrl
					DisplayString,
				extremeWingCfgProfCrlUpdateInterval
					Unsigned32
			 }

		-- 1.3.6.1.4.1.1916.2.131.50.1.3.16.14.1.1.1
		extremeWingCfgProfCrlUpdateTrustpoint OBJECT-TYPE
			SYNTAX ExtremeWingIdentifier
			MAX-ACCESS read-only
			STATUS current
			DESCRIPTION
				"
				
				XPath: /extremeWing-config/profile[name=key1]/crl_update_interval[trustpoint=key2]/trustpoint"
			::= { extremeWingCfgProfCrlUpdateEntry 1 }

		
		-- 1.3.6.1.4.1.1916.2.131.50.1.3.16.14.1.1.3
		extremeWingCfgProfCrlUpdateUrl OBJECT-TYPE
			SYNTAX DisplayString
			MAX-ACCESS read-write
			STATUS current
			DESCRIPTION
				"
				
				XPath: /extremeWing-config/profile[name=key1]/crl_update_interval[trustpoint=key2]/url"
			::= { extremeWingCfgProfCrlUpdateEntry 3 }

		
		-- 1.3.6.1.4.1.1916.2.131.50.1.3.16.14.1.1.4
		extremeWingCfgProfCrlUpdateInterval OBJECT-TYPE
			SYNTAX Unsigned32 (1..168)
			UNITS "hour"
			MAX-ACCESS read-write
			STATUS current
			DESCRIPTION
				"
				
				XPath: /extremeWing-config/profile[name=key1]/crl_update_interval[trustpoint=key2]/interval"
			::= { extremeWingCfgProfCrlUpdateEntry 4 }

		
-- /extremeWing-config/profile
		-- 1.3.6.1.4.1.1916.2.131.50.1.3.16.15
		extremeWingCfgProfNat OBJECT IDENTIFIER ::= { extremeWingCfgProf 15 }

		
		-- 1.3.6.1.4.1.1916.2.131.50.1.3.16.15.1
		extremeWingCfgProfNatPoolTable OBJECT-TYPE
			SYNTAX SEQUENCE OF ExtremeWingCfgProfNatPoolEntry
			MAX-ACCESS not-accessible
			STATUS current
			DESCRIPTION
				"
				
				/extremeWing-config/profile/nat_pool"
			::= { extremeWingCfgProfNat 1 }

		
		-- 1.3.6.1.4.1.1916.2.131.50.1.3.16.15.1.1
		extremeWingCfgProfNatPoolEntry OBJECT-TYPE
			SYNTAX ExtremeWingCfgProfNatPoolEntry
			MAX-ACCESS not-accessible
			STATUS current
			DESCRIPTION
				"An entry in the table."
			INDEX { extremeWingCfgProfName, extremeWingCfgProfNatPoolName }
			::= { extremeWingCfgProfNatPoolTable 1 }

		
		ExtremeWingCfgProfNatPoolEntry ::=
			SEQUENCE { 
				extremeWingCfgProfNatPoolName
					ExtremeWingIdentifier
			 }

		-- 1.3.6.1.4.1.1916.2.131.50.1.3.16.15.1.1.1
		extremeWingCfgProfNatPoolName OBJECT-TYPE
			SYNTAX ExtremeWingIdentifier
			MAX-ACCESS read-only
			STATUS current
			DESCRIPTION
				"Name of the NAT pool.
				
				XPath: /extremeWing-config/profile[name=key1]/nat_pool[name=key2]/name"
			::= { extremeWingCfgProfNatPoolEntry 1 }

		
		-- 1.3.6.1.4.1.1916.2.131.50.1.3.16.15.2
		extremeWingCfgProfNatPoolAddrTable OBJECT-TYPE
			SYNTAX SEQUENCE OF ExtremeWingCfgProfNatPoolAddrEntry
			MAX-ACCESS not-accessible
			STATUS current
			DESCRIPTION
				"
				
				/extremeWing-config/profile/nat_pool/address_range"
			::= { extremeWingCfgProfNat 2 }

		
		-- 1.3.6.1.4.1.1916.2.131.50.1.3.16.15.2.1
		extremeWingCfgProfNatPoolAddrEntry OBJECT-TYPE
			SYNTAX ExtremeWingCfgProfNatPoolAddrEntry
			MAX-ACCESS not-accessible
			STATUS current
			DESCRIPTION
				"An entry in the table."
			INDEX { extremeWingCfgProfName, extremeWingCfgProfNatPoolName, extremeWingCfgProfNatPoolAddrStartIp }
			::= { extremeWingCfgProfNatPoolAddrTable 1 }

		
		ExtremeWingCfgProfNatPoolAddrEntry ::=
			SEQUENCE { 
				extremeWingCfgProfNatPoolAddrStartIp
					ExtremeWingIdentifier,
				extremeWingCfgProfNatPoolAddrEndIp
					IpAddress
			 }

		-- 1.3.6.1.4.1.1916.2.131.50.1.3.16.15.2.1.1
		extremeWingCfgProfNatPoolAddrStartIp OBJECT-TYPE
			SYNTAX ExtremeWingIdentifier
			MAX-ACCESS read-only
			STATUS current
			DESCRIPTION
				"
				
				XPath: /extremeWing-config/profile[name=key1]/nat_pool[name=key2]/address_rage[start_ip=key3]/start_ip"
			::= { extremeWingCfgProfNatPoolAddrEntry 1 }

		
		-- 1.3.6.1.4.1.1916.2.131.50.1.3.16.15.2.1.3
		extremeWingCfgProfNatPoolAddrEndIp OBJECT-TYPE
			SYNTAX IpAddress 
			MAX-ACCESS read-write
			STATUS current
			DESCRIPTION
				"
				
				XPath: /extremeWing-config/profile[name=key1]/nat_pool[name=key2]/address_rage[start_ip=key3]/end_ip"
			::= { extremeWingCfgProfNatPoolAddrEntry 3 }

		
		-- 1.3.6.1.4.1.1916.2.131.50.1.3.16.15.7
		extremeWingCfgProfNatBridgeSrcDynamicTable OBJECT-TYPE
			SYNTAX SEQUENCE OF ExtremeWingCfgProfNatBridgeSrcDynamicEntry
			MAX-ACCESS not-accessible
			STATUS current
			DESCRIPTION
				"Description."
			::= { extremeWingCfgProfNat 7 }

		
		-- 1.3.6.1.4.1.1916.2.131.50.1.3.16.15.7.1
		extremeWingCfgProfNatBridgeSrcDynamicEntry OBJECT-TYPE
			SYNTAX ExtremeWingCfgProfNatBridgeSrcDynamicEntry
			MAX-ACCESS not-accessible
			STATUS current
			DESCRIPTION
				"An entry in the table."
			INDEX { extremeWingCfgProfName, extremeWingCfgProfNatBridgeSrcDynamicAcl }
			::= { extremeWingCfgProfNatBridgeSrcDynamicTable 1 }

		
		ExtremeWingCfgProfNatBridgeSrcDynamicEntry ::=
			SEQUENCE { 
				extremeWingCfgProfNatBridgeSrcDynamicAcl
					ExtremeWingIdentifier
			 }

		-- 1.3.6.1.4.1.1916.2.131.50.1.3.16.15.7.1.1
		extremeWingCfgProfNatBridgeSrcDynamicAcl OBJECT-TYPE
			SYNTAX ExtremeWingIdentifier
			MAX-ACCESS read-only
			STATUS current
			DESCRIPTION
				"ACL 
				
				XPath: /extremeWing-config/profile[name=key1]/bridge_source_dynamic_nat[acl=key2]/acl"
			::= { extremeWingCfgProfNatBridgeSrcDynamicEntry 1 }

		
		-- 1.3.6.1.4.1.1916.2.131.50.1.3.16.15.8
		extremeWingCfgProfNatBridgeSrcDynamicIfTable OBJECT-TYPE
			SYNTAX SEQUENCE OF ExtremeWingCfgProfNatBridgeSrcDynamicIfEntry
			MAX-ACCESS not-accessible
			STATUS current
			DESCRIPTION
				"Description."
			::= { extremeWingCfgProfNat 8 }

		
		-- 1.3.6.1.4.1.1916.2.131.50.1.3.16.15.8.1
		extremeWingCfgProfNatBridgeSrcDynamicIfEntry OBJECT-TYPE
			SYNTAX ExtremeWingCfgProfNatBridgeSrcDynamicIfEntry
			MAX-ACCESS not-accessible
			STATUS current
			DESCRIPTION
				"An entry in the table."
			INDEX { extremeWingCfgProfName, extremeWingCfgProfNatBridgeSrcDynamicAcl, extremeWingCfgProfNatBridgeSrcDynamicIfName }
			::= { extremeWingCfgProfNatBridgeSrcDynamicIfTable 1 }

		
		ExtremeWingCfgProfNatBridgeSrcDynamicIfEntry ::=
			SEQUENCE { 
				extremeWingCfgProfNatBridgeSrcDynamicIfName
					ExtremeWingIdentifier,
				extremeWingCfgProfNatBridgeSrcDynamicIfOverloadType
					DisplayString,
				extremeWingCfgProfNatBridgeSrcDynamicIfOverloadIp
					DisplayString,
				extremeWingCfgProfNatBridgeSrcDynamicIfNatPool
					DisplayString
			 }

		-- 1.3.6.1.4.1.1916.2.131.50.1.3.16.15.8.1.1
		extremeWingCfgProfNatBridgeSrcDynamicIfName OBJECT-TYPE
			SYNTAX ExtremeWingIdentifier
			MAX-ACCESS read-only
			STATUS current
			DESCRIPTION
				"The outgoing layer 3 interface for NAT.
				
				XPath: /extremeWing-config/profile[name=key1]/bridge_source_dynamic_nat[acl=key2]/interface_cfg[interface=key3]/interface"
			::= { extremeWingCfgProfNatBridgeSrcDynamicIfEntry 1 }

		
		-- 1.3.6.1.4.1.1916.2.131.50.1.3.16.15.8.1.3
		extremeWingCfgProfNatBridgeSrcDynamicIfOverloadType OBJECT-TYPE
			SYNTAX DisplayString
			MAX-ACCESS read-write
			STATUS current
			DESCRIPTION
				"Overload Type.
				
				XPath: /extremeWing-config/profile[name=key1]/bridge_source_dynamic_nat[acl=key2]/interface_cfg[interface=key3]/overload_type"
			::= { extremeWingCfgProfNatBridgeSrcDynamicIfEntry 3 }

		
		-- 1.3.6.1.4.1.1916.2.131.50.1.3.16.15.8.1.4
		extremeWingCfgProfNatBridgeSrcDynamicIfOverloadIp OBJECT-TYPE
			SYNTAX DisplayString
			MAX-ACCESS read-write
			STATUS current
			DESCRIPTION
				"Overload IP.
				
				XPath: /extremeWing-config/profile[name=key1]/bridge_source_dynamic_nat[acl=key2]/interface_cfg[interface=key3]/overload_ip"
			::= { extremeWingCfgProfNatBridgeSrcDynamicIfEntry 4 }

		
		-- 1.3.6.1.4.1.1916.2.131.50.1.3.16.15.8.1.5
		extremeWingCfgProfNatBridgeSrcDynamicIfNatPool OBJECT-TYPE
			SYNTAX DisplayString
			MAX-ACCESS read-write
			STATUS current
			DESCRIPTION
				"Nat Pool.
				
				XPath: /extremeWing-config/profile[name=key1]/bridge_source_dynamic_nat[acl=key2]/interface_cfg[interface=key3]/nat_pool"
			::= { extremeWingCfgProfNatBridgeSrcDynamicIfEntry 5 }

		
-- /extremeWing-config/profile
		-- 1.3.6.1.4.1.1916.2.131.50.1.3.16.18
		extremeWingCfgProfVpn OBJECT IDENTIFIER ::= { extremeWingCfgProf 18 }

		
		-- 1.3.6.1.4.1.1916.2.131.50.1.3.16.18.1
		extremeWingCfgProfVpnTable OBJECT-TYPE
			SYNTAX SEQUENCE OF ExtremeWingCfgProfVpnEntry
			MAX-ACCESS not-accessible
			STATUS current
			DESCRIPTION
				"
				
				/extremeWing-config/profile"
			::= { extremeWingCfgProfVpn 1 }

		
		-- 1.3.6.1.4.1.1916.2.131.50.1.3.16.18.1.1
		extremeWingCfgProfVpnEntry OBJECT-TYPE
			SYNTAX ExtremeWingCfgProfVpnEntry
			MAX-ACCESS not-accessible
			STATUS current
			DESCRIPTION
				"An entry in the table."
			INDEX { extremeWingCfgProfName }
			::= { extremeWingCfgProfVpnTable 1 }

		
		ExtremeWingCfgProfVpnEntry ::=
			SEQUENCE { 
				extremeWingCfgProfVpnLifetimeSeconds
					Unsigned32,
				extremeWingCfgProfVpnLifetimeKb
					Unsigned32,
				extremeWingCfgProfVpnIkev1GlobalDpdKeepalive
					Unsigned32,
				extremeWingCfgProfVpnIkev1GlobalDpdRetries
					Unsigned32,
				extremeWingCfgProfVpnIkev1GlobalNatKeepalive
					Unsigned32,
				extremeWingCfgProfVpnIkev2GlobalDpdKeepalive
					Unsigned32,
				extremeWingCfgProfVpnIkev2GlobalDpdRetries
					Unsigned32,
				extremeWingCfgProfVpnIkev2GlobalNatKeepalive
					Unsigned32,
				extremeWingCfgProfVpnCookieChallengeThreshold
					Unsigned32,
				extremeWingCfgProfVpnMaxInNegotiationSa
					Unsigned32,
				extremeWingCfgProfVpnDfBit
					DisplayString
			 }

		-- 1.3.6.1.4.1.1916.2.131.50.1.3.16.18.1.1.1
		extremeWingCfgProfVpnLifetimeSeconds OBJECT-TYPE
			SYNTAX Unsigned32 (120..2147483646)
			UNITS "seconds"
			MAX-ACCESS read-write
			STATUS current
			DESCRIPTION
				"Time-based IPsec security association lifetime.
				
				XPath: /extremeWing-config/profile[name=key1]/lifetime_seconds"
			DEFVAL { 3600 }
			::= { extremeWingCfgProfVpnEntry 1 }

		
		-- 1.3.6.1.4.1.1916.2.131.50.1.3.16.18.1.1.2
		extremeWingCfgProfVpnLifetimeKb OBJECT-TYPE
			SYNTAX Unsigned32 (500..2147483646)
			UNITS "kilobytes"
			MAX-ACCESS read-write
			STATUS current
			DESCRIPTION
				"Data-based IPsec security association lifetime.
				
				XPath: /extremeWing-config/profile[name=key1]/lifetime_kb"
			DEFVAL { 4608000 }
			::= { extremeWingCfgProfVpnEntry 2 }

		
		-- 1.3.6.1.4.1.1916.2.131.50.1.3.16.18.1.1.3
		extremeWingCfgProfVpnIkev1GlobalDpdKeepalive OBJECT-TYPE
			SYNTAX Unsigned32 (10..3600)
			UNITS "seconds"
			MAX-ACCESS read-write
			STATUS current
			DESCRIPTION
				"Global setting for frequency of IKE keepalive messages for Dead Peer Detection.
				
				XPath: /extremeWing-config/profile[name=key1]/ikev1_dpd_keepalive"
			DEFVAL { 30 }
			::= { extremeWingCfgProfVpnEntry 3 }

		
		-- 1.3.6.1.4.1.1916.2.131.50.1.3.16.18.1.1.4
		extremeWingCfgProfVpnIkev1GlobalDpdRetries OBJECT-TYPE
			SYNTAX Unsigned32 (1..100)
			MAX-ACCESS read-write
			STATUS current
			DESCRIPTION
				"Global setting for number of keepalive messages to send before declaring a peer dead.
				
				XPath: /extremeWing-config/profile[name=key1]/ikev1_dpd_retries"
			DEFVAL { 5 }
			::= { extremeWingCfgProfVpnEntry 4 }

		
		-- 1.3.6.1.4.1.1916.2.131.50.1.3.16.18.1.1.5
		extremeWingCfgProfVpnIkev1GlobalNatKeepalive OBJECT-TYPE
			SYNTAX Unsigned32 (10..3600)
			UNITS "seconds"
			MAX-ACCESS read-write
			STATUS current
			DESCRIPTION
				"Global setting for frequency of NAT keepalive messages.
				
				XPath: /extremeWing-config/profile[name=key1]/ikev1_nat_keepalive"
			DEFVAL { 20 }
			::= { extremeWingCfgProfVpnEntry 5 }

		
		-- 1.3.6.1.4.1.1916.2.131.50.1.3.16.18.1.1.6
		extremeWingCfgProfVpnIkev2GlobalDpdKeepalive OBJECT-TYPE
			SYNTAX Unsigned32 (10..3600)
			UNITS "seconds"
			MAX-ACCESS read-write
			STATUS current
			DESCRIPTION
				"Global setting for frequency of IKE keepalive messages for Dead Peer Detection.
				
				XPath: /extremeWing-config/profile[name=key1]/ikev2_dpd_keepalive"
			DEFVAL { 30 }
			::= { extremeWingCfgProfVpnEntry 6 }

		
		-- 1.3.6.1.4.1.1916.2.131.50.1.3.16.18.1.1.7
		extremeWingCfgProfVpnIkev2GlobalDpdRetries OBJECT-TYPE
			SYNTAX Unsigned32 (1..100)
			MAX-ACCESS read-write
			STATUS current
			DESCRIPTION
				"Global setting for number of keepalive messages to send before declaring a peer dead.
				
				XPath: /extremeWing-config/profile[name=key1]/ikev2_dpd_retries"
			DEFVAL { 5 }
			::= { extremeWingCfgProfVpnEntry 7 }

		
		-- 1.3.6.1.4.1.1916.2.131.50.1.3.16.18.1.1.8
		extremeWingCfgProfVpnIkev2GlobalNatKeepalive OBJECT-TYPE
			SYNTAX Unsigned32 (10..3600)
			UNITS "seconds"
			MAX-ACCESS read-write
			STATUS current
			DESCRIPTION
				"Global setting for frequency of NAT keepalive messages.
				
				XPath: /extremeWing-config/profile[name=key1]/ikev2_nat_keepalive"
			DEFVAL { 20 }
			::= { extremeWingCfgProfVpnEntry 8 }

		
		-- 1.3.6.1.4.1.1916.2.131.50.1.3.16.18.1.1.9
		extremeWingCfgProfVpnCookieChallengeThreshold OBJECT-TYPE
			SYNTAX Unsigned32 (1..100)
			MAX-ACCESS read-write
			STATUS current
			DESCRIPTION
				"Number of Half open IKE SA after which cookie challenge mechanism is enabled (IKEv2 only).
				
				XPath: /extremeWing-config/profile[name=key1]/cookie_challenge_threshold"
			DEFVAL { 5 }
			::= { extremeWingCfgProfVpnEntry 9 }

		
		-- 1.3.6.1.4.1.1916.2.131.50.1.3.16.18.1.1.10
		extremeWingCfgProfVpnMaxInNegotiationSa OBJECT-TYPE
			SYNTAX Unsigned32 (1..100)
			MAX-ACCESS read-write
			STATUS current
			DESCRIPTION
				"Maximum allowed half open IKE SAs (IKEv2 only).
				
				XPath: /extremeWing-config/profile[name=key1]/max_in_negotiation_sa"
			DEFVAL { 10 }
			::= { extremeWingCfgProfVpnEntry 10 }

		
		-- 1.3.6.1.4.1.1916.2.131.50.1.3.16.18.1.1.11
		extremeWingCfgProfVpnDfBit OBJECT-TYPE
			SYNTAX DisplayString
			MAX-ACCESS read-write
			STATUS current
			DESCRIPTION
				"Configure DF bit handling for esp encapsulating header
				
				Values:
				clear,
				set,
				copy
				
				XPath: /extremeWing-config/profile[name=key1]/df_bit"
			DEFVAL { "copy" }
			::= { extremeWingCfgProfVpnEntry 11 }

		
		-- 1.3.6.1.4.1.1916.2.131.50.1.3.16.18.2
		extremeWingCfgProfVpnIkev1Table OBJECT-TYPE
			SYNTAX SEQUENCE OF ExtremeWingCfgProfVpnIkev1Entry
			MAX-ACCESS not-accessible
			STATUS current
			DESCRIPTION
				"
				
				/extremeWing-config/profile/ikev1_policy"
			::= { extremeWingCfgProfVpn 2 }

		
		-- 1.3.6.1.4.1.1916.2.131.50.1.3.16.18.2.1
		extremeWingCfgProfVpnIkev1Entry OBJECT-TYPE
			SYNTAX ExtremeWingCfgProfVpnIkev1Entry
			MAX-ACCESS not-accessible
			STATUS current
			DESCRIPTION
				"An entry in the table."
			INDEX { extremeWingCfgProfName, extremeWingCfgProfVpnIkev1Name }
			::= { extremeWingCfgProfVpnIkev1Table 1 }

		
		ExtremeWingCfgProfVpnIkev1Entry ::=
			SEQUENCE { 
				extremeWingCfgProfVpnIkev1Name
					ExtremeWingIdentifier,
				extremeWingCfgProfVpnIkev1Mode
					DisplayString,
				extremeWingCfgProfVpnIkev1IsakmpLifetime
					Unsigned32,
				extremeWingCfgProfVpnIkev1DpdKeepalive
					Unsigned32,
				extremeWingCfgProfVpnIkev1DpdRetries
					Unsigned32
			 }

		-- 1.3.6.1.4.1.1916.2.131.50.1.3.16.18.2.1.1
		extremeWingCfgProfVpnIkev1Name OBJECT-TYPE
			SYNTAX ExtremeWingIdentifier
			MAX-ACCESS read-only
			STATUS current
			DESCRIPTION
				"
				
				XPath: /extremeWing-config/profile[name=key1]/ikev1_policy[name=key2]/name"
			::= { extremeWingCfgProfVpnIkev1Entry 1 }

		
		-- 1.3.6.1.4.1.1916.2.131.50.1.3.16.18.2.1.3
		extremeWingCfgProfVpnIkev1Mode OBJECT-TYPE
			SYNTAX DisplayString
			MAX-ACCESS read-write
			STATUS current
			DESCRIPTION
				"IKE version 1 mode of operation (main/aggressive).
				
				Values:
				main,
				aggressive
				
				XPath: /extremeWing-config/profile[name=key1]/ikev1_policy[name=key2]/mode"
			DEFVAL { "main" }
			::= { extremeWingCfgProfVpnIkev1Entry 3 }

		
		-- 1.3.6.1.4.1.1916.2.131.50.1.3.16.18.2.1.4
		extremeWingCfgProfVpnIkev1IsakmpLifetime OBJECT-TYPE
			SYNTAX Unsigned32 (600..2147483646)
			UNITS "seconds"
			MAX-ACCESS read-write
			STATUS current
			DESCRIPTION
				"Lifetime in seconds for IKE Security Association (ISAKMP SA).
				
				XPath: /extremeWing-config/profile[name=key1]/ikev1_policy[name=key2]/isakmp_lifetime"
			DEFVAL { 86400 }
			::= { extremeWingCfgProfVpnIkev1Entry 4 }

		
		-- 1.3.6.1.4.1.1916.2.131.50.1.3.16.18.2.1.5
		extremeWingCfgProfVpnIkev1DpdKeepalive OBJECT-TYPE
			SYNTAX Unsigned32 (10..3600)
			UNITS "seconds"
			MAX-ACCESS read-write
			STATUS current
			DESCRIPTION
				"Frequency of IKE keepalive messages for Dead Peer Detection.
				
				XPath: /extremeWing-config/profile[name=key1]/ikev1_policy[name=key2]/dpd_keepalive"
			DEFVAL { 30 }
			::= { extremeWingCfgProfVpnIkev1Entry 5 }

		
		-- 1.3.6.1.4.1.1916.2.131.50.1.3.16.18.2.1.6
		extremeWingCfgProfVpnIkev1DpdRetries OBJECT-TYPE
			SYNTAX Unsigned32 (1..100)
			MAX-ACCESS read-write
			STATUS current
			DESCRIPTION
				"Number of keepalive messages to send before declaring a peer dead.
				
				XPath: /extremeWing-config/profile[name=key1]/ikev1_policy[name=key2]/dpd_retries"
			DEFVAL { 5 }
			::= { extremeWingCfgProfVpnIkev1Entry 6 }

		
		-- 1.3.6.1.4.1.1916.2.131.50.1.3.16.18.3
		extremeWingCfgProfVpnIkev1IsakmpTable OBJECT-TYPE
			SYNTAX SEQUENCE OF ExtremeWingCfgProfVpnIkev1IsakmpEntry
			MAX-ACCESS not-accessible
			STATUS current
			DESCRIPTION
				"
				
				/extremeWing-config/profile/ikev1_policy/isakmp_proposal"
			::= { extremeWingCfgProfVpn 3 }

		
		-- 1.3.6.1.4.1.1916.2.131.50.1.3.16.18.3.1
		extremeWingCfgProfVpnIkev1IsakmpEntry OBJECT-TYPE
			SYNTAX ExtremeWingCfgProfVpnIkev1IsakmpEntry
			MAX-ACCESS not-accessible
			STATUS current
			DESCRIPTION
				"An entry in the table."
			INDEX { extremeWingCfgProfName, extremeWingCfgProfVpnIkev1Name, extremeWingCfgProfVpnIkev1IsakmpName }
			::= { extremeWingCfgProfVpnIkev1IsakmpTable 1 }

		
		ExtremeWingCfgProfVpnIkev1IsakmpEntry ::=
			SEQUENCE { 
				extremeWingCfgProfVpnIkev1IsakmpName
					ExtremeWingIdentifier,
				extremeWingCfgProfVpnIkev1IsakmpEncryption
					DisplayString,
				extremeWingCfgProfVpnIkev1IsakmpGroup
					DisplayString,
				extremeWingCfgProfVpnIkev1IsakmpHash
					DisplayString
			 }

		-- 1.3.6.1.4.1.1916.2.131.50.1.3.16.18.3.1.1
		extremeWingCfgProfVpnIkev1IsakmpName OBJECT-TYPE
			SYNTAX ExtremeWingIdentifier
			MAX-ACCESS read-only
			STATUS current
			DESCRIPTION
				"
				
				XPath: /extremeWing-config/profile[name=key1]/ikev1_policy[name=key2]/isakmp_proposal[name=key3]/name"
			::= { extremeWingCfgProfVpnIkev1IsakmpEntry 1 }

		
		-- 1.3.6.1.4.1.1916.2.131.50.1.3.16.18.3.1.3
		extremeWingCfgProfVpnIkev1IsakmpEncryption OBJECT-TYPE
			SYNTAX DisplayString
			MAX-ACCESS read-write
			STATUS current
			DESCRIPTION
				"Encryption method protecting data transmitted between peers.
				
				Values:
				3des,
				aes,
				aes-192,
				aes-256
				
				XPath: /extremeWing-config/profile[name=key1]/ikev1_policy[name=key2]/isakmp_proposal[name=key3]/encryption"
			DEFVAL { "aes-256" }
			::= { extremeWingCfgProfVpnIkev1IsakmpEntry 3 }

		
		-- 1.3.6.1.4.1.1916.2.131.50.1.3.16.18.3.1.4
		extremeWingCfgProfVpnIkev1IsakmpGroup OBJECT-TYPE
			SYNTAX DisplayString
			MAX-ACCESS read-write
			STATUS current
			DESCRIPTION
				"Diffie-Hellman group identifier. IPsec peers use the defined value to derive a shared secret without transmitting.
				
				Values:
				2,
				5,
				14
				
				XPath: /extremeWing-config/profile[name=key1]/ikev1_policy[name=key2]/isakmp_proposal[name=key3]/group"
			DEFVAL { "2" }
			::= { extremeWingCfgProfVpnIkev1IsakmpEntry 4 }

		
		-- 1.3.6.1.4.1.1916.2.131.50.1.3.16.18.3.1.5
		extremeWingCfgProfVpnIkev1IsakmpHash OBJECT-TYPE
			SYNTAX DisplayString
			MAX-ACCESS read-write
			STATUS current
			DESCRIPTION
				"Hash algorithm used to ensure data integrity.
				
				Values:
				md5,
				sha
				
				XPath: /extremeWing-config/profile[name=key1]/ikev1_policy[name=key2]/isakmp_proposal[name=key3]/hash"
			DEFVAL { "sha" }
			::= { extremeWingCfgProfVpnIkev1IsakmpEntry 5 }

		
		-- 1.3.6.1.4.1.1916.2.131.50.1.3.16.18.4
		extremeWingCfgProfVpnIkev2Table OBJECT-TYPE
			SYNTAX SEQUENCE OF ExtremeWingCfgProfVpnIkev2Entry
			MAX-ACCESS not-accessible
			STATUS current
			DESCRIPTION
				"
				
				/extremeWing-config/profile/ikev2_policy"
			::= { extremeWingCfgProfVpn 4 }

		
		-- 1.3.6.1.4.1.1916.2.131.50.1.3.16.18.4.1
		extremeWingCfgProfVpnIkev2Entry OBJECT-TYPE
			SYNTAX ExtremeWingCfgProfVpnIkev2Entry
			MAX-ACCESS not-accessible
			STATUS current
			DESCRIPTION
				"An entry in the table."
			INDEX { extremeWingCfgProfName, extremeWingCfgProfVpnIkev2Name }
			::= { extremeWingCfgProfVpnIkev2Table 1 }

		
		ExtremeWingCfgProfVpnIkev2Entry ::=
			SEQUENCE { 
				extremeWingCfgProfVpnIkev2Name
					ExtremeWingIdentifier,
				extremeWingCfgProfVpnIkev2IsakmpLifetime
					Unsigned32,
				extremeWingCfgProfVpnIkev2DpdKeepalive
					Unsigned32
			 }

		-- 1.3.6.1.4.1.1916.2.131.50.1.3.16.18.4.1.1
		extremeWingCfgProfVpnIkev2Name OBJECT-TYPE
			SYNTAX ExtremeWingIdentifier
			MAX-ACCESS read-only
			STATUS current
			DESCRIPTION
				"
				
				XPath: /extremeWing-config/profile[name=key1]/ikev2_policy[name=key2]/name"
			::= { extremeWingCfgProfVpnIkev2Entry 1 }

		
		-- 1.3.6.1.4.1.1916.2.131.50.1.3.16.18.4.1.3
		extremeWingCfgProfVpnIkev2IsakmpLifetime OBJECT-TYPE
			SYNTAX Unsigned32 (600..2147483646)
			UNITS "seconds"
			MAX-ACCESS read-write
			STATUS current
			DESCRIPTION
				"Lifetime in seconds for IKE Security Association (ISAKMP SA).
				
				XPath: /extremeWing-config/profile[name=key1]/ikev2_policy[name=key2]/isakmp_lifetime"
			DEFVAL { 86400 }
			::= { extremeWingCfgProfVpnIkev2Entry 3 }

		
		-- 1.3.6.1.4.1.1916.2.131.50.1.3.16.18.4.1.4
		extremeWingCfgProfVpnIkev2DpdKeepalive OBJECT-TYPE
			SYNTAX Unsigned32 (10..3600)
			UNITS "seconds"
			MAX-ACCESS read-write
			STATUS current
			DESCRIPTION
				"Frequency of IKE keepalive messages for Dead Peer Detection.
				
				XPath: /extremeWing-config/profile[name=key1]/ikev2_policy[name=key2]/dpd_keepalive"
			DEFVAL { 10 }
			::= { extremeWingCfgProfVpnIkev2Entry 4 }

		
		-- 1.3.6.1.4.1.1916.2.131.50.1.3.16.18.5
		extremeWingCfgProfVpnIkev2IsakmpTable OBJECT-TYPE
			SYNTAX SEQUENCE OF ExtremeWingCfgProfVpnIkev2IsakmpEntry
			MAX-ACCESS not-accessible
			STATUS current
			DESCRIPTION
				"
				
				/extremeWing-config/profile/ikev2_policy/isakmp_proposal"
			::= { extremeWingCfgProfVpn 5 }

		
		-- 1.3.6.1.4.1.1916.2.131.50.1.3.16.18.5.1
		extremeWingCfgProfVpnIkev2IsakmpEntry OBJECT-TYPE
			SYNTAX ExtremeWingCfgProfVpnIkev2IsakmpEntry
			MAX-ACCESS not-accessible
			STATUS current
			DESCRIPTION
				"An entry in the table."
			INDEX { extremeWingCfgProfName, extremeWingCfgProfVpnIkev2Name, extremeWingCfgProfVpnIkev2IsakmpName }
			::= { extremeWingCfgProfVpnIkev2IsakmpTable 1 }

		
		ExtremeWingCfgProfVpnIkev2IsakmpEntry ::=
			SEQUENCE { 
				extremeWingCfgProfVpnIkev2IsakmpName
					ExtremeWingIdentifier,
				extremeWingCfgProfVpnIkev2IsakmpEncryption
					DisplayString,
				extremeWingCfgProfVpnIkev2IsakmpGroup
					DisplayString,
				extremeWingCfgProfVpnIkev2IsakmpHash
					DisplayString
			 }

		-- 1.3.6.1.4.1.1916.2.131.50.1.3.16.18.5.1.1
		extremeWingCfgProfVpnIkev2IsakmpName OBJECT-TYPE
			SYNTAX ExtremeWingIdentifier
			MAX-ACCESS read-only
			STATUS current
			DESCRIPTION
				"
				
				XPath: /extremeWing-config/profile[name=key1]/ikev2_policy[name=key2]/isakmp_proposal[name=key3]/name"
			::= { extremeWingCfgProfVpnIkev2IsakmpEntry 1 }

		
		-- 1.3.6.1.4.1.1916.2.131.50.1.3.16.18.5.1.3
		extremeWingCfgProfVpnIkev2IsakmpEncryption OBJECT-TYPE
			SYNTAX DisplayString
			MAX-ACCESS read-write
			STATUS current
			DESCRIPTION
				"Encryption method protecting data transmitted between peers.
				
				Values:
				3des,
				aes,
				aes-192,
				aes-256
				
				XPath: /extremeWing-config/profile[name=key1]/ikev2_policy[name=key2]/isakmp_proposal[name=key3]/encryption"
			DEFVAL { "aes-256" }
			::= { extremeWingCfgProfVpnIkev2IsakmpEntry 3 }

		
		-- 1.3.6.1.4.1.1916.2.131.50.1.3.16.18.5.1.4
		extremeWingCfgProfVpnIkev2IsakmpGroup OBJECT-TYPE
			SYNTAX DisplayString
			MAX-ACCESS read-write
			STATUS current
			DESCRIPTION
				"Diffie-Hellman group identifier. IPsec peers use the defined value to derive a shared secret without transmitting.
				
				Values:
				2,
				5,
				14
				
				XPath: /extremeWing-config/profile[name=key1]/ikev2_policy[name=key2]/isakmp_proposal[name=key3]/group"
			DEFVAL { "2" }
			::= { extremeWingCfgProfVpnIkev2IsakmpEntry 4 }

		
		-- 1.3.6.1.4.1.1916.2.131.50.1.3.16.18.5.1.5
		extremeWingCfgProfVpnIkev2IsakmpHash OBJECT-TYPE
			SYNTAX DisplayString
			MAX-ACCESS read-write
			STATUS current
			DESCRIPTION
				"Hash algorithm used to ensure data integrity.
				
				Values:
				md5,
				sha
				
				XPath: /extremeWing-config/profile[name=key1]/ikev2_policy[name=key2]/isakmp_proposal[name=key3]/hash"
			DEFVAL { "sha" }
			::= { extremeWingCfgProfVpnIkev2IsakmpEntry 5 }

		
		-- 1.3.6.1.4.1.1916.2.131.50.1.3.16.18.6
		extremeWingCfgProfVpnIkev1PeerTable OBJECT-TYPE
			SYNTAX SEQUENCE OF ExtremeWingCfgProfVpnIkev1PeerEntry
			MAX-ACCESS not-accessible
			STATUS current
			DESCRIPTION
				"
				
				/extremeWing-config/profile/ikev1_peer"
			::= { extremeWingCfgProfVpn 6 }

		
		-- 1.3.6.1.4.1.1916.2.131.50.1.3.16.18.6.1
		extremeWingCfgProfVpnIkev1PeerEntry OBJECT-TYPE
			SYNTAX ExtremeWingCfgProfVpnIkev1PeerEntry
			MAX-ACCESS not-accessible
			STATUS current
			DESCRIPTION
				"An entry in the table."
			INDEX { extremeWingCfgProfName, extremeWingCfgProfVpnIkev1PeerName }
			::= { extremeWingCfgProfVpnIkev1PeerTable 1 }

		
		ExtremeWingCfgProfVpnIkev1PeerEntry ::=
			SEQUENCE { 
				extremeWingCfgProfVpnIkev1PeerName
					ExtremeWingIdentifier,
				extremeWingCfgProfVpnIkev1PeerIpType
					DisplayString,
				extremeWingCfgProfVpnIkev1PeerIpValue
					DisplayString,
				extremeWingCfgProfVpnIkev1PeerAuthType
					DisplayString,
				extremeWingCfgProfVpnIkev1PeerAuthKey
					DisplayString,
				extremeWingCfgProfVpnIkev1PeerLocalidType
					DisplayString,
				extremeWingCfgProfVpnIkev1PeerLocalidValue
					DisplayString,
				extremeWingCfgProfVpnIkev1PeerRemoteidType
					DisplayString,
				extremeWingCfgProfVpnIkev1PeerRemoteidValue
					DisplayString,
				extremeWingCfgProfVpnIkev1PeerIkev1Policy
					ExtremeWingIdentifier
			 }

		-- 1.3.6.1.4.1.1916.2.131.50.1.3.16.18.6.1.1
		extremeWingCfgProfVpnIkev1PeerName OBJECT-TYPE
			SYNTAX ExtremeWingIdentifier
			MAX-ACCESS read-only
			STATUS current
			DESCRIPTION
				"
				
				XPath: /extremeWing-config/profile[name=key1]/ikev1_peer[name=key2]/name"
			::= { extremeWingCfgProfVpnIkev1PeerEntry 1 }

		
		-- 1.3.6.1.4.1.1916.2.131.50.1.3.16.18.6.1.3
		extremeWingCfgProfVpnIkev1PeerIpType OBJECT-TYPE
			SYNTAX DisplayString
			MAX-ACCESS read-write
			STATUS current
			DESCRIPTION
				"IP address/fqdn of the IPSEC VPN peer for tunnel setup
				
				Values:
				address,
				fqdn
				
				XPath: /extremeWing-config/profile[name=key1]/ikev1_peer[name=key2]/ip/type"
			DEFVAL { "address" }
			::= { extremeWingCfgProfVpnIkev1PeerEntry 3 }

		
		-- 1.3.6.1.4.1.1916.2.131.50.1.3.16.18.6.1.4
		extremeWingCfgProfVpnIkev1PeerIpValue OBJECT-TYPE
			SYNTAX DisplayString (SIZE (1..64))
			MAX-ACCESS read-write
			STATUS current
			DESCRIPTION
				"Peer IP can be specified as either IP or FQDN.
				
				XPath: /extremeWing-config/profile[name=key1]/ikev1_peer[name=key2]/ip/value"
			::= { extremeWingCfgProfVpnIkev1PeerEntry 4 }

		
		-- 1.3.6.1.4.1.1916.2.131.50.1.3.16.18.6.1.5
		extremeWingCfgProfVpnIkev1PeerAuthType OBJECT-TYPE
			SYNTAX DisplayString
			MAX-ACCESS read-write
			STATUS current
			DESCRIPTION
				"
				
				Values:
				psk,
				rsa
				
				XPath: /extremeWing-config/profile[name=key1]/ikev1_peer[name=key2]/authentication/type"
			DEFVAL { "rsa" }
			::= { extremeWingCfgProfVpnIkev1PeerEntry 5 }

		
		-- 1.3.6.1.4.1.1916.2.131.50.1.3.16.18.6.1.6
		extremeWingCfgProfVpnIkev1PeerAuthKey OBJECT-TYPE
			SYNTAX DisplayString (SIZE (8..21))
			MAX-ACCESS read-write
			STATUS current
			DESCRIPTION
				"The shared secret used for peer authentication.
				
				XPath: /extremeWing-config/profile[name=key1]/ikev1_peer[name=key2]/authentication/key"
			::= { extremeWingCfgProfVpnIkev1PeerEntry 6 }

		
		-- 1.3.6.1.4.1.1916.2.131.50.1.3.16.18.6.1.7
		extremeWingCfgProfVpnIkev1PeerLocalidType OBJECT-TYPE
			SYNTAX DisplayString
			MAX-ACCESS read-write
			STATUS current
			DESCRIPTION
				"Local identity to use in IKE exchange with this peer.
				
				Values:
				address,
				dn,
				fqdn,
				email,
				string
				
				XPath: /extremeWing-config/profile[name=key1]/ikev1_peer[name=key2]/localid/localid_type"
			DEFVAL { "'string'" }
			::= { extremeWingCfgProfVpnIkev1PeerEntry 7 }

		
		-- 1.3.6.1.4.1.1916.2.131.50.1.3.16.18.6.1.8
		extremeWingCfgProfVpnIkev1PeerLocalidValue OBJECT-TYPE
			SYNTAX DisplayString (SIZE (1..128))
			MAX-ACCESS read-write
			STATUS current
			DESCRIPTION
				"
				
				XPath: /extremeWing-config/profile[name=key1]/ikev1_peer[name=key2]/localid/localid_value"
			::= { extremeWingCfgProfVpnIkev1PeerEntry 8 }

		
		-- 1.3.6.1.4.1.1916.2.131.50.1.3.16.18.6.1.9
		extremeWingCfgProfVpnIkev1PeerRemoteidType OBJECT-TYPE
			SYNTAX DisplayString
			MAX-ACCESS read-write
			STATUS current
			DESCRIPTION
				"Peer identity of this peer.
				
				Values:
				address,
				dn,
				fqdn,
				email,
				string
				
				XPath: /extremeWing-config/profile[name=key1]/ikev1_peer[name=key2]/remoteid/remoteid_type"
			DEFVAL { "'string'" }
			::= { extremeWingCfgProfVpnIkev1PeerEntry 9 }

		
		-- 1.3.6.1.4.1.1916.2.131.50.1.3.16.18.6.1.10
		extremeWingCfgProfVpnIkev1PeerRemoteidValue OBJECT-TYPE
			SYNTAX DisplayString (SIZE (1..128))
			MAX-ACCESS read-write
			STATUS current
			DESCRIPTION
				"
				
				XPath: /extremeWing-config/profile[name=key1]/ikev1_peer[name=key2]/remoteid/remoteid_value"
			::= { extremeWingCfgProfVpnIkev1PeerEntry 10 }

		
		-- 1.3.6.1.4.1.1916.2.131.50.1.3.16.18.6.1.11
		extremeWingCfgProfVpnIkev1PeerIkev1Policy OBJECT-TYPE
			SYNTAX ExtremeWingIdentifier
			MAX-ACCESS read-write
			STATUS current
			DESCRIPTION
				"
				
				XPath: /extremeWing-config/profile[name=key1]/ikev1_peer[name=key2]/ikev1_policy"
			::= { extremeWingCfgProfVpnIkev1PeerEntry 11 }

		
		-- 1.3.6.1.4.1.1916.2.131.50.1.3.16.18.7
		extremeWingCfgProfVpnIkev2PeerTable OBJECT-TYPE
			SYNTAX SEQUENCE OF ExtremeWingCfgProfVpnIkev2PeerEntry
			MAX-ACCESS not-accessible
			STATUS current
			DESCRIPTION
				"
				
				/extremeWing-config/profile/ikev2_peer"
			::= { extremeWingCfgProfVpn 7 }

		
		-- 1.3.6.1.4.1.1916.2.131.50.1.3.16.18.7.1
		extremeWingCfgProfVpnIkev2PeerEntry OBJECT-TYPE
			SYNTAX ExtremeWingCfgProfVpnIkev2PeerEntry
			MAX-ACCESS not-accessible
			STATUS current
			DESCRIPTION
				"An entry in the table."
			INDEX { extremeWingCfgProfName, extremeWingCfgProfVpnIkev2PeerName }
			::= { extremeWingCfgProfVpnIkev2PeerTable 1 }

		
		ExtremeWingCfgProfVpnIkev2PeerEntry ::=
			SEQUENCE { 
				extremeWingCfgProfVpnIkev2PeerName
					ExtremeWingIdentifier,
				extremeWingCfgProfVpnIkev2PeerIpType
					DisplayString,
				extremeWingCfgProfVpnIkev2PeerIpValue
					DisplayString,
				extremeWingCfgProfVpnIkev2PeerLocalAuthType
					DisplayString,
				extremeWingCfgProfVpnIkev2PeerLocalAuthKey
					DisplayString,
				extremeWingCfgProfVpnIkev2PeerRemoteAuthType
					DisplayString,
				extremeWingCfgProfVpnIkev2PeerRemoteAuthKey
					DisplayString,
				extremeWingCfgProfVpnIkev2PeerLocalidType
					DisplayString,
				extremeWingCfgProfVpnIkev2PeerLocalidValue
					DisplayString,
				extremeWingCfgProfVpnIkev2PeerRemoteidType
					DisplayString,
				extremeWingCfgProfVpnIkev2PeerRemoteidValue
					DisplayString,
				extremeWingCfgProfVpnIkev2PeerIkev2Policy
					ExtremeWingIdentifier
			 }

		-- 1.3.6.1.4.1.1916.2.131.50.1.3.16.18.7.1.1
		extremeWingCfgProfVpnIkev2PeerName OBJECT-TYPE
			SYNTAX ExtremeWingIdentifier
			MAX-ACCESS read-only
			STATUS current
			DESCRIPTION
				"
				
				XPath: /extremeWing-config/profile[name=key1]/ikev2_peer[name=key2]/name"
			::= { extremeWingCfgProfVpnIkev2PeerEntry 1 }

		
		-- 1.3.6.1.4.1.1916.2.131.50.1.3.16.18.7.1.3
		extremeWingCfgProfVpnIkev2PeerIpType OBJECT-TYPE
			SYNTAX DisplayString
			MAX-ACCESS read-write
			STATUS current
			DESCRIPTION
				"IP address/hostname of the IPSEC VPN peer for tunnel setup
				
				Values:
				address,
				fqdn
				
				XPath: /extremeWing-config/profile[name=key1]/ikev2_peer[name=key2]/ip/type"
			DEFVAL { "address" }
			::= { extremeWingCfgProfVpnIkev2PeerEntry 3 }

		
		-- 1.3.6.1.4.1.1916.2.131.50.1.3.16.18.7.1.4
		extremeWingCfgProfVpnIkev2PeerIpValue OBJECT-TYPE
			SYNTAX DisplayString (SIZE (1..64))
			MAX-ACCESS read-write
			STATUS current
			DESCRIPTION
				"Peer IP can be specified as either IP or FQDN.
				
				XPath: /extremeWing-config/profile[name=key1]/ikev2_peer[name=key2]/ip/value"
			::= { extremeWingCfgProfVpnIkev2PeerEntry 4 }

		
		-- 1.3.6.1.4.1.1916.2.131.50.1.3.16.18.7.1.5
		extremeWingCfgProfVpnIkev2PeerLocalAuthType OBJECT-TYPE
			SYNTAX DisplayString
			MAX-ACCESS read-write
			STATUS current
			DESCRIPTION
				"
				
				Values:
				psk,
				rsa
				
				XPath: /extremeWing-config/profile[name=key1]/ikev2_peer[name=key2]/local_authentication/type"
			DEFVAL { "rsa" }
			::= { extremeWingCfgProfVpnIkev2PeerEntry 5 }

		
		-- 1.3.6.1.4.1.1916.2.131.50.1.3.16.18.7.1.6
		extremeWingCfgProfVpnIkev2PeerLocalAuthKey OBJECT-TYPE
			SYNTAX DisplayString (SIZE (8..21))
			MAX-ACCESS read-write
			STATUS current
			DESCRIPTION
				"The shared secret used for local peer authentication.
				
				XPath: /extremeWing-config/profile[name=key1]/ikev2_peer[name=key2]/local_authentication/key"
			::= { extremeWingCfgProfVpnIkev2PeerEntry 6 }

		
		-- 1.3.6.1.4.1.1916.2.131.50.1.3.16.18.7.1.7
		extremeWingCfgProfVpnIkev2PeerRemoteAuthType OBJECT-TYPE
			SYNTAX DisplayString
			MAX-ACCESS read-write
			STATUS current
			DESCRIPTION
				"
				
				Values:
				psk,
				rsa
				
				XPath: /extremeWing-config/profile[name=key1]/ikev2_peer[name=key2]/remote_authentication/type"
			DEFVAL { "rsa" }
			::= { extremeWingCfgProfVpnIkev2PeerEntry 7 }

		
		-- 1.3.6.1.4.1.1916.2.131.50.1.3.16.18.7.1.8
		extremeWingCfgProfVpnIkev2PeerRemoteAuthKey OBJECT-TYPE
			SYNTAX DisplayString (SIZE (8..21))
			MAX-ACCESS read-write
			STATUS current
			DESCRIPTION
				"The shared secret used for remote peer authentication.
				
				XPath: /extremeWing-config/profile[name=key1]/ikev2_peer[name=key2]/remote_authentication/key"
			::= { extremeWingCfgProfVpnIkev2PeerEntry 8 }

		
		-- 1.3.6.1.4.1.1916.2.131.50.1.3.16.18.7.1.9
		extremeWingCfgProfVpnIkev2PeerLocalidType OBJECT-TYPE
			SYNTAX DisplayString
			MAX-ACCESS read-write
			STATUS current
			DESCRIPTION
				"Local identity to use in IKE exchange with this peer.
				
				Values:
				address,
				dn,
				fqdn,
				email,
				string
				
				XPath: /extremeWing-config/profile[name=key1]/ikev2_peer[name=key2]/localid/localid_type"
			DEFVAL { "'string'" }
			::= { extremeWingCfgProfVpnIkev2PeerEntry 9 }

		
		-- 1.3.6.1.4.1.1916.2.131.50.1.3.16.18.7.1.10
		extremeWingCfgProfVpnIkev2PeerLocalidValue OBJECT-TYPE
			SYNTAX DisplayString (SIZE (1..128))
			MAX-ACCESS read-write
			STATUS current
			DESCRIPTION
				"
				
				XPath: /extremeWing-config/profile[name=key1]/ikev2_peer[name=key2]/localid/localid_value"
			::= { extremeWingCfgProfVpnIkev2PeerEntry 10 }

		
		-- 1.3.6.1.4.1.1916.2.131.50.1.3.16.18.7.1.11
		extremeWingCfgProfVpnIkev2PeerRemoteidType OBJECT-TYPE
			SYNTAX DisplayString
			MAX-ACCESS read-write
			STATUS current
			DESCRIPTION
				"Peer identity of this peer.
				
				Values:
				address,
				dn,
				fqdn,
				email,
				string
				
				XPath: /extremeWing-config/profile[name=key1]/ikev2_peer[name=key2]/remoteid/remoteid_type"
			DEFVAL { "'string'" }
			::= { extremeWingCfgProfVpnIkev2PeerEntry 11 }

		
		-- 1.3.6.1.4.1.1916.2.131.50.1.3.16.18.7.1.12
		extremeWingCfgProfVpnIkev2PeerRemoteidValue OBJECT-TYPE
			SYNTAX DisplayString (SIZE (1..128))
			MAX-ACCESS read-write
			STATUS current
			DESCRIPTION
				"
				
				XPath: /extremeWing-config/profile[name=key1]/ikev2_peer[name=key2]/remoteid/remoteid_value"
			::= { extremeWingCfgProfVpnIkev2PeerEntry 12 }

		
		-- 1.3.6.1.4.1.1916.2.131.50.1.3.16.18.7.1.13
		extremeWingCfgProfVpnIkev2PeerIkev2Policy OBJECT-TYPE
			SYNTAX ExtremeWingIdentifier
			MAX-ACCESS read-write
			STATUS current
			DESCRIPTION
				"IKEv2 Policy to use with this peer.
				
				XPath: /extremeWing-config/profile[name=key1]/ikev2_peer[name=key2]/ikev2_policy"
			::= { extremeWingCfgProfVpnIkev2PeerEntry 13 }

		
		-- 1.3.6.1.4.1.1916.2.131.50.1.3.16.18.8
		extremeWingCfgProfVpnTransformTable OBJECT-TYPE
			SYNTAX SEQUENCE OF ExtremeWingCfgProfVpnTransformEntry
			MAX-ACCESS not-accessible
			STATUS current
			DESCRIPTION
				"
				
				/extremeWing-config/profile/ipsec_transform_set"
			::= { extremeWingCfgProfVpn 8 }

		
		-- 1.3.6.1.4.1.1916.2.131.50.1.3.16.18.8.1
		extremeWingCfgProfVpnTransformEntry OBJECT-TYPE
			SYNTAX ExtremeWingCfgProfVpnTransformEntry
			MAX-ACCESS not-accessible
			STATUS current
			DESCRIPTION
				"An entry in the table."
			INDEX { extremeWingCfgProfName, extremeWingCfgProfVpnTransformName }
			::= { extremeWingCfgProfVpnTransformTable 1 }

		
		ExtremeWingCfgProfVpnTransformEntry ::=
			SEQUENCE { 
				extremeWingCfgProfVpnTransformName
					ExtremeWingIdentifier,
				extremeWingCfgProfVpnTransformCipherAlgo
					DisplayString,
				extremeWingCfgProfVpnTransformAuthAlgo
					DisplayString,
				extremeWingCfgProfVpnTransformMode
					DisplayString
			 }

		-- 1.3.6.1.4.1.1916.2.131.50.1.3.16.18.8.1.1
		extremeWingCfgProfVpnTransformName OBJECT-TYPE
			SYNTAX ExtremeWingIdentifier
			MAX-ACCESS read-only
			STATUS current
			DESCRIPTION
				"
				
				XPath: /extremeWing-config/profile[name=key1]/ipsec_transform_set[name=key2]/name"
			::= { extremeWingCfgProfVpnTransformEntry 1 }

		
		-- 1.3.6.1.4.1.1916.2.131.50.1.3.16.18.8.1.3
		extremeWingCfgProfVpnTransformCipherAlgo OBJECT-TYPE
			SYNTAX DisplayString
			MAX-ACCESS read-write
			STATUS current
			DESCRIPTION
				"Encryption method protecting data transmission.
				
				Values:
				esp-null,
				des,
				3des,
				aes,
				aes-192,
				aes-256
				
				XPath: /extremeWing-config/profile[name=key1]/ipsec_transform_set[name=key2]/cipher_algo"
			DEFVAL { "aes-256" }
			::= { extremeWingCfgProfVpnTransformEntry 3 }

		
		-- 1.3.6.1.4.1.1916.2.131.50.1.3.16.18.8.1.4
		extremeWingCfgProfVpnTransformAuthAlgo OBJECT-TYPE
			SYNTAX DisplayString
			MAX-ACCESS read-write
			STATUS current
			DESCRIPTION
				"Authentication scheme used to validate identity.
				
				Values:
				md5-hmac,
				sha-hmac
				
				XPath: /extremeWing-config/profile[name=key1]/ipsec_transform_set[name=key2]/auth_algo"
			DEFVAL { "sha-hmac" }
			::= { extremeWingCfgProfVpnTransformEntry 4 }

		
		-- 1.3.6.1.4.1.1916.2.131.50.1.3.16.18.8.1.5
		extremeWingCfgProfVpnTransformMode OBJECT-TYPE
			SYNTAX DisplayString
			MAX-ACCESS read-write
			STATUS current
			DESCRIPTION
				"IPsec tunnel type - tunnel mode is used for site-to-site vpn and transport mode is used to remote-vpn.
				
				Values:
				tunnel,
				transport
				
				XPath: /extremeWing-config/profile[name=key1]/ipsec_transform_set[name=key2]/mode"
			DEFVAL { "tunnel" }
			::= { extremeWingCfgProfVpnTransformEntry 5 }

		
		-- 1.3.6.1.4.1.1916.2.131.50.1.3.16.18.9
		extremeWingCfgProfVpnCryptoTable OBJECT-TYPE
			SYNTAX SEQUENCE OF ExtremeWingCfgProfVpnCryptoEntry
			MAX-ACCESS not-accessible
			STATUS current
			DESCRIPTION
				"
				
				/extremeWing-config/profile/crypto_map"
			::= { extremeWingCfgProfVpn 9 }

		
		-- 1.3.6.1.4.1.1916.2.131.50.1.3.16.18.9.1
		extremeWingCfgProfVpnCryptoEntry OBJECT-TYPE
			SYNTAX ExtremeWingCfgProfVpnCryptoEntry
			MAX-ACCESS not-accessible
			STATUS current
			DESCRIPTION
				"An entry in the table."
			INDEX { extremeWingCfgProfName, extremeWingCfgProfVpnCryptoName }
			::= { extremeWingCfgProfVpnCryptoTable 1 }

		
		ExtremeWingCfgProfVpnCryptoEntry ::=
			SEQUENCE { 
				extremeWingCfgProfVpnCryptoName
					ExtremeWingIdentifier
			 }

		-- 1.3.6.1.4.1.1916.2.131.50.1.3.16.18.9.1.1
		extremeWingCfgProfVpnCryptoName OBJECT-TYPE
			SYNTAX ExtremeWingIdentifier
			MAX-ACCESS read-only
			STATUS current
			DESCRIPTION
				"
				
				XPath: /extremeWing-config/profile[name=key1]/crypto_map[name=key2]/name"
			::= { extremeWingCfgProfVpnCryptoEntry 1 }

		
		-- 1.3.6.1.4.1.1916.2.131.50.1.3.16.18.10
		extremeWingCfgProfVpnCryptoInstTable OBJECT-TYPE
			SYNTAX SEQUENCE OF ExtremeWingCfgProfVpnCryptoInstEntry
			MAX-ACCESS not-accessible
			STATUS current
			DESCRIPTION
				"
				
				/extremeWing-config/profile/crypto_map/crypto_map_entry"
			::= { extremeWingCfgProfVpn 10 }

		
		-- 1.3.6.1.4.1.1916.2.131.50.1.3.16.18.10.1
		extremeWingCfgProfVpnCryptoInstEntry OBJECT-TYPE
			SYNTAX ExtremeWingCfgProfVpnCryptoInstEntry
			MAX-ACCESS not-accessible
			STATUS current
			DESCRIPTION
				"An entry in the table."
			INDEX { extremeWingCfgProfName, extremeWingCfgProfVpnCryptoName, extremeWingCfgProfVpnCryptoInstSequence }
			::= { extremeWingCfgProfVpnCryptoInstTable 1 }

		
		ExtremeWingCfgProfVpnCryptoInstEntry ::=
			SEQUENCE { 
				extremeWingCfgProfVpnCryptoInstSequence
					Unsigned32,
				extremeWingCfgProfVpnCryptoInstType
					DisplayString,
				extremeWingCfgProfVpnCryptoInstIpAcl
					ExtremeWingIdentifier,
				extremeWingCfgProfVpnCryptoInstTransformSet
					ExtremeWingIdentifier,
				extremeWingCfgProfVpnCryptoInstLocalip
					DisplayString,
				extremeWingCfgProfVpnCryptoInstPfs
					DisplayString,
				extremeWingCfgProfVpnCryptoInstLifetimeSeconds
					Unsigned32,
				extremeWingCfgProfVpnCryptoInstLifetimeKb
					Unsigned32,
				extremeWingCfgProfVpnCryptoInstRemoteType
					DisplayString,
				extremeWingCfgProfVpnCryptoInstModeconfig
					DisplayString,
				extremeWingCfgProfVpnCryptoInstPeer
					DisplayString,
				extremeWingCfgProfVpnCryptoInstProtocol
					DisplayString,
				extremeWingCfgProfVpnCryptoInstMode
					DisplayString
			 }

		-- 1.3.6.1.4.1.1916.2.131.50.1.3.16.18.10.1.1
		extremeWingCfgProfVpnCryptoInstSequence OBJECT-TYPE
			SYNTAX Unsigned32 (1..1000)
			MAX-ACCESS read-only
			STATUS current
			DESCRIPTION
				"
				
				XPath: /extremeWing-config/profile[name=key1]/crypto_map[name=key2]/crypto_map_entry[sequence=key3]/sequence"
			::= { extremeWingCfgProfVpnCryptoInstEntry 1 }

		
		-- 1.3.6.1.4.1.1916.2.131.50.1.3.16.18.10.1.3
		extremeWingCfgProfVpnCryptoInstType OBJECT-TYPE
			SYNTAX DisplayString
			MAX-ACCESS read-write
			STATUS current
			DESCRIPTION
				"
				
				Values:
				site-to-site-auto,
				remote-vpn,
				site-to-site-manual
				
				XPath: /extremeWing-config/profile[name=key1]/crypto_map[name=key2]/crypto_map_entry[sequence=key3]/type"
			DEFVAL { "site-to-site-auto" }
			::= { extremeWingCfgProfVpnCryptoInstEntry 3 }

		
		-- 1.3.6.1.4.1.1916.2.131.50.1.3.16.18.10.1.4
		extremeWingCfgProfVpnCryptoInstIpAcl OBJECT-TYPE
			SYNTAX ExtremeWingIdentifier
			MAX-ACCESS read-write
			STATUS current
			DESCRIPTION
				"Access list for traffic that should be protected by IPsec.
				
				XPath: /extremeWing-config/profile[name=key1]/crypto_map[name=key2]/crypto_map_entry[sequence=key3]/ip_acl"
			::= { extremeWingCfgProfVpnCryptoInstEntry 4 }

		
		-- 1.3.6.1.4.1.1916.2.131.50.1.3.16.18.10.1.5
		extremeWingCfgProfVpnCryptoInstTransformSet OBJECT-TYPE
			SYNTAX ExtremeWingIdentifier
			MAX-ACCESS read-write
			STATUS current
			DESCRIPTION
				"NOTE: This column is valid only if extremeWingCfgProfVpnCryptoInstType sets to site-to-site-auto or remote-vpn
				
				IPsec transform (encryption and hash algorithms) to use.
				
				XPath: /extremeWing-config/profile[name=key1]/crypto_map[name=key2]/crypto_map_entry[sequence=key3]/ipsec_transform_set"
			::= { extremeWingCfgProfVpnCryptoInstEntry 5 }

		
		-- 1.3.6.1.4.1.1916.2.131.50.1.3.16.18.10.1.6
		extremeWingCfgProfVpnCryptoInstLocalip OBJECT-TYPE
			SYNTAX DisplayString
			MAX-ACCESS read-write
			STATUS current
			DESCRIPTION
				"Use this IP as local tunnel endpoint address, instead of the interface IP (Advanced Configuration).
				
				XPath: /extremeWing-config/profile[name=key1]/crypto_map[name=key2]/crypto_map_entry[sequence=key3]/localip"
			::= { extremeWingCfgProfVpnCryptoInstEntry 6 }

		
		-- 1.3.6.1.4.1.1916.2.131.50.1.3.16.18.10.1.7
		extremeWingCfgProfVpnCryptoInstPfs OBJECT-TYPE
			SYNTAX DisplayString
			MAX-ACCESS read-write
			STATUS current
			DESCRIPTION
				"NOTE: This column is valid only if extremeWingCfgProfVpnCryptoInstType sets to site-to-site-auto or remote-vpn
				
				Perfect Forward Secrecy.
				
				Values:
				none,
				2,
				5,
				14
				
				XPath: /extremeWing-config/profile[name=key1]/crypto_map[name=key2]/crypto_map_entry[sequence=key3]/pfs"
			DEFVAL { "none" }
			::= { extremeWingCfgProfVpnCryptoInstEntry 7 }

		
		-- 1.3.6.1.4.1.1916.2.131.50.1.3.16.18.10.1.8
		extremeWingCfgProfVpnCryptoInstLifetimeSeconds OBJECT-TYPE
			SYNTAX Unsigned32 (120..2147483646)
			UNITS "seconds"
			MAX-ACCESS read-write
			STATUS current
			DESCRIPTION
				"Time-based IPsec security association lifetime.
				
				XPath: /extremeWing-config/profile[name=key1]/crypto_map[name=key2]/crypto_map_entry[sequence=key3]/lifetime_seconds"
			::= { extremeWingCfgProfVpnCryptoInstEntry 8 }

		
		-- 1.3.6.1.4.1.1916.2.131.50.1.3.16.18.10.1.9
		extremeWingCfgProfVpnCryptoInstLifetimeKb OBJECT-TYPE
			SYNTAX Unsigned32 (500..2147483646)
			UNITS "kilobytes"
			MAX-ACCESS read-write
			STATUS current
			DESCRIPTION
				"Volume-based IPsec security association lifetime.
				
				XPath: /extremeWing-config/profile[name=key1]/crypto_map[name=key2]/crypto_map_entry[sequence=key3]/lifetime_kb"
			::= { extremeWingCfgProfVpnCryptoInstEntry 9 }

		
		-- 1.3.6.1.4.1.1916.2.131.50.1.3.16.18.10.1.10
		extremeWingCfgProfVpnCryptoInstRemoteType OBJECT-TYPE
			SYNTAX DisplayString
			MAX-ACCESS read-write
			STATUS current
			DESCRIPTION
				"NOTE: This column is valid only if extremeWingCfgProfVpnCryptoInstType sets to remote-vpn
				
				Remote VPN client type.
				
				Values:
				none,
				xauth
				
				XPath: /extremeWing-config/profile[name=key1]/crypto_map[name=key2]/crypto_map_entry[sequence=key3]/remote_type"
			DEFVAL { "xauth" }
			::= { extremeWingCfgProfVpnCryptoInstEntry 10 }

		
		-- 1.3.6.1.4.1.1916.2.131.50.1.3.16.18.10.1.11
		extremeWingCfgProfVpnCryptoInstModeconfig OBJECT-TYPE
			SYNTAX DisplayString
			MAX-ACCESS read-write
			STATUS current
			DESCRIPTION
				"NOTE: This column is valid only if extremeWingCfgProfVpnCryptoInstType sets to remote-vpn
				
				Choose the modeconfig method to use.
				
				Values:
				push,
				pull
				
				XPath: /extremeWing-config/profile[name=key1]/crypto_map[name=key2]/crypto_map_entry[sequence=key3]/modeconfig"
			DEFVAL { "push" }
			::= { extremeWingCfgProfVpnCryptoInstEntry 11 }

		
		-- 1.3.6.1.4.1.1916.2.131.50.1.3.16.18.10.1.12
		extremeWingCfgProfVpnCryptoInstPeer OBJECT-TYPE
			SYNTAX DisplayString
			MAX-ACCESS read-write
			STATUS current
			DESCRIPTION
				"NOTE: This column is valid only if extremeWingCfgProfVpnCryptoInstType sets to site-to-site-manual
				
				Allowed Encryption/Decryption peer.
				
				XPath: /extremeWing-config/profile[name=key1]/crypto_map[name=key2]/crypto_map_entry[sequence=key3]/peer"
			::= { extremeWingCfgProfVpnCryptoInstEntry 12 }

		
		-- 1.3.6.1.4.1.1916.2.131.50.1.3.16.18.10.1.13
		extremeWingCfgProfVpnCryptoInstProtocol OBJECT-TYPE
			SYNTAX DisplayString
			MAX-ACCESS read-write
			STATUS current
			DESCRIPTION
				"NOTE: This column is valid only if extremeWingCfgProfVpnCryptoInstType sets to site-to-site-manual
				
				Procotol to be used to the IPsec tunnel. It can be ESP or AH.
				
				Values:
				ESP,
				AH
				
				XPath: /extremeWing-config/profile[name=key1]/crypto_map[name=key2]/crypto_map_entry[sequence=key3]/protocol"
			DEFVAL { "ESP" }
			::= { extremeWingCfgProfVpnCryptoInstEntry 13 }

		
		-- 1.3.6.1.4.1.1916.2.131.50.1.3.16.18.10.1.14
		extremeWingCfgProfVpnCryptoInstMode OBJECT-TYPE
			SYNTAX DisplayString
			MAX-ACCESS read-write
			STATUS current
			DESCRIPTION
				"NOTE: This column is valid only if extremeWingCfgProfVpnCryptoInstType sets to site-to-site-manual
				
				IPsec tunnel type - tunnel or transport mode.
				
				Values:
				tunnel,
				transport
				
				XPath: /extremeWing-config/profile[name=key1]/crypto_map[name=key2]/crypto_map_entry[sequence=key3]/mode"
			DEFVAL { "tunnel" }
			::= { extremeWingCfgProfVpnCryptoInstEntry 14 }

		
		-- 1.3.6.1.4.1.1916.2.131.50.1.3.16.18.11
		extremeWingCfgProfVpnCryptoInstPeerListTable OBJECT-TYPE
			SYNTAX SEQUENCE OF ExtremeWingCfgProfVpnCryptoInstPeerListEntry
			MAX-ACCESS not-accessible
			STATUS current
			DESCRIPTION
				"NOTE: Columns under this table are valid only if extremeWingCfgProfVpnCryptoInstType sets to site-to-site-auto or remote-vpn
				
				/extremeWing-config/profile/crypto_map/crypto_map_entry"
			::= { extremeWingCfgProfVpn 11 }

		
		-- 1.3.6.1.4.1.1916.2.131.50.1.3.16.18.11.1
		extremeWingCfgProfVpnCryptoInstPeerListEntry OBJECT-TYPE
			SYNTAX ExtremeWingCfgProfVpnCryptoInstPeerListEntry
			MAX-ACCESS not-accessible
			STATUS current
			DESCRIPTION
				"An entry in the table."
			INDEX { extremeWingCfgProfName, extremeWingCfgProfVpnCryptoName, extremeWingCfgProfVpnCryptoInstSequence, extremeWingCfgProfVpnCryptoInstPeerListPriority }
			::= { extremeWingCfgProfVpnCryptoInstPeerListTable 1 }

		
		ExtremeWingCfgProfVpnCryptoInstPeerListEntry ::=
			SEQUENCE { 
				extremeWingCfgProfVpnCryptoInstPeerListPriority
					Unsigned32,
				extremeWingCfgProfVpnCryptoInstPeerListType
					DisplayString,
				extremeWingCfgProfVpnCryptoInstPeerListIkev1Peer
					ExtremeWingIdentifier,
				extremeWingCfgProfVpnCryptoInstPeerListIkev2Peer
					ExtremeWingIdentifier
			 }

		-- 1.3.6.1.4.1.1916.2.131.50.1.3.16.18.11.1.1
		extremeWingCfgProfVpnCryptoInstPeerListPriority OBJECT-TYPE
			SYNTAX Unsigned32 (1..3)
			MAX-ACCESS read-only
			STATUS current
			DESCRIPTION
				"List of prioritized redundant peers.
				
				XPath: /extremeWing-config/profile[name=key1]/crypto_map[name=key2]/crypto_map_entry[sequence=key3]/peer_list[priority=key4]/priority"
			::= { extremeWingCfgProfVpnCryptoInstPeerListEntry 1 }

		
		-- 1.3.6.1.4.1.1916.2.131.50.1.3.16.18.11.1.3
		extremeWingCfgProfVpnCryptoInstPeerListType OBJECT-TYPE
			SYNTAX DisplayString
			MAX-ACCESS read-write
			STATUS current
			DESCRIPTION
				"Peer IKE type.
				
				Values:
				ikev1,
				ikev2
				
				XPath: /extremeWing-config/profile[name=key1]/crypto_map[name=key2]/crypto_map_entry[sequence=key3]/peer_list[priority=key4]/type"
			::= { extremeWingCfgProfVpnCryptoInstPeerListEntry 3 }

		
		-- 1.3.6.1.4.1.1916.2.131.50.1.3.16.18.11.1.4
		extremeWingCfgProfVpnCryptoInstPeerListIkev1Peer OBJECT-TYPE
			SYNTAX ExtremeWingIdentifier
			MAX-ACCESS read-write
			STATUS current
			DESCRIPTION
				"Name of the IKEv1 Peer.
				
				XPath: /extremeWing-config/profile[name=key1]/crypto_map[name=key2]/crypto_map_entry[sequence=key3]/peer_list[priority=key4]/ikev1_peer"
			::= { extremeWingCfgProfVpnCryptoInstPeerListEntry 4 }

		
		-- 1.3.6.1.4.1.1916.2.131.50.1.3.16.18.11.1.5
		extremeWingCfgProfVpnCryptoInstPeerListIkev2Peer OBJECT-TYPE
			SYNTAX ExtremeWingIdentifier
			MAX-ACCESS read-write
			STATUS current
			DESCRIPTION
				"Name of the IKEv2 Peer.
				
				XPath: /extremeWing-config/profile[name=key1]/crypto_map[name=key2]/crypto_map_entry[sequence=key3]/peer_list[priority=key4]/ikev2_peer"
			::= { extremeWingCfgProfVpnCryptoInstPeerListEntry 5 }

		
		-- 1.3.6.1.4.1.1916.2.131.50.1.3.16.18.12
		extremeWingCfgProfVpnCryptoInstAhSessionTable OBJECT-TYPE
			SYNTAX SEQUENCE OF ExtremeWingCfgProfVpnCryptoInstAhSessionEntry
			MAX-ACCESS not-accessible
			STATUS current
			DESCRIPTION
				"NOTE: Columns under this table are valid only if extremeWingCfgProfVpnCryptoInstType sets to site-to-site-manual
				
				/extremeWing-config/profile/crypto_map/crypto_map_entry/ah_session_keys"
			::= { extremeWingCfgProfVpn 12 }

		
		-- 1.3.6.1.4.1.1916.2.131.50.1.3.16.18.12.1
		extremeWingCfgProfVpnCryptoInstAhSessionEntry OBJECT-TYPE
			SYNTAX ExtremeWingCfgProfVpnCryptoInstAhSessionEntry
			MAX-ACCESS not-accessible
			STATUS current
			DESCRIPTION
				"An entry in the table."
			INDEX { extremeWingCfgProfName, extremeWingCfgProfVpnCryptoName, extremeWingCfgProfVpnCryptoInstSequence, extremeWingCfgProfVpnCryptoInstAhSessionDirection }
			::= { extremeWingCfgProfVpnCryptoInstAhSessionTable 1 }

		
		ExtremeWingCfgProfVpnCryptoInstAhSessionEntry ::=
			SEQUENCE { 
				extremeWingCfgProfVpnCryptoInstAhSessionDirection
					ExtremeWingIdentifier,
				extremeWingCfgProfVpnCryptoInstAhSessionSpi
					Unsigned32,
				extremeWingCfgProfVpnCryptoInstAhSessionAuth
					DisplayString,
				extremeWingCfgProfVpnCryptoInstAhSessionKey
					OCTET STRING
			 }

		-- 1.3.6.1.4.1.1916.2.131.50.1.3.16.18.12.1.1
		extremeWingCfgProfVpnCryptoInstAhSessionDirection OBJECT-TYPE
			SYNTAX ExtremeWingIdentifier
			MAX-ACCESS read-only
			STATUS current
			DESCRIPTION
				"Direction of the security association.
				
				Values:
				inbound,
				outbound
				
				XPath: /extremeWing-config/profile[name=key1]/crypto_map[name=key2]/crypto_map_entry[sequence=key3]/ah_session_keys[direction=key4]/direction"
			::= { extremeWingCfgProfVpnCryptoInstAhSessionEntry 1 }

		
		-- 1.3.6.1.4.1.1916.2.131.50.1.3.16.18.12.1.3
		extremeWingCfgProfVpnCryptoInstAhSessionSpi OBJECT-TYPE
			SYNTAX Unsigned32 (256..4294967295)
			MAX-ACCESS read-write
			STATUS current
			DESCRIPTION
				"Security Parameter Index for Security Association.
				This should be unique for all Security Associations.
				
				XPath: /extremeWing-config/profile[name=key1]/crypto_map[name=key2]/crypto_map_entry[sequence=key3]/ah_session_keys[direction=key4]/spi"
			::= { extremeWingCfgProfVpnCryptoInstAhSessionEntry 3 }

		
		-- 1.3.6.1.4.1.1916.2.131.50.1.3.16.18.12.1.4
		extremeWingCfgProfVpnCryptoInstAhSessionAuth OBJECT-TYPE
			SYNTAX DisplayString
			MAX-ACCESS read-write
			STATUS current
			DESCRIPTION
				"Authentication scheme used to validate identity.
				
				Values:
				md5,
				sha
				
				XPath: /extremeWing-config/profile[name=key1]/crypto_map[name=key2]/crypto_map_entry[sequence=key3]/ah_session_keys[direction=key4]/auth_algo"
			DEFVAL { "sha" }
			::= { extremeWingCfgProfVpnCryptoInstAhSessionEntry 4 }

		
		-- 1.3.6.1.4.1.1916.2.131.50.1.3.16.18.12.1.5
		extremeWingCfgProfVpnCryptoInstAhSessionKey OBJECT-TYPE
			SYNTAX OCTET STRING (SIZE (8..512))
			MAX-ACCESS read-write
			STATUS current
			DESCRIPTION
				"Security association key value. The following key lengths
				(in hex characters) are required.ESP-MD5: 32,ESP-SHA: 40.
				
				XPath: /extremeWing-config/profile[name=key1]/crypto_map[name=key2]/crypto_map_entry[sequence=key3]/ah_session_keys[direction=key4]/key"
			::= { extremeWingCfgProfVpnCryptoInstAhSessionEntry 5 }

		
		-- 1.3.6.1.4.1.1916.2.131.50.1.3.16.18.13
		extremeWingCfgProfVpnCryptoInstEspSessionTable OBJECT-TYPE
			SYNTAX SEQUENCE OF ExtremeWingCfgProfVpnCryptoInstEspSessionEntry
			MAX-ACCESS not-accessible
			STATUS current
			DESCRIPTION
				"NOTE: Columns under this table are valid only if extremeWingCfgProfVpnCryptoInstType sets to site-to-site-manual
				
				/extremeWing-config/profile/crypto_map/crypto_map_entry/esp_session_keys"
			::= { extremeWingCfgProfVpn 13 }

		
		-- 1.3.6.1.4.1.1916.2.131.50.1.3.16.18.13.1
		extremeWingCfgProfVpnCryptoInstEspSessionEntry OBJECT-TYPE
			SYNTAX ExtremeWingCfgProfVpnCryptoInstEspSessionEntry
			MAX-ACCESS not-accessible
			STATUS current
			DESCRIPTION
				"An entry in the table."
			INDEX { extremeWingCfgProfName, extremeWingCfgProfVpnCryptoName, extremeWingCfgProfVpnCryptoInstSequence, extremeWingCfgProfVpnCryptoInstEspSessionDirection }
			::= { extremeWingCfgProfVpnCryptoInstEspSessionTable 1 }

		
		ExtremeWingCfgProfVpnCryptoInstEspSessionEntry ::=
			SEQUENCE { 
				extremeWingCfgProfVpnCryptoInstEspSessionDirection
					ExtremeWingIdentifier,
				extremeWingCfgProfVpnCryptoInstEspSessionSpi
					Unsigned32,
				extremeWingCfgProfVpnCryptoInstEspSessionCipherAlgo
					DisplayString,
				extremeWingCfgProfVpnCryptoInstEspSessionCipherKey
					OCTET STRING,
				extremeWingCfgProfVpnCryptoInstEspSessionAuthAlgo
					DisplayString,
				extremeWingCfgProfVpnCryptoInstEspSessionAuthKey
					OCTET STRING
			 }

		-- 1.3.6.1.4.1.1916.2.131.50.1.3.16.18.13.1.1
		extremeWingCfgProfVpnCryptoInstEspSessionDirection OBJECT-TYPE
			SYNTAX ExtremeWingIdentifier
			MAX-ACCESS read-only
			STATUS current
			DESCRIPTION
				"
				
				Values:
				inbound,
				outbound
				
				XPath: /extremeWing-config/profile[name=key1]/crypto_map[name=key2]/crypto_map_entry[sequence=key3]/esp_session_keys[direction=key4]/direction"
			::= { extremeWingCfgProfVpnCryptoInstEspSessionEntry 1 }

		
		-- 1.3.6.1.4.1.1916.2.131.50.1.3.16.18.13.1.3
		extremeWingCfgProfVpnCryptoInstEspSessionSpi OBJECT-TYPE
			SYNTAX Unsigned32 (256..4294967295)
			MAX-ACCESS read-write
			STATUS current
			DESCRIPTION
				"Security Parameter Index for Security Association. This should be unique for all Security Associations.
				
				XPath: /extremeWing-config/profile[name=key1]/crypto_map[name=key2]/crypto_map_entry[sequence=key3]/esp_session_keys[direction=key4]/spi"
			::= { extremeWingCfgProfVpnCryptoInstEspSessionEntry 3 }

		
		-- 1.3.6.1.4.1.1916.2.131.50.1.3.16.18.13.1.4
		extremeWingCfgProfVpnCryptoInstEspSessionCipherAlgo OBJECT-TYPE
			SYNTAX DisplayString
			MAX-ACCESS read-write
			STATUS current
			DESCRIPTION
				"Encryption method protecting data transmission.
				
				Values:
				esp-null,
				des,
				3des,
				aes,
				aes-192,
				aes-256
				
				XPath: /extremeWing-config/profile[name=key1]/crypto_map[name=key2]/crypto_map_entry[sequence=key3]/esp_session_keys[direction=key4]/cipher_algo"
			DEFVAL { "aes-256" }
			::= { extremeWingCfgProfVpnCryptoInstEspSessionEntry 4 }

		
		-- 1.3.6.1.4.1.1916.2.131.50.1.3.16.18.13.1.5
		extremeWingCfgProfVpnCryptoInstEspSessionCipherKey OBJECT-TYPE
			SYNTAX OCTET STRING (SIZE (8..512))
			MAX-ACCESS read-write
			STATUS current
			DESCRIPTION
				"Security association key value. The following key lengths (in hex characters) are required .ESP-NULL: 0, ESP-DES: 16, ESP-3DES: 48, ESP-AES: 32, ESP-AES-192: 48, ESP-AES-256: 64
				
				XPath: /extremeWing-config/profile[name=key1]/crypto_map[name=key2]/crypto_map_entry[sequence=key3]/esp_session_keys[direction=key4]/cipher_key"
			::= { extremeWingCfgProfVpnCryptoInstEspSessionEntry 5 }

		
		-- 1.3.6.1.4.1.1916.2.131.50.1.3.16.18.13.1.6
		extremeWingCfgProfVpnCryptoInstEspSessionAuthAlgo OBJECT-TYPE
			SYNTAX DisplayString
			MAX-ACCESS read-write
			STATUS current
			DESCRIPTION
				"Authentication scheme used to validate identity.
				
				Values:
				md5,
				sha
				
				XPath: /extremeWing-config/profile[name=key1]/crypto_map[name=key2]/crypto_map_entry[sequence=key3]/esp_session_keys[direction=key4]/auth_algo"
			DEFVAL { "sha" }
			::= { extremeWingCfgProfVpnCryptoInstEspSessionEntry 6 }

		
		-- 1.3.6.1.4.1.1916.2.131.50.1.3.16.18.13.1.7
		extremeWingCfgProfVpnCryptoInstEspSessionAuthKey OBJECT-TYPE
			SYNTAX OCTET STRING (SIZE (8..512))
			MAX-ACCESS read-write
			STATUS current
			DESCRIPTION
				"Security association key value. The following key lengths (in hex characters) are required.ESP-MD5: 32,ESP-SHA: 40.
				
				XPath: /extremeWing-config/profile[name=key1]/crypto_map[name=key2]/crypto_map_entry[sequence=key3]/esp_session_keys[direction=key4]/auth_key"
			::= { extremeWingCfgProfVpnCryptoInstEspSessionEntry 7 }

		
		-- 1.3.6.1.4.1.1916.2.131.50.1.3.16.18.14
		extremeWingCfgProfVpnIkev1RemoteTable OBJECT-TYPE
			SYNTAX SEQUENCE OF ExtremeWingCfgProfVpnIkev1RemoteEntry
			MAX-ACCESS not-accessible
			STATUS current
			DESCRIPTION
				"
				
				/extremeWing-config/profile/ikev1_remote_vpn"
			::= { extremeWingCfgProfVpn 14 }

		
		-- 1.3.6.1.4.1.1916.2.131.50.1.3.16.18.14.1
		extremeWingCfgProfVpnIkev1RemoteEntry OBJECT-TYPE
			SYNTAX ExtremeWingCfgProfVpnIkev1RemoteEntry
			MAX-ACCESS not-accessible
			STATUS current
			DESCRIPTION
				"An entry in the table."
			INDEX { extremeWingCfgProfName }
			::= { extremeWingCfgProfVpnIkev1RemoteTable 1 }

		
		ExtremeWingCfgProfVpnIkev1RemoteEntry ::=
			SEQUENCE { 
				extremeWingCfgProfVpnIkev1RemoteAuthMethod
					DisplayString,
				extremeWingCfgProfVpnIkev1RemoteAaaPolicy
					ExtremeWingIdentifier,
				extremeWingCfgProfVpnIkev1RemoteIpLocalPool
					DisplayString
			 }

		-- 1.3.6.1.4.1.1916.2.131.50.1.3.16.18.14.1.1
		extremeWingCfgProfVpnIkev1RemoteAuthMethod OBJECT-TYPE
			SYNTAX DisplayString
			MAX-ACCESS read-write
			STATUS current
			DESCRIPTION
				"The authentication method used for Remove VPN client. It can be one of RADIUS or LOCAL.
				
				Values:
				radius,
				local
				
				XPath: /extremeWing-config/profile[name=key1]/ikev1_remote_vpn/auth_method"
			DEFVAL { "local" }
			::= { extremeWingCfgProfVpnIkev1RemoteEntry 1 }

		
		-- 1.3.6.1.4.1.1916.2.131.50.1.3.16.18.14.1.2
		extremeWingCfgProfVpnIkev1RemoteAaaPolicy OBJECT-TYPE
			SYNTAX ExtremeWingIdentifier
			MAX-ACCESS read-write
			STATUS current
			DESCRIPTION
				"AAA Policy to use for remote VPN clients.
				
				XPath: /extremeWing-config/profile[name=key1]/ikev1_remote_vpn/aaa_policy"
			::= { extremeWingCfgProfVpnIkev1RemoteEntry 2 }

		
		-- 1.3.6.1.4.1.1916.2.131.50.1.3.16.18.14.1.3
		extremeWingCfgProfVpnIkev1RemoteIpLocalPool OBJECT-TYPE
			SYNTAX DisplayString
			MAX-ACCESS read-write
			STATUS current
			DESCRIPTION
				"The virtual IP pool for assigning IP addresses to remote VPN clients.
				
				XPath: /extremeWing-config/profile[name=key1]/ikev1_remote_vpn/ip_local_pool"
			::= { extremeWingCfgProfVpnIkev1RemoteEntry 3 }

		
		-- 1.3.6.1.4.1.1916.2.131.50.1.3.16.18.15
		extremeWingCfgProfVpnIkev1RemoteLocalUsersTable OBJECT-TYPE
			SYNTAX SEQUENCE OF ExtremeWingCfgProfVpnIkev1RemoteLocalUsersEntry
			MAX-ACCESS not-accessible
			STATUS current
			DESCRIPTION
				"
				
				/extremeWing-config/profile/ikev1_remote_vpn/local_users"
			::= { extremeWingCfgProfVpn 15 }

		
		-- 1.3.6.1.4.1.1916.2.131.50.1.3.16.18.15.1
		extremeWingCfgProfVpnIkev1RemoteLocalUsersEntry OBJECT-TYPE
			SYNTAX ExtremeWingCfgProfVpnIkev1RemoteLocalUsersEntry
			MAX-ACCESS not-accessible
			STATUS current
			DESCRIPTION
				"An entry in the table."
			INDEX { extremeWingCfgProfName, extremeWingCfgProfVpnIkev1RemoteLocalUsersName }
			::= { extremeWingCfgProfVpnIkev1RemoteLocalUsersTable 1 }

		
		ExtremeWingCfgProfVpnIkev1RemoteLocalUsersEntry ::=
			SEQUENCE { 
				extremeWingCfgProfVpnIkev1RemoteLocalUsersName
					ExtremeWingIdentifier,
				extremeWingCfgProfVpnIkev1RemoteLocalUsersPassword
					DisplayString
			 }

		-- 1.3.6.1.4.1.1916.2.131.50.1.3.16.18.15.1.1
		extremeWingCfgProfVpnIkev1RemoteLocalUsersName OBJECT-TYPE
			SYNTAX ExtremeWingIdentifier
			MAX-ACCESS read-only
			STATUS current
			DESCRIPTION
				"User name
				
				XPath: /extremeWing-config/profile[name=key1]/ikev1_remote_vpn/local_users[name=key2]/name"
			::= { extremeWingCfgProfVpnIkev1RemoteLocalUsersEntry 1 }
-- TODO: Key length may exceed 128 sub-identifiers
-- add leaf with Integer as key to append as the last digit of OID
		
		-- 1.3.6.1.4.1.1916.2.131.50.1.3.16.18.15.1.3
		extremeWingCfgProfVpnIkev1RemoteLocalUsersPassword OBJECT-TYPE
			SYNTAX DisplayString (SIZE (8..21))
			MAX-ACCESS read-write
			STATUS current
			DESCRIPTION
				"The password to authenticate the user.
				
				XPath: /extremeWing-config/profile[name=key1]/ikev1_remote_vpn/local_users[name=key2]/password"
			::= { extremeWingCfgProfVpnIkev1RemoteLocalUsersEntry 3 }

		
		-- 1.3.6.1.4.1.1916.2.131.50.1.3.16.18.16
		extremeWingCfgProfVpnIkev1RemoteWinsTable OBJECT-TYPE
			SYNTAX SEQUENCE OF ExtremeWingCfgProfVpnIkev1RemoteWinsEntry
			MAX-ACCESS not-accessible
			STATUS current
			DESCRIPTION
				"
				
				/extremeWing-config/profile/ikev1_remote_vpn/wins"
			::= { extremeWingCfgProfVpn 16 }

		
		-- 1.3.6.1.4.1.1916.2.131.50.1.3.16.18.16.1
		extremeWingCfgProfVpnIkev1RemoteWinsEntry OBJECT-TYPE
			SYNTAX ExtremeWingCfgProfVpnIkev1RemoteWinsEntry
			MAX-ACCESS not-accessible
			STATUS current
			DESCRIPTION
				"An entry in the table."
			INDEX { extremeWingCfgProfName, extremeWingCfgProfVpnIkev1RemoteWinsServerType }
			::= { extremeWingCfgProfVpnIkev1RemoteWinsTable 1 }

		
		ExtremeWingCfgProfVpnIkev1RemoteWinsEntry ::=
			SEQUENCE { 
				extremeWingCfgProfVpnIkev1RemoteWinsServerType
					ExtremeWingIdentifier,
				extremeWingCfgProfVpnIkev1RemoteWinsServerIp
					DisplayString
			 }

		-- 1.3.6.1.4.1.1916.2.131.50.1.3.16.18.16.1.1
		extremeWingCfgProfVpnIkev1RemoteWinsServerType OBJECT-TYPE
			SYNTAX ExtremeWingIdentifier
			MAX-ACCESS read-only
			STATUS current
			DESCRIPTION
				"Primary or Secondary WINS server.
				
				Values:
				primary,
				secondary
				
				XPath: /extremeWing-config/profile[name=key1]/ikev1_remote_vpn/wins[server_type=key2]/server_type"
			::= { extremeWingCfgProfVpnIkev1RemoteWinsEntry 1 }

		
		-- 1.3.6.1.4.1.1916.2.131.50.1.3.16.18.16.1.3
		extremeWingCfgProfVpnIkev1RemoteWinsServerIp OBJECT-TYPE
			SYNTAX DisplayString
			MAX-ACCESS read-write
			STATUS current
			DESCRIPTION
				"
				
				XPath: /extremeWing-config/profile[name=key1]/ikev1_remote_vpn/wins[server_type=key2]/server_ip"
			::= { extremeWingCfgProfVpnIkev1RemoteWinsEntry 3 }

		
		-- 1.3.6.1.4.1.1916.2.131.50.1.3.16.18.17
		extremeWingCfgProfVpnIkev1RemoteNameServerTable OBJECT-TYPE
			SYNTAX SEQUENCE OF ExtremeWingCfgProfVpnIkev1RemoteNameServerEntry
			MAX-ACCESS not-accessible
			STATUS current
			DESCRIPTION
				"
				
				/extremeWing-config/profile/ikev1_remote_vpn/nameserver"
			::= { extremeWingCfgProfVpn 17 }

		
		-- 1.3.6.1.4.1.1916.2.131.50.1.3.16.18.17.1
		extremeWingCfgProfVpnIkev1RemoteNameServerEntry OBJECT-TYPE
			SYNTAX ExtremeWingCfgProfVpnIkev1RemoteNameServerEntry
			MAX-ACCESS not-accessible
			STATUS current
			DESCRIPTION
				"An entry in the table."
			INDEX { extremeWingCfgProfName, extremeWingCfgProfVpnIkev1RemoteNameServerType }
			::= { extremeWingCfgProfVpnIkev1RemoteNameServerTable 1 }

		
		ExtremeWingCfgProfVpnIkev1RemoteNameServerEntry ::=
			SEQUENCE { 
				extremeWingCfgProfVpnIkev1RemoteNameServerType
					ExtremeWingIdentifier,
				extremeWingCfgProfVpnIkev1RemoteNameServerIp
					DisplayString
			 }

		-- 1.3.6.1.4.1.1916.2.131.50.1.3.16.18.17.1.1
		extremeWingCfgProfVpnIkev1RemoteNameServerType OBJECT-TYPE
			SYNTAX ExtremeWingIdentifier
			MAX-ACCESS read-only
			STATUS current
			DESCRIPTION
				"Primary or Secondary Name server.
				
				Values:
				primary,
				secondary
				
				XPath: /extremeWing-config/profile[name=key1]/ikev1_remote_vpn/nameserver[server_type=key2]/server_type"
			::= { extremeWingCfgProfVpnIkev1RemoteNameServerEntry 1 }

		
		-- 1.3.6.1.4.1.1916.2.131.50.1.3.16.18.17.1.3
		extremeWingCfgProfVpnIkev1RemoteNameServerIp OBJECT-TYPE
			SYNTAX DisplayString
			MAX-ACCESS read-write
			STATUS current
			DESCRIPTION
				"
				
				XPath: /extremeWing-config/profile[name=key1]/ikev1_remote_vpn/nameserver[server_type=key2]/server_ip"
			::= { extremeWingCfgProfVpnIkev1RemoteNameServerEntry 3 }

		
		-- 1.3.6.1.4.1.1916.2.131.50.1.3.16.18.18
		extremeWingCfgProfVpnIkev2RemoteTable OBJECT-TYPE
			SYNTAX SEQUENCE OF ExtremeWingCfgProfVpnIkev2RemoteEntry
			MAX-ACCESS not-accessible
			STATUS current
			DESCRIPTION
				"
				
				/extremeWing-config/profile/ikev2_remote_vpn"
			::= { extremeWingCfgProfVpn 18 }

		
		-- 1.3.6.1.4.1.1916.2.131.50.1.3.16.18.18.1
		extremeWingCfgProfVpnIkev2RemoteEntry OBJECT-TYPE
			SYNTAX ExtremeWingCfgProfVpnIkev2RemoteEntry
			MAX-ACCESS not-accessible
			STATUS current
			DESCRIPTION
				"An entry in the table."
			INDEX { extremeWingCfgProfName }
			::= { extremeWingCfgProfVpnIkev2RemoteTable 1 }

		
		ExtremeWingCfgProfVpnIkev2RemoteEntry ::=
			SEQUENCE { 
				extremeWingCfgProfVpnIkev2RemoteAuthMethod
					DisplayString,
				extremeWingCfgProfVpnIkev2RemoteAaaPolicy
					ExtremeWingIdentifier,
				extremeWingCfgProfVpnIkev2RemoteIpLocalPool
					DisplayString,
				extremeWingCfgProfVpnIkev2RemoteDhcpServerType
					DisplayString,
				extremeWingCfgProfVpnIkev2RemoteDhcpServer
					DisplayString,
				extremeWingCfgProfVpnIkev2RemoteDhcpServerGiaddr
					DisplayString,
				extremeWingCfgProfVpnIkev2RemoteNetmask
					DisplayString
			 }

		-- 1.3.6.1.4.1.1916.2.131.50.1.3.16.18.18.1.1
		extremeWingCfgProfVpnIkev2RemoteAuthMethod OBJECT-TYPE
			SYNTAX DisplayString
			MAX-ACCESS read-write
			STATUS current
			DESCRIPTION
				"The authentication method used for Remove VPN client. It can be one of RADIUS or LOCAL.
				
				Values:
				radius,
				local
				
				XPath: /extremeWing-config/profile[name=key1]/ikev2_remote_vpn/auth_method"
			DEFVAL { "local" }
			::= { extremeWingCfgProfVpnIkev2RemoteEntry 1 }

		
		-- 1.3.6.1.4.1.1916.2.131.50.1.3.16.18.18.1.2
		extremeWingCfgProfVpnIkev2RemoteAaaPolicy OBJECT-TYPE
			SYNTAX ExtremeWingIdentifier
			MAX-ACCESS read-write
			STATUS current
			DESCRIPTION
				"AAA Policy to use for remote VPN clients.
				
				XPath: /extremeWing-config/profile[name=key1]/ikev2_remote_vpn/aaa_policy"
			::= { extremeWingCfgProfVpnIkev2RemoteEntry 2 }

		
		-- 1.3.6.1.4.1.1916.2.131.50.1.3.16.18.18.1.3
		extremeWingCfgProfVpnIkev2RemoteIpLocalPool OBJECT-TYPE
			SYNTAX DisplayString
			MAX-ACCESS read-write
			STATUS current
			DESCRIPTION
				"The virtual IP pool for assigning IP addresses to remote VPN clients.
				
				XPath: /extremeWing-config/profile[name=key1]/ikev2_remote_vpn/ip_local_pool"
			::= { extremeWingCfgProfVpnIkev2RemoteEntry 3 }

		
		-- 1.3.6.1.4.1.1916.2.131.50.1.3.16.18.18.1.4
		extremeWingCfgProfVpnIkev2RemoteDhcpServerType OBJECT-TYPE
			SYNTAX DisplayString
			MAX-ACCESS read-write
			STATUS current
			DESCRIPTION
				"Select DHCP server type as IP or Hostname.
				
				Values:
				address,
				hostname,
				none
				
				XPath: /extremeWing-config/profile[name=key1]/ikev2_remote_vpn/dhcp_server/dhcp_server_type"
			DEFVAL { "'none'" }
			::= { extremeWingCfgProfVpnIkev2RemoteEntry 4 }

		
		-- 1.3.6.1.4.1.1916.2.131.50.1.3.16.18.18.1.5
		extremeWingCfgProfVpnIkev2RemoteDhcpServer OBJECT-TYPE
			SYNTAX DisplayString (SIZE (1..64))
			MAX-ACCESS read-write
			STATUS current
			DESCRIPTION
				"Specify DHCP Server IP or Hostname.
				
				XPath: /extremeWing-config/profile[name=key1]/ikev2_remote_vpn/dhcp_server/dhcp_server"
			::= { extremeWingCfgProfVpnIkev2RemoteEntry 5 }

		
		-- 1.3.6.1.4.1.1916.2.131.50.1.3.16.18.18.1.6
		extremeWingCfgProfVpnIkev2RemoteDhcpServerGiaddr OBJECT-TYPE
			SYNTAX DisplayString
			MAX-ACCESS read-write
			STATUS current
			DESCRIPTION
				"DHCP Relay Agent IP address
				
				XPath: /extremeWing-config/profile[name=key1]/ikev2_remote_vpn/dhcp_server/giaddr"
			::= { extremeWingCfgProfVpnIkev2RemoteEntry 6 }

		
		-- 1.3.6.1.4.1.1916.2.131.50.1.3.16.18.18.1.7
		extremeWingCfgProfVpnIkev2RemoteNetmask OBJECT-TYPE
			SYNTAX DisplayString
			MAX-ACCESS read-write
			STATUS current
			DESCRIPTION
				"Netmask for remote VPN clients (IKEv2 only)
				
				XPath: /extremeWing-config/profile[name=key1]/ikev2_remote_vpn/netmask"
			::= { extremeWingCfgProfVpnIkev2RemoteEntry 7 }

		
		-- 1.3.6.1.4.1.1916.2.131.50.1.3.16.18.19
		extremeWingCfgProfVpnIkev2RemoteLocalUsersTable OBJECT-TYPE
			SYNTAX SEQUENCE OF ExtremeWingCfgProfVpnIkev2RemoteLocalUsersEntry
			MAX-ACCESS not-accessible
			STATUS current
			DESCRIPTION
				"
				
				/extremeWing-config/profile/ikev2_remote_vpn/local_users"
			::= { extremeWingCfgProfVpn 19 }

		
		-- 1.3.6.1.4.1.1916.2.131.50.1.3.16.18.19.1
		extremeWingCfgProfVpnIkev2RemoteLocalUsersEntry OBJECT-TYPE
			SYNTAX ExtremeWingCfgProfVpnIkev2RemoteLocalUsersEntry
			MAX-ACCESS not-accessible
			STATUS current
			DESCRIPTION
				"An entry in the table."
			INDEX { extremeWingCfgProfName, extremeWingCfgProfVpnIkev2RemoteLocalUsersName }
			::= { extremeWingCfgProfVpnIkev2RemoteLocalUsersTable 1 }

		
		ExtremeWingCfgProfVpnIkev2RemoteLocalUsersEntry ::=
			SEQUENCE { 
				extremeWingCfgProfVpnIkev2RemoteLocalUsersName
					ExtremeWingIdentifier,
				extremeWingCfgProfVpnIkev2RemoteLocalUsersPassword
					DisplayString
			 }

		-- 1.3.6.1.4.1.1916.2.131.50.1.3.16.18.19.1.1
		extremeWingCfgProfVpnIkev2RemoteLocalUsersName OBJECT-TYPE
			SYNTAX ExtremeWingIdentifier
			MAX-ACCESS read-only
			STATUS current
			DESCRIPTION
				"User name
				
				XPath: /extremeWing-config/profile[name=key1]/ikev2_remote_vpn/local_users[name=key2]/name"
			::= { extremeWingCfgProfVpnIkev2RemoteLocalUsersEntry 1 }
-- TODO: Key length may exceed 128 sub-identifiers
-- add leaf with Integer as key to append as the last digit of OID
		
		-- 1.3.6.1.4.1.1916.2.131.50.1.3.16.18.19.1.3
		extremeWingCfgProfVpnIkev2RemoteLocalUsersPassword OBJECT-TYPE
			SYNTAX DisplayString (SIZE (8..21))
			MAX-ACCESS read-write
			STATUS current
			DESCRIPTION
				"The password to authenticate the user.
				
				XPath: /extremeWing-config/profile[name=key1]/ikev2_remote_vpn/local_users[name=key2]/password"
			::= { extremeWingCfgProfVpnIkev2RemoteLocalUsersEntry 3 }

		
		-- 1.3.6.1.4.1.1916.2.131.50.1.3.16.18.20
		extremeWingCfgProfVpnIkev2RemoteWinsTable OBJECT-TYPE
			SYNTAX SEQUENCE OF ExtremeWingCfgProfVpnIkev2RemoteWinsEntry
			MAX-ACCESS not-accessible
			STATUS current
			DESCRIPTION
				"
				
				/extremeWing-config/profile/ikev2_remote_vpn/wins"
			::= { extremeWingCfgProfVpn 20 }

		
		-- 1.3.6.1.4.1.1916.2.131.50.1.3.16.18.20.1
		extremeWingCfgProfVpnIkev2RemoteWinsEntry OBJECT-TYPE
			SYNTAX ExtremeWingCfgProfVpnIkev2RemoteWinsEntry
			MAX-ACCESS not-accessible
			STATUS current
			DESCRIPTION
				"An entry in the table."
			INDEX { extremeWingCfgProfName, extremeWingCfgProfVpnIkev2RemoteWinsServerType }
			::= { extremeWingCfgProfVpnIkev2RemoteWinsTable 1 }

		
		ExtremeWingCfgProfVpnIkev2RemoteWinsEntry ::=
			SEQUENCE { 
				extremeWingCfgProfVpnIkev2RemoteWinsServerType
					ExtremeWingIdentifier,
				extremeWingCfgProfVpnIkev2RemoteWinsServerIp
					DisplayString
			 }

		-- 1.3.6.1.4.1.1916.2.131.50.1.3.16.18.20.1.1
		extremeWingCfgProfVpnIkev2RemoteWinsServerType OBJECT-TYPE
			SYNTAX ExtremeWingIdentifier
			MAX-ACCESS read-only
			STATUS current
			DESCRIPTION
				"Primary or Secondary WINS server.
				
				Values:
				primary,
				secondary
				
				XPath: /extremeWing-config/profile[name=key1]/ikev2_remote_vpn/wins[server_type=key2]/server_type"
			::= { extremeWingCfgProfVpnIkev2RemoteWinsEntry 1 }

		
		-- 1.3.6.1.4.1.1916.2.131.50.1.3.16.18.20.1.3
		extremeWingCfgProfVpnIkev2RemoteWinsServerIp OBJECT-TYPE
			SYNTAX DisplayString
			MAX-ACCESS read-write
			STATUS current
			DESCRIPTION
				"
				
				XPath: /extremeWing-config/profile[name=key1]/ikev2_remote_vpn/wins[server_type=key2]/server_ip"
			::= { extremeWingCfgProfVpnIkev2RemoteWinsEntry 3 }

		
		-- 1.3.6.1.4.1.1916.2.131.50.1.3.16.18.21
		extremeWingCfgProfVpnIkev2RemoteNameServerTable OBJECT-TYPE
			SYNTAX SEQUENCE OF ExtremeWingCfgProfVpnIkev2RemoteNameServerEntry
			MAX-ACCESS not-accessible
			STATUS current
			DESCRIPTION
				"
				
				/extremeWing-config/profile/ikev2_remote_vpn/nameserver"
			::= { extremeWingCfgProfVpn 21 }

		
		-- 1.3.6.1.4.1.1916.2.131.50.1.3.16.18.21.1
		extremeWingCfgProfVpnIkev2RemoteNameServerEntry OBJECT-TYPE
			SYNTAX ExtremeWingCfgProfVpnIkev2RemoteNameServerEntry
			MAX-ACCESS not-accessible
			STATUS current
			DESCRIPTION
				"An entry in the table."
			INDEX { extremeWingCfgProfName, extremeWingCfgProfVpnIkev2RemoteNameServerType }
			::= { extremeWingCfgProfVpnIkev2RemoteNameServerTable 1 }

		
		ExtremeWingCfgProfVpnIkev2RemoteNameServerEntry ::=
			SEQUENCE { 
				extremeWingCfgProfVpnIkev2RemoteNameServerType
					ExtremeWingIdentifier,
				extremeWingCfgProfVpnIkev2RemoteNameServerIp
					DisplayString
			 }

		-- 1.3.6.1.4.1.1916.2.131.50.1.3.16.18.21.1.1
		extremeWingCfgProfVpnIkev2RemoteNameServerType OBJECT-TYPE
			SYNTAX ExtremeWingIdentifier
			MAX-ACCESS read-only
			STATUS current
			DESCRIPTION
				"Primary or Secondary Name server.
				
				Values:
				primary,
				secondary
				
				XPath: /extremeWing-config/profile[name=key1]/ikev2_remote_vpn/nameserver[server_type=key2]/server_type"
			::= { extremeWingCfgProfVpnIkev2RemoteNameServerEntry 1 }

		
		-- 1.3.6.1.4.1.1916.2.131.50.1.3.16.18.21.1.3
		extremeWingCfgProfVpnIkev2RemoteNameServerIp OBJECT-TYPE
			SYNTAX DisplayString
			MAX-ACCESS read-write
			STATUS current
			DESCRIPTION
				"
				
				XPath: /extremeWing-config/profile[name=key1]/ikev2_remote_vpn/nameserver[server_type=key2]/server_ip"
			::= { extremeWingCfgProfVpnIkev2RemoteNameServerEntry 3 }

		
		-- 1.3.6.1.4.1.1916.2.131.50.1.3.16.18.22
		extremeWingCfgProfVpnAutoIPSecSecureTable OBJECT-TYPE
			SYNTAX SEQUENCE OF ExtremeWingCfgProfVpnAutoIPSecSecureEntry
			MAX-ACCESS not-accessible
			STATUS current
			DESCRIPTION
				"Description."
			::= { extremeWingCfgProfVpn 22 }

		
		-- 1.3.6.1.4.1.1916.2.131.50.1.3.16.18.22.1
		extremeWingCfgProfVpnAutoIPSecSecureEntry OBJECT-TYPE
			SYNTAX ExtremeWingCfgProfVpnAutoIPSecSecureEntry
			MAX-ACCESS not-accessible
			STATUS current
			DESCRIPTION
				"Description."
			INDEX { extremeWingCfgProfName }
			::= { extremeWingCfgProfVpnAutoIPSecSecureTable 1 }

		
		ExtremeWingCfgProfVpnAutoIPSecSecureEntry ::=
			SEQUENCE { 
				extremeWingCfgProfVpnAutoIPSecSecureGroupId
					OCTET STRING,
				extremeWingCfgProfVpnAutoIPSecSecureGroupIdAuthType
					DisplayString,
				extremeWingCfgProfVpnAutoIPSecSecureGroupIdAuthKey
					DisplayString,
				extremeWingCfgProfVpnAutoIPSecSecureRemoteGWIkeVersion
					DisplayString
			 }

		-- 1.3.6.1.4.1.1916.2.131.50.1.3.16.18.22.1.1
		extremeWingCfgProfVpnAutoIPSecSecureGroupId OBJECT-TYPE
			SYNTAX OCTET STRING (SIZE (1..128))
			MAX-ACCESS read-write
			STATUS current
			DESCRIPTION
				"Group identity to use in IKE exchange for auto ipsec secure peers.
				
				XPath: /extremeWing-config/profile[name=key1]/auto_ipsec_secure/group_id_auth_type_key/groupid_id"
			::= { extremeWingCfgProfVpnAutoIPSecSecureEntry 1 }

		
		-- 1.3.6.1.4.1.1916.2.131.50.1.3.16.18.22.1.2
		extremeWingCfgProfVpnAutoIPSecSecureGroupIdAuthType OBJECT-TYPE
			SYNTAX DisplayString
			MAX-ACCESS read-write
			STATUS current
			DESCRIPTION
				"The authentication type for auto ipsec secure peer authentication.
				
				XPath: /extremeWing-config/profile[name=key1]/auto_ipsec_secure/group_id_auth_type_key/groupid_auth_type"
			::= { extremeWingCfgProfVpnAutoIPSecSecureEntry 2 }

		
		-- 1.3.6.1.4.1.1916.2.131.50.1.3.16.18.22.1.3
		extremeWingCfgProfVpnAutoIPSecSecureGroupIdAuthKey OBJECT-TYPE
			SYNTAX DisplayString (SIZE (8..21))
			MAX-ACCESS read-write
			STATUS current
			DESCRIPTION
				"The shared secret used for auto ipsec secure peer authentication.
				
				XPath: /extremeWing-config/profile[name=key1]/auto_ipsec_secure/group_id_auth_type_key/groupid_auth_key"
			::= { extremeWingCfgProfVpnAutoIPSecSecureEntry 3 }

		
		-- 1.3.6.1.4.1.1916.2.131.50.1.3.16.18.22.1.4
		extremeWingCfgProfVpnAutoIPSecSecureRemoteGWIkeVersion OBJECT-TYPE
			SYNTAX DisplayString
			MAX-ACCESS read-write
			STATUS current
			DESCRIPTION
				"The ike version for auto ipsec secure authentication with ipsec gateway other than controllers.
				
				XPath: /extremeWing-config/profile[name=key1]/auto_ipsec_secure/remotegw_ike_version"
			::= { extremeWingCfgProfVpnAutoIPSecSecureEntry 4 }

		
-- /extremeWing-config/profile/controller_host
                -- 1.3.6.1.4.1.1916.2.131.50.1.3.16.19
                extremeWingCfgProfControllerHost OBJECT IDENTIFIER ::= { extremeWingCfgProf 19 }


                -- 1.3.6.1.4.1.1916.2.131.50.1.3.16.19.1
                extremeWingCfgProfControllerHostTable OBJECT-TYPE
                        SYNTAX SEQUENCE OF ExtremeWingCfgProfControllerHostEntry
                        MAX-ACCESS not-accessible
                        STATUS current
                        DESCRIPTION
                                "WLAN controller configuration

                                /extremeWing-config/profile/controller_host"
                        ::= { extremeWingCfgProfControllerHost 1 }


                -- 1.3.6.1.4.1.1916.2.131.50.1.3.16.19.1.1
                extremeWingCfgProfControllerHostEntry OBJECT-TYPE
                        SYNTAX ExtremeWingCfgProfControllerHostEntry
                        MAX-ACCESS not-accessible
                        STATUS current
                        DESCRIPTION
                                "An entry in the table."
                        INDEX { extremeWingCfgProfName, extremeWingCfgProfControllerHostHost, extremeWingCfgProfControllerHostPool, extremeWingCfgProfControllerHostLevel }
                        ::= { extremeWingCfgProfControllerHostTable 1 }


                ExtremeWingCfgProfControllerHostEntry ::=
                        SEQUENCE {
                                extremeWingCfgProfControllerHostHost
                                        DisplayString,
                                extremeWingCfgProfControllerHostPool
                                        Unsigned32,
                                extremeWingCfgProfControllerHostLevel
                                        Unsigned32,
                                extremeWingCfgProfControllerHostRowStatus
                                        RowStatus,
                                extremeWingCfgProfControllerHostForce
                                        TruthValue,
                                extremeWingCfgProfControllerHostRemoteVpnClient
                                        TruthValue,
                                extremeWingCfgProfControllerHostIPSecSecure
                                        TruthValue,
                                extremeWingCfgProfControllerHostIPSecGw
                                        IpAddress
                         }

                -- 1.3.6.1.4.1.1916.2.131.50.1.3.16.19.1.1.1
                extremeWingCfgProfControllerHostHost OBJECT-TYPE
                        SYNTAX DisplayString
                        MAX-ACCESS read-only
                        STATUS current
                        DESCRIPTION
                                "IP address or hostname of controller.

                                As this object is indirectly part of the key,
                                to change its value the row must be deleted and created with
                                the new key.

                                XPath: /extremeWing-config/profile[name=key1]/controller_host[host=key2,pool=key3,level=key4]/host"
                        ::= { extremeWingCfgProfControllerHostEntry 1 }


                -- 1.3.6.1.4.1.1916.2.131.50.1.3.16.19.1.1.2
                extremeWingCfgProfControllerHostPool OBJECT-TYPE
                        SYNTAX Unsigned32 (1..2)
                        MAX-ACCESS read-only
                        STATUS current
                        DESCRIPTION
                                "Pool this controller belongs to.

                                As this object is indirectly part of the key,
                                to change its value the row must be deleted and created with
                                the new key.

                                XPath: /extremeWing-config/profile[name=key1]/controller_host[host=key2,pool=key3,level=key4]/pool"
                        ::= { extremeWingCfgProfControllerHostEntry 2 }


                -- 1.3.6.1.4.1.1916.2.131.50.1.3.16.19.1.1.3
                extremeWingCfgProfControllerHostLevel OBJECT-TYPE
                        SYNTAX Unsigned32 (1..2)
                        MAX-ACCESS read-only
                        STATUS current
                        DESCRIPTION
                                "Routing level for controller link.

                                As this object is indirectly part of the key,
                                to change its value the row must be deleted and created with
                                the new key.

                                Values:
                                1  Level 1 (local)
                                2  Level 2 (inter-site)

                                XPath: /extremeWing-config/profile[name=key1]/controller_host[host=key2,pool=key3,level=key4]/level"
                        ::= { extremeWingCfgProfControllerHostEntry 3 }


                -- 1.3.6.1.4.1.1916.2.131.50.1.3.16.19.1.1.4
                extremeWingCfgProfControllerHostRowStatus OBJECT-TYPE
                        SYNTAX RowStatus
                                {
                                active(1),
                                createAndGo(4),
                                destroy(6)
                                }
                        MAX-ACCESS read-write
                        STATUS current
                        DESCRIPTION
                                "The status of this conceptual row.

                                XPath: /extremeWing-config/profile[name=key1]/controller_host[host=key2,pool=key3,level=key4]/row_status"
                        ::= { extremeWingCfgProfControllerHostEntry 4 }


                -- 1.3.6.1.4.1.1916.2.131.50.1.3.16.19.1.1.5
                extremeWingCfgProfControllerHostForce OBJECT-TYPE
                        SYNTAX TruthValue
                        MAX-ACCESS read-write
                        STATUS current
                        DESCRIPTION
                                "Force link to be created even when unnecessary.

                                XPath: /extremeWing-config/profile[name=key1]/controller_host[host=key2,pool=key3,level=key4]/force"
                        DEFVAL { false }
                        ::= { extremeWingCfgProfControllerHostEntry 5 }


                -- 1.3.6.1.4.1.1916.2.131.50.1.3.16.19.1.1.6
                extremeWingCfgProfControllerHostRemoteVpnClient OBJECT-TYPE
                        SYNTAX TruthValue
                        MAX-ACCESS read-write
                        STATUS current
                        DESCRIPTION
                                "Secure controller link using remote vpn connection.

                                XPath: /extremeWing-config/profile[name=key1]/controller_host[host=key2,pool=key3,level=key4]/remote_vpn_client"
                        DEFVAL { false }
                        ::= { extremeWingCfgProfControllerHostEntry 6 }


                -- 1.3.6.1.4.1.1916.2.131.50.1.3.16.19.1.1.7
                extremeWingCfgProfControllerHostIPSecSecure OBJECT-TYPE
                        SYNTAX TruthValue
                        MAX-ACCESS read-write
                        STATUS current
                        DESCRIPTION
                                "IPSec secure controller link.

                                XPath: /extremeWing-config/profile[name=key1]/controller_host[host=key2,pool=key3,level=key4]/ipsec_secure"
                        DEFVAL { false }
                        ::= { extremeWingCfgProfControllerHostEntry 7 }


                -- 1.3.6.1.4.1.1916.2.131.50.1.3.16.19.1.1.8
                extremeWingCfgProfControllerHostIPSecGw OBJECT-TYPE
                        SYNTAX IpAddress
                        MAX-ACCESS read-write
                        STATUS current
                        DESCRIPTION
                                "IP address or hostname of controller.

                                XPath: /extremeWing-config/profile[name=key1]/controller_host[host=key2,pool=key3,level=key4]/ipsec_gw"
                        ::= { extremeWingCfgProfControllerHostEntry 8 }
		
		-- 1.3.6.1.4.1.1916.2.131.50.1.3.16.20
		extremeWingCfgProfDynRoute OBJECT IDENTIFIER ::= { extremeWingCfgProf 20 }

		
		-- 1.3.6.1.4.1.1916.2.131.50.1.3.16.20.1
		extremeWingCfgProfDynRouteOspfTable OBJECT-TYPE
			SYNTAX SEQUENCE OF ExtremeWingCfgProfDynRouteOspfEntry
			MAX-ACCESS not-accessible
			STATUS current
			DESCRIPTION
				"Route Ospf Table.
				
				/extremeWing-config/profile/dynamic_router_ospf"
			::= { extremeWingCfgProfDynRoute 1 }

		
		-- 1.3.6.1.4.1.1916.2.131.50.1.3.16.20.1.1
		extremeWingCfgProfDynRouteOspfEntry OBJECT-TYPE
			SYNTAX ExtremeWingCfgProfDynRouteOspfEntry
			MAX-ACCESS not-accessible
			STATUS current
			DESCRIPTION
				"An entry in the table."
			INDEX { extremeWingCfgProfName }
			::= { extremeWingCfgProfDynRouteOspfTable 1 }

		
		ExtremeWingCfgProfDynRouteOspfEntry ::=
			SEQUENCE { 
				extremeWingCfgProfDynRouteOspfEnabled
					TruthValue,
				extremeWingCfgProfDynRouteOspfRouterId
					OCTET STRING,
				extremeWingCfgProfDynRouteOspfAutoCost
					Unsigned32,
				extremeWingCfgProfDynRouteOspfPassiveAll
					TruthValue,
				extremeWingCfgProfDynRouteOspfPassive
					DisplayString,
				extremeWingCfgProfDynRouteOspfPassiveRemoved
					DisplayString,
				extremeWingCfgProfDynRouteOspfVrrpStateCheck
					TruthValue,
				extremeWingCfgProfDynRouteOspfDefaultRoutePriority
					Unsigned32,
				extremeWingCfgProfDynRouteOspfNumRoutes
					Unsigned32,
				extremeWingCfgProfDynRouteOspfRetryCount
					Unsigned32,
				extremeWingCfgProfDynRouteOspfRetryTimeout
					Unsigned32,
				extremeWingCfgProfDynRouteOspfResetTime
					Unsigned32
			 }

		-- 1.3.6.1.4.1.1916.2.131.50.1.3.16.20.1.1.1
		extremeWingCfgProfDynRouteOspfEnabled OBJECT-TYPE
			SYNTAX TruthValue
			MAX-ACCESS read-write
			STATUS current
			DESCRIPTION
				"Dynamic routing protocol OSPF
				
				XPath: /extremeWing-config/profile[name=key1]/dynamic_router_ospf/ospf"
			DEFVAL { false }
			::= { extremeWingCfgProfDynRouteOspfEntry 1 }

		
		-- 1.3.6.1.4.1.1916.2.131.50.1.3.16.20.1.1.2
		extremeWingCfgProfDynRouteOspfRouterId OBJECT-TYPE
			SYNTAX OCTET STRING
			MAX-ACCESS read-write
			STATUS current
			DESCRIPTION
				"Router-ID for this device. If Router-ID is not configured, system generates one and it can be viewed in statistics
				
				XPath: /extremeWing-config/profile[name=key1]/dynamic_router_ospf/router_id"
			::= { extremeWingCfgProfDynRouteOspfEntry 2 }

		
		-- 1.3.6.1.4.1.1916.2.131.50.1.3.16.20.1.1.3
		extremeWingCfgProfDynRouteOspfAutoCost OBJECT-TYPE
			SYNTAX Unsigned32 (1..4294967)
			MAX-ACCESS read-write
			STATUS current
			DESCRIPTION
				"Specifies reference bandwidth to be used in Mbps to calculate OSPF interface cost if OSPF area is STUB or NSSA
				
				XPath: /extremeWing-config/profile[name=key1]/dynamic_router_ospf/auto_cost"
			::= { extremeWingCfgProfDynRouteOspfEntry 3 }

		
		-- 1.3.6.1.4.1.1916.2.131.50.1.3.16.20.1.1.4
		extremeWingCfgProfDynRouteOspfPassiveAll OBJECT-TYPE
			SYNTAX TruthValue
			MAX-ACCESS read-write
			STATUS current
			DESCRIPTION
				"Configures all L3 interfaces as OSPF passive interface
				
				XPath: /extremeWing-config/profile[name=key1]/dynamic_router_ospf/passive_all"
			DEFVAL { false }
			::= { extremeWingCfgProfDynRouteOspfEntry 4 }

		
		-- 1.3.6.1.4.1.1916.2.131.50.1.3.16.20.1.1.5
		extremeWingCfgProfDynRouteOspfPassive OBJECT-TYPE
			SYNTAX DisplayString
			MAX-ACCESS read-write
			STATUS current
			DESCRIPTION
				"Configures specified interface(s) as OSPF passive interface(s).
				
				XPath: /extremeWing-config/profile[name=key1]/dynamic_router_ospf/passive"
			::= { extremeWingCfgProfDynRouteOspfEntry 5 }

		
		-- 1.3.6.1.4.1.1916.2.131.50.1.3.16.20.1.1.6
		extremeWingCfgProfDynRouteOspfPassiveRemoved OBJECT-TYPE
			SYNTAX DisplayString
			MAX-ACCESS read-write
			STATUS current
			DESCRIPTION
				"Configures specified interface(s) as OSPF NON-passive interface(s).
				
				XPath: /extremeWing-config/profile[name=key1]/dynamic_router_ospf/passive_removed"
			REFERENCE
				"Configures specified interface(s) as OSPF NON-passive interface(s)."
			::= { extremeWingCfgProfDynRouteOspfEntry 6 }

		
		-- 1.3.6.1.4.1.1916.2.131.50.1.3.16.20.1.1.7
		extremeWingCfgProfDynRouteOspfVrrpStateCheck OBJECT-TYPE
			SYNTAX TruthValue
			MAX-ACCESS read-write
			STATUS current
			DESCRIPTION
				"Publish interface via OSPF only if the interface VRRP state is not BACKUP.
				
				XPath: /extremeWing-config/profile[name=key1]/dynamic_router_ospf/vrrp_state_check"
			::= { extremeWingCfgProfDynRouteOspfEntry 7 }

		
		-- 1.3.6.1.4.1.1916.2.131.50.1.3.16.20.1.1.8
		extremeWingCfgProfDynRouteOspfDefaultRoutePriority OBJECT-TYPE
			SYNTAX Unsigned32 (1..8000)
			MAX-ACCESS read-write
			STATUS current
			DESCRIPTION
				"Priority for the default route learnt via OSPF.
				
				XPath: /extremeWing-config/profile[name=key1]/dynamic_router_ospf/ospf_default_route_priority"
			DEFVAL { 7000 }
			::= { extremeWingCfgProfDynRouteOspfEntry 8 }

		
		-- 1.3.6.1.4.1.1916.2.131.50.1.3.16.20.1.1.9
		extremeWingCfgProfDynRouteOspfNumRoutes OBJECT-TYPE
			SYNTAX Unsigned32 (1..4294967295)
			MAX-ACCESS read-write
			STATUS current
			DESCRIPTION
				"Maximum number of OSPF routes allowed.
				
				XPath: /extremeWing-config/profile[name=key1]/dynamic_router_ospf/route_limit/num_routes"
			::= { extremeWingCfgProfDynRouteOspfEntry 9 }

		
		-- 1.3.6.1.4.1.1916.2.131.50.1.3.16.20.1.1.10
		extremeWingCfgProfDynRouteOspfRetryCount OBJECT-TYPE
			SYNTAX Unsigned32 (1..32)
			MAX-ACCESS read-write
			STATUS current
			DESCRIPTION
				"Maximum number for which OSPF process will be reset before permanently shutting down OSPF.
				
				XPath: /extremeWing-config/profile[name=key1]/dynamic_router_ospf/route_limit/retry_count"
			DEFVAL { 5 }
			::= { extremeWingCfgProfDynRouteOspfEntry 10 }

		
		-- 1.3.6.1.4.1.1916.2.131.50.1.3.16.20.1.1.11
		extremeWingCfgProfDynRouteOspfRetryTimeout OBJECT-TYPE
			SYNTAX Unsigned32 (1..300)
			MAX-ACCESS read-write
			STATUS current
			DESCRIPTION
				"Time in seconds during which the OSPF process remains shut before attempting next retry.
				
				XPath: /extremeWing-config/profile[name=key1]/dynamic_router_ospf/route_limit/retry_timeout"
			DEFVAL { 60 }
			::= { extremeWingCfgProfDynRouteOspfEntry 11 }

		
		-- 1.3.6.1.4.1.1916.2.131.50.1.3.16.20.1.1.12
		extremeWingCfgProfDynRouteOspfResetTime OBJECT-TYPE
			SYNTAX Unsigned32 (1..9600)
			MAX-ACCESS read-write
			STATUS current
			DESCRIPTION
				"Time in seconds after which retry-count is reset to zero.
				
				XPath: /extremeWing-config/profile[name=key1]/dynamic_router_ospf/route_limit/reset_time"
			DEFVAL { 360 }
			::= { extremeWingCfgProfDynRouteOspfEntry 12 }

		
		-- 1.3.6.1.4.1.1916.2.131.50.1.3.16.20.2
		extremeWingCfgProfDynRouteOspfNetworkTable OBJECT-TYPE
			SYNTAX SEQUENCE OF ExtremeWingCfgProfDynRouteOspfNetworkEntry
			MAX-ACCESS not-accessible
			STATUS current
			DESCRIPTION
				"Route Ospf Network Table
				
				/extremeWing-config/profile/dynamic_router_cfg/ospf_network"
			::= { extremeWingCfgProfDynRoute 2 }

		
		-- 1.3.6.1.4.1.1916.2.131.50.1.3.16.20.2.1
		extremeWingCfgProfDynRouteOspfNetworkEntry OBJECT-TYPE
			SYNTAX ExtremeWingCfgProfDynRouteOspfNetworkEntry
			MAX-ACCESS not-accessible
			STATUS current
			DESCRIPTION
				"An entry in the table."
			INDEX { extremeWingCfgProfName, extremeWingCfgProfDynRouteOspfNetwork }
			::= { extremeWingCfgProfDynRouteOspfNetworkTable 1 }

		
		ExtremeWingCfgProfDynRouteOspfNetworkEntry ::=
			SEQUENCE { 
				extremeWingCfgProfDynRouteOspfNetwork
					ExtremeWingIdentifier,
				extremeWingCfgProfDynRouteOspfNetworkAreaId
					DisplayString
			 }

		-- 1.3.6.1.4.1.1916.2.131.50.1.3.16.20.2.1.1
		extremeWingCfgProfDynRouteOspfNetwork OBJECT-TYPE
			SYNTAX ExtremeWingIdentifier
			MAX-ACCESS read-only
			STATUS current
			DESCRIPTION
				"Networks that need to participate in OSPF
				
				XPath: /extremeWing-config/profile[name=key1]/dynamic_router_ospf/ospf_network[network=key2]/network"
			::= { extremeWingCfgProfDynRouteOspfNetworkEntry 1 }

		
		-- 1.3.6.1.4.1.1916.2.131.50.1.3.16.20.2.1.3
		extremeWingCfgProfDynRouteOspfNetworkAreaId OBJECT-TYPE
			SYNTAX DisplayString
			MAX-ACCESS read-write
			STATUS current
			DESCRIPTION
				"OSPF area to which this network belongs; area is a 32 bit number, which can be represented as IPv4 address
				
				XPath: /extremeWing-config/profile[name=key1]/dynamic_router_ospf/ospf_network[network=key2]/area_id"
			::= { extremeWingCfgProfDynRouteOspfNetworkEntry 3 }

		
		-- 1.3.6.1.4.1.1916.2.131.50.1.3.16.20.3
		extremeWingCfgProfDynRouteOspfAreaTable OBJECT-TYPE
			SYNTAX SEQUENCE OF ExtremeWingCfgProfDynRouteOspfAreaEntry
			MAX-ACCESS not-accessible
			STATUS current
			DESCRIPTION
				"RouteOspfAreaTable
				
				/extremeWing-config/profile/dynamic_router_cfg/ospf_area"
			::= { extremeWingCfgProfDynRoute 3 }

		
		-- 1.3.6.1.4.1.1916.2.131.50.1.3.16.20.3.1
		extremeWingCfgProfDynRouteOspfAreaEntry OBJECT-TYPE
			SYNTAX ExtremeWingCfgProfDynRouteOspfAreaEntry
			MAX-ACCESS not-accessible
			STATUS current
			DESCRIPTION
				"An entry in the table."
			INDEX { extremeWingCfgProfName, extremeWingCfgProfDynRouteOspfAreaId }
			::= { extremeWingCfgProfDynRouteOspfAreaTable 1 }

		
		ExtremeWingCfgProfDynRouteOspfAreaEntry ::=
			SEQUENCE { 
				extremeWingCfgProfDynRouteOspfAreaId
					ExtremeWingIdentifier,
				extremeWingCfgProfDynRouteOspfAreaAuthentication
					DisplayString,
				extremeWingCfgProfDynRouteOspfAreaRange
					DisplayString,
				extremeWingCfgProfDynRouteOspfAreaType
					DisplayString,
				extremeWingCfgProfDynRouteOspfAreaDefaultCost
					Unsigned32,
				extremeWingCfgProfDynRouteOspfAreaTranslateType
					DisplayString
			 }

		-- 1.3.6.1.4.1.1916.2.131.50.1.3.16.20.3.1.1
		extremeWingCfgProfDynRouteOspfAreaId OBJECT-TYPE
			SYNTAX ExtremeWingIdentifier
			MAX-ACCESS read-only
			STATUS current
			DESCRIPTION
				"OSPF area related parameters
                                 area id can be represented as IPv4 address or a 32 bit number between (0..4294967294).
				
				XPath: /extremeWing-config/profile[name=key1]/dynamic_router_ospf/ospf_area[ospf_area_id=key2]/ospf_area_id"
			::= { extremeWingCfgProfDynRouteOspfAreaEntry 1 }

		
		-- 1.3.6.1.4.1.1916.2.131.50.1.3.16.20.3.1.3
		extremeWingCfgProfDynRouteOspfAreaAuthentication OBJECT-TYPE
			SYNTAX DisplayString
			MAX-ACCESS read-write
			STATUS current
			DESCRIPTION
				"OSPF authentication type
				
				Values:
				simple-password,
				message-digest,
				none
				
				XPath: /extremeWing-config/profile[name=key1]/dynamic_router_ospf/ospf_area[ospf_area_id=key2]/authentication"
			DEFVAL { "none" }
			::= { extremeWingCfgProfDynRouteOspfAreaEntry 3 }

		
		-- 1.3.6.1.4.1.1916.2.131.50.1.3.16.20.3.1.4
		extremeWingCfgProfDynRouteOspfAreaRange OBJECT-TYPE
			SYNTAX DisplayString
			MAX-ACCESS read-only
			STATUS current
			DESCRIPTION
				"Specifies the routes matching address/mask for summarization
				
				XPath: /extremeWing-config/profile[name=key1]/dynamic_router_ospf/ospf_area[ospf_area_id=key2]/range"
			::= { extremeWingCfgProfDynRouteOspfAreaEntry 4 }

		
		-- 1.3.6.1.4.1.1916.2.131.50.1.3.16.20.3.1.5
		extremeWingCfgProfDynRouteOspfAreaType OBJECT-TYPE
			SYNTAX DisplayString
			MAX-ACCESS read-write
			STATUS current
			DESCRIPTION
				"Type of this OSPF area
				
				Values:
				stub,
				totally-stub,
				nssa,
				totally-nssa,
				non-stub
				
				XPath: /extremeWing-config/profile[name=key1]/dynamic_router_ospf/ospf_area[ospf_area_id=key2]/area_type/type"
			DEFVAL { "non-stub" }
			::= { extremeWingCfgProfDynRouteOspfAreaEntry 5 }

		
		-- 1.3.6.1.4.1.1916.2.131.50.1.3.16.20.3.1.6
		extremeWingCfgProfDynRouteOspfAreaDefaultCost OBJECT-TYPE
			SYNTAX Unsigned32 (1..16777215)
			MAX-ACCESS read-write
			STATUS current
			DESCRIPTION
				"Default summary cost that will be advertised if this are is stub
				
				XPath: /extremeWing-config/profile[name=key1]/dynamic_router_ospf/ospf_area[ospf_area_id=key2]/area_type/default_cost"
			::= { extremeWingCfgProfDynRouteOspfAreaEntry 6 }

		
		-- 1.3.6.1.4.1.1916.2.131.50.1.3.16.20.3.1.7
		extremeWingCfgProfDynRouteOspfAreaTranslateType OBJECT-TYPE
			SYNTAX DisplayString
			MAX-ACCESS read-write
			STATUS current
			DESCRIPTION
				"Configures if/how LSA Type 7 message shall be translated
				
				Values:
				translate-always,
				translate-candidate,
				translate-never
				
				XPath: /extremeWing-config/profile[name=key1]/dynamic_router_ospf/ospf_area[ospf_area_id=key2]/area_type/translate_type"
			::= { extremeWingCfgProfDynRouteOspfAreaEntry 7 }

		
		-- 1.3.6.1.4.1.1916.2.131.50.1.3.16.20.4
		extremeWingCfgProfDynRouteDefaultInfoTable OBJECT-TYPE
			SYNTAX SEQUENCE OF ExtremeWingCfgProfDynRouteDefaultInfoEntry
			MAX-ACCESS not-accessible
			STATUS current
			DESCRIPTION
				"Description."
			::= { extremeWingCfgProfDynRoute 4 }
-- Dyn Route Default Info.
-- 
-- XPath: /extremeWing-config/device[mac=key1]/dynamic_router_ospf/default_information
		
		-- 1.3.6.1.4.1.1916.2.131.50.1.3.16.20.4.1
		extremeWingCfgProfDynRouteDefaultInfoEntry OBJECT-TYPE
			SYNTAX ExtremeWingCfgProfDynRouteDefaultInfoEntry
			MAX-ACCESS not-accessible
			STATUS current
			DESCRIPTION
				"An entry in the table."
			INDEX { extremeWingCfgProfName }
			::= { extremeWingCfgProfDynRouteDefaultInfoTable 1 }

		
		ExtremeWingCfgProfDynRouteDefaultInfoEntry ::=
			SEQUENCE { 
				extremeWingCfgProfDynRouteDefaultInfoOriginate
					TruthValue,
				extremeWingCfgProfDynRouteDefaultInfoAlways
					TruthValue,
				extremeWingCfgProfDynRouteDefaultInfoRtMetric
					Unsigned32,
				extremeWingCfgProfDynRouteDefaultInfoRtMetricType
					DisplayString
			 }

		-- 1.3.6.1.4.1.1916.2.131.50.1.3.16.20.4.1.1
		extremeWingCfgProfDynRouteDefaultInfoOriginate OBJECT-TYPE
			SYNTAX TruthValue
			MAX-ACCESS read-write
			STATUS current
			DESCRIPTION
				"Specifies whether default route should be distributed or not.
				
				XPath: /extremeWing-config/profile[name=key1]/dynamic_router_ospf/default_information/originate"
			::= { extremeWingCfgProfDynRouteDefaultInfoEntry 1 }

		
		-- 1.3.6.1.4.1.1916.2.131.50.1.3.16.20.4.1.2
		extremeWingCfgProfDynRouteDefaultInfoAlways OBJECT-TYPE
			SYNTAX TruthValue
			MAX-ACCESS read-write
			STATUS current
			DESCRIPTION
				"Originate a default route even if one is not present in routing table.
				
				XPath: /extremeWing-config/profile[name=key1]/dynamic_router_ospf/default_information/always"
			::= { extremeWingCfgProfDynRouteDefaultInfoEntry 2 }

		
		-- 1.3.6.1.4.1.1916.2.131.50.1.3.16.20.4.1.3
		extremeWingCfgProfDynRouteDefaultInfoRtMetric OBJECT-TYPE
			SYNTAX Unsigned32 (1..16777214)
			MAX-ACCESS read-write
			STATUS current
			DESCRIPTION
				"Metric for default route.
				
				XPath: /extremeWing-config/profile[name=key1]/dynamic_router_ospf/default_information/default_rt_metric"
			::= { extremeWingCfgProfDynRouteDefaultInfoEntry 3 }

		
		-- 1.3.6.1.4.1.1916.2.131.50.1.3.16.20.4.1.4
		extremeWingCfgProfDynRouteDefaultInfoRtMetricType OBJECT-TYPE
			SYNTAX DisplayString
			MAX-ACCESS read-write
			STATUS current
			DESCRIPTION
				"OSPF exterior metric type for default route.
				
				XPath: /extremeWing-config/profile[name=key1]/dynamic_router_ospf/default_information/default_rt_metric_type"
			::= { extremeWingCfgProfDynRouteDefaultInfoEntry 4 }

		
		-- 1.3.6.1.4.1.1916.2.131.50.1.3.16.20.5
		extremeWingCfgProfDynRouteRedistributeTable OBJECT-TYPE
			SYNTAX SEQUENCE OF ExtremeWingCfgProfDynRouteRedistributeEntry
			MAX-ACCESS not-accessible
			STATUS current
			DESCRIPTION
				"
				
				/extremeWing-config/profile/dynamic_router_cfg/redistribute"
			::= { extremeWingCfgProfDynRoute 5 }

		
		-- 1.3.6.1.4.1.1916.2.131.50.1.3.16.20.5.1
		extremeWingCfgProfDynRouteRedistributeEntry OBJECT-TYPE
			SYNTAX ExtremeWingCfgProfDynRouteRedistributeEntry
			MAX-ACCESS not-accessible
			STATUS current
			DESCRIPTION
				"An entry in the table."
			INDEX { extremeWingCfgProfName, extremeWingCfgProfDynRouteRedistributeRouteType }
			::= { extremeWingCfgProfDynRouteRedistributeTable 1 }

		
		ExtremeWingCfgProfDynRouteRedistributeEntry ::=
			SEQUENCE { 
				extremeWingCfgProfDynRouteRedistributeRouteType
					ExtremeWingIdentifier,
				extremeWingCfgProfDynRouteRedistributeMetric
					Unsigned32,
				extremeWingCfgProfDynRouteRedistributeMetricType
					DisplayString
			 }

		-- 1.3.6.1.4.1.1916.2.131.50.1.3.16.20.5.1.1
		extremeWingCfgProfDynRouteRedistributeRouteType OBJECT-TYPE
			SYNTAX ExtremeWingIdentifier
			MAX-ACCESS read-only
			STATUS current
			DESCRIPTION
				"Type of redistributed type
				
				Values:
				connected,
				kernel,
				static
				
				XPath: /extremeWing-config/profile[name=key1]/dynamic_router_ospf/redistribute[route_type=key2]/route_type"
			::= { extremeWingCfgProfDynRouteRedistributeEntry 1 }

		
		-- 1.3.6.1.4.1.1916.2.131.50.1.3.16.20.5.1.3
		extremeWingCfgProfDynRouteRedistributeMetric OBJECT-TYPE
			SYNTAX Unsigned32 (1..16777214)
			MAX-ACCESS read-write
			STATUS current
			DESCRIPTION
				"Metric for redistributed routes
				
				XPath: /extremeWing-config/profile[name=key1]/dynamic_router_ospf/redistribute[route_type=key2]/metric"
			::= { extremeWingCfgProfDynRouteRedistributeEntry 3 }

		
		-- 1.3.6.1.4.1.1916.2.131.50.1.3.16.20.5.1.4
		extremeWingCfgProfDynRouteRedistributeMetricType OBJECT-TYPE
			SYNTAX DisplayString
			MAX-ACCESS read-write
			STATUS current
			DESCRIPTION
				"OSPF exterior metric type for redistributed routes
				
				Values:
				1,
				2
				
				XPath: /extremeWing-config/profile[name=key1]/dynamic_router_ospf/redistribute[route_type=key2]/metric_type"
			::= { extremeWingCfgProfDynRouteRedistributeEntry 4 }

		
		-- 1.3.6.1.4.1.1916.2.131.50.1.3.16.21
		extremeWingCfgProfVrrp OBJECT IDENTIFIER ::= { extremeWingCfgProf 21 }

		
		-- 1.3.6.1.4.1.1916.2.131.50.1.3.16.21.1
		extremeWingCfgProfVrrpTable OBJECT-TYPE
			SYNTAX SEQUENCE OF ExtremeWingCfgProfVrrpEntry
			MAX-ACCESS not-accessible
			STATUS current
			DESCRIPTION
				"
				
				/extremeWing-config/profile"
			::= { extremeWingCfgProfVrrp 1 }

		
		-- 1.3.6.1.4.1.1916.2.131.50.1.3.16.21.1.1
		extremeWingCfgProfVrrpEntry OBJECT-TYPE
			SYNTAX ExtremeWingCfgProfVrrpEntry
			MAX-ACCESS not-accessible
			STATUS current
			DESCRIPTION
				"An entry in the table."
			INDEX { extremeWingCfgProfName }
			::= { extremeWingCfgProfVrrpTable 1 }

		
		ExtremeWingCfgProfVrrpEntry ::=
			SEQUENCE { 
				extremeWingCfgProfVrrpVersion
					DisplayString
			 }

		-- 1.3.6.1.4.1.1916.2.131.50.1.3.16.21.1.1.1
		extremeWingCfgProfVrrpVersion OBJECT-TYPE
			SYNTAX DisplayString
			MAX-ACCESS read-write
			STATUS current
			DESCRIPTION
				"VRRP version supported by the device
				
				Values:
				3
				
				XPath: /extremeWing-config/profile[name=key1]/vrrp_version"
			DEFVAL { "2" }
			::= { extremeWingCfgProfVrrpEntry 1 }

		
		-- 1.3.6.1.4.1.1916.2.131.50.1.3.16.21.2
		extremeWingCfgProfVrrpGroupTable OBJECT-TYPE
			SYNTAX SEQUENCE OF ExtremeWingCfgProfVrrpGroupEntry
			MAX-ACCESS not-accessible
			STATUS current
			DESCRIPTION
				"
				
				/extremeWing-config/profile/vrrp_groups"
			::= { extremeWingCfgProfVrrp 2 }

		
		-- 1.3.6.1.4.1.1916.2.131.50.1.3.16.21.2.1
		extremeWingCfgProfVrrpGroupEntry OBJECT-TYPE
			SYNTAX ExtremeWingCfgProfVrrpGroupEntry
			MAX-ACCESS not-accessible
			STATUS current
			DESCRIPTION
				"An entry in the table."
			INDEX { extremeWingCfgProfName, extremeWingCfgProfVrrpGroupVirtualRouterId }
			::= { extremeWingCfgProfVrrpGroupTable 1 }

		
		ExtremeWingCfgProfVrrpGroupEntry ::=
			SEQUENCE { 
				extremeWingCfgProfVrrpGroupVirtualRouterId
					Unsigned32,
				extremeWingCfgProfVrrpGroupDescription
					DisplayString,
				extremeWingCfgProfVrrpGroupPriority
					Unsigned32,
				extremeWingCfgProfVrrpGroupAdvertisementUnit
					DisplayString,
				extremeWingCfgProfVrrpGroupAdvertisementIntervalV2
					Unsigned32,
				extremeWingCfgProfVrrpGroupAdvertisementIntervalV2Msec
					Unsigned32,
				extremeWingCfgProfVrrpGroupAdvertisementIntervalV3
					Unsigned32,
				extremeWingCfgProfVrrpGroupPreempt
					TruthValue,
				extremeWingCfgProfVrrpGroupPreemptDelay
					Unsigned32,
				extremeWingCfgProfVrrpGroupCrmAction
					DisplayString,
				extremeWingCfgProfVrrpGroupDeltaPriority
					Unsigned32,
				extremeWingCfgProfVrrpGroupInterface
					Unsigned32,
				extremeWingCfgProfVrrpGroupSyncGroup
					TruthValue
			 }

		-- 1.3.6.1.4.1.1916.2.131.50.1.3.16.21.2.1.1
		extremeWingCfgProfVrrpGroupVirtualRouterId OBJECT-TYPE
			SYNTAX Unsigned32 (1..255)
			MAX-ACCESS read-only
			STATUS current
			DESCRIPTION
				"Identifies the virtual router and used for associating VRRP packet with this field
				
				XPath: /extremeWing-config/profile[name=key1]/vrrp_groups[virtual_router_id=key2]/virtual_router_id"
			::= { extremeWingCfgProfVrrpGroupEntry 1 }

		
		-- 1.3.6.1.4.1.1916.2.131.50.1.3.16.21.2.1.3
		extremeWingCfgProfVrrpGroupDescription OBJECT-TYPE
			SYNTAX DisplayString (SIZE (1..64))
			MAX-ACCESS read-write
			STATUS current
			DESCRIPTION
				"Assigns a text description to the VRRP group
				
				XPath: /extremeWing-config/profile[name=key1]/vrrp_groups[virtual_router_id=key2]/description"
			::= { extremeWingCfgProfVrrpGroupEntry 3 }

		
		-- 1.3.6.1.4.1.1916.2.131.50.1.3.16.21.2.1.4
		extremeWingCfgProfVrrpGroupPriority OBJECT-TYPE
			SYNTAX Unsigned32 (1..254)
			MAX-ACCESS read-write
			STATUS current
			DESCRIPTION
				"the priority to be used for the virtual router master election process.  Higher values imply higher priority.
				
				XPath: /extremeWing-config/profile[name=key1]/vrrp_groups[virtual_router_id=key2]/priority"
			DEFVAL { 100 }
			::= { extremeWingCfgProfVrrpGroupEntry 4 }

		
		-- 1.3.6.1.4.1.1916.2.131.50.1.3.16.21.2.1.5
		extremeWingCfgProfVrrpGroupAdvertisementUnit OBJECT-TYPE
			SYNTAX DisplayString
			MAX-ACCESS read-write
			STATUS current
			DESCRIPTION
				"unit of the advertisment interval
				
				Values:
				seconds,
				milliseconds,
				centiseconds
				
				XPath: /extremeWing-config/profile[name=key1]/vrrp_groups[virtual_router_id=key2]/advertisement_interval/advertisement_unit"
			DEFVAL { "seconds" }
			::= { extremeWingCfgProfVrrpGroupEntry 5 }

		
		-- 1.3.6.1.4.1.1916.2.131.50.1.3.16.21.2.1.6
		extremeWingCfgProfVrrpGroupAdvertisementIntervalV2 OBJECT-TYPE
			SYNTAX Unsigned32 (1..255)
			UNITS "seconds"
			MAX-ACCESS read-write
			STATUS current
			DESCRIPTION
				"Time interval between VRRP advertisments
				
				XPath: /extremeWing-config/profile[name=key1]/vrrp_groups[virtual_router_id=key2]/advertisement_interval/advertisement_interval_v2"
			DEFVAL { 1 }
			::= { extremeWingCfgProfVrrpGroupEntry 6 }

		
		-- 1.3.6.1.4.1.1916.2.131.50.1.3.16.21.2.1.7
		extremeWingCfgProfVrrpGroupAdvertisementIntervalV2Msec OBJECT-TYPE
			SYNTAX Unsigned32 (50..999)
			UNITS "milliseconds"
			MAX-ACCESS read-write
			STATUS current
			DESCRIPTION
				"Time interval between VRRP advertisments
				
				XPath: /extremeWing-config/profile[name=key1]/vrrp_groups[virtual_router_id=key2]/advertisement_interval/advertisement_interval_v2_msec"
			::= { extremeWingCfgProfVrrpGroupEntry 7 }

		
		-- 1.3.6.1.4.1.1916.2.131.50.1.3.16.21.2.1.8
		extremeWingCfgProfVrrpGroupAdvertisementIntervalV3 OBJECT-TYPE
			SYNTAX Unsigned32 (1..4095)
			UNITS "centiseconds"
			MAX-ACCESS read-write
			STATUS current
			DESCRIPTION
				"Time interval between VRRP advertisments
				
				XPath: /extremeWing-config/profile[name=key1]/vrrp_groups[virtual_router_id=key2]/advertisement_interval/advertisement_interval_v3"
			DEFVAL { 100 }
			::= { extremeWingCfgProfVrrpGroupEntry 8 }

		
		-- 1.3.6.1.4.1.1916.2.131.50.1.3.16.21.2.1.9
		extremeWingCfgProfVrrpGroupPreempt OBJECT-TYPE
			SYNTAX TruthValue
			MAX-ACCESS read-write
			STATUS current
			DESCRIPTION
				"Controls whether a higher priority backup router will preempt a lower priority master.
				
				XPath: /extremeWing-config/profile[name=key1]/vrrp_groups[virtual_router_id=key2]/preemption/preempt"
			DEFVAL { true }
			::= { extremeWingCfgProfVrrpGroupEntry 9 }

		
		-- 1.3.6.1.4.1.1916.2.131.50.1.3.16.21.2.1.10
		extremeWingCfgProfVrrpGroupPreemptDelay OBJECT-TYPE
			SYNTAX Unsigned32 (1..65535)
			UNITS "seconds"
			MAX-ACCESS read-write
			STATUS current
			DESCRIPTION
				"Delay interval for pre-emption
				
				XPath: /extremeWing-config/profile[name=key1]/vrrp_groups[virtual_router_id=key2]/preemption/preempt_delay"
			::= { extremeWingCfgProfVrrpGroupEntry 10 }

		
		-- 1.3.6.1.4.1.1916.2.131.50.1.3.16.21.2.1.11
		extremeWingCfgProfVrrpGroupCrmAction OBJECT-TYPE
			SYNTAX DisplayString
			MAX-ACCESS read-write
			STATUS current
			DESCRIPTION
				"Backup virtual router may raise its priority in case the critical resources connected via the master router fail so that
				
				Values:
				increment-priority,
				decrement-priority,
				none
				
				XPath: /extremeWing-config/profile[name=key1]/vrrp_groups[virtual_router_id=key2]/crm_action"
			DEFVAL { "none" }
			::= { extremeWingCfgProfVrrpGroupEntry 11 }

		
		-- 1.3.6.1.4.1.1916.2.131.50.1.3.16.21.2.1.12
		extremeWingCfgProfVrrpGroupDeltaPriority OBJECT-TYPE
			SYNTAX Unsigned32 (1..253)
			MAX-ACCESS read-write
			STATUS current
			DESCRIPTION
				"The configured priority will be decremented by this value when the monitored interface state is down. In case of critical resource monitoring, the configured priority will be incremented by this value
				
				XPath: /extremeWing-config/profile[name=key1]/vrrp_groups[virtual_router_id=key2]/delta_priority"
			::= { extremeWingCfgProfVrrpGroupEntry 12 }

		
		-- 1.3.6.1.4.1.1916.2.131.50.1.3.16.21.2.1.13
		extremeWingCfgProfVrrpGroupInterface OBJECT-TYPE
			SYNTAX Unsigned32 (1..4094)
			MAX-ACCESS read-write
			STATUS current
			DESCRIPTION
				"The SVI (VLAN only) interface on which VRRP will be running. This also enable/disable VRRP operations
				
				XPath: /extremeWing-config/profile[name=key1]/vrrp_groups[virtual_router_id=key2]/interface"
			::= { extremeWingCfgProfVrrpGroupEntry 13 }

		
		-- 1.3.6.1.4.1.1916.2.131.50.1.3.16.21.2.1.14
		extremeWingCfgProfVrrpGroupSyncGroup OBJECT-TYPE
			SYNTAX TruthValue
			MAX-ACCESS read-write
			STATUS current
			DESCRIPTION
				"Make this group part of vrrp sync group. This triggers VRRP failover only when advertisement is not received from all the masters of the virtual routers that is part of this vrrp sync group
				
				XPath: /extremeWing-config/profile[name=key1]/vrrp_groups[virtual_router_id=key2]/sync_group"
			DEFVAL { false }
			::= { extremeWingCfgProfVrrpGroupEntry 14 }

		
		-- 1.3.6.1.4.1.1916.2.131.50.1.3.16.22
		extremeWingCfgProfIgs OBJECT IDENTIFIER ::= { extremeWingCfgProf 22 }

		
		-- 1.3.6.1.4.1.1916.2.131.50.1.3.16.22.1
		extremeWingCfgProfIgsTable OBJECT-TYPE
			SYNTAX SEQUENCE OF ExtremeWingCfgProfIgsEntry
			MAX-ACCESS not-accessible
			STATUS current
			DESCRIPTION
				"
				
				/extremeWing-config/profile"
			::= { extremeWingCfgProfIgs 1 }

		
		-- 1.3.6.1.4.1.1916.2.131.50.1.3.16.22.1.1
		extremeWingCfgProfIgsEntry OBJECT-TYPE
			SYNTAX ExtremeWingCfgProfIgsEntry
			MAX-ACCESS not-accessible
			STATUS current
			DESCRIPTION
				"An entry in the table."
			INDEX { extremeWingCfgProfName }
			::= { extremeWingCfgProfIgsTable 1 }

		
		ExtremeWingCfgProfIgsEntry ::=
			SEQUENCE { 
				extremeWingCfgProfIgsIpIgmpSnooping
					TruthValue,
				extremeWingCfgProfIgsIpIgmpSnoopingForwardUnknownMulticast
					TruthValue,
				extremeWingCfgProfIgsIpIgmpSnoopingQuerier
					TruthValue,
				extremeWingCfgProfIgsIpIgmpSnoopingQuerierAddress
					IpAddress,
				extremeWingCfgProfIgsIpIgmpSnoopingQuerierMaxResponseTime
					Unsigned32,
				extremeWingCfgProfIgsIpIgmpSnoopingQuerierOtherQuerierTimerExpiry
					Unsigned32,
				extremeWingCfgProfIgsIpIgmpSnoopingQuerierVersion
					Unsigned32,
				extremeWingCfgProfIgsIpIgmpSnoopingQuerierQueryInterval
					Unsigned32,
				extremeWingCfgProfIgsIpIgmpSnoopingQuerierRobustnessVariable
					Unsigned32
			 }

		-- 1.3.6.1.4.1.1916.2.131.50.1.3.16.22.1.1.1
		extremeWingCfgProfIgsIpIgmpSnooping OBJECT-TYPE
			SYNTAX TruthValue
			MAX-ACCESS read-write
			STATUS current
			DESCRIPTION
				"Enable/Disable igmp snooping; if set to disable, then per vlan bridge configuration is ignored
				
				XPath: /extremeWing-config/profile[name=key1]/ip_igmp_snooping"
			DEFVAL { true }
			::= { extremeWingCfgProfIgsEntry 1 }

		
		-- 1.3.6.1.4.1.1916.2.131.50.1.3.16.22.1.1.2
		extremeWingCfgProfIgsIpIgmpSnoopingForwardUnknownMulticast OBJECT-TYPE
			SYNTAX TruthValue
			MAX-ACCESS read-write
			STATUS current
			DESCRIPTION
				"Enable/Disable unknown multicast fowarding
				
				XPath: /extremeWing-config/profile[name=key1]/ip_igmp_snooping_forward_unknown_multicast"
			DEFVAL { false }
			::= { extremeWingCfgProfIgsEntry 2 }

		
		-- 1.3.6.1.4.1.1916.2.131.50.1.3.16.22.1.1.3
		extremeWingCfgProfIgsIpIgmpSnoopingQuerier OBJECT-TYPE
			SYNTAX TruthValue
			MAX-ACCESS read-write
			STATUS current
			DESCRIPTION
				"Enable/Disable on board IGMP querier on the device
				
				XPath: /extremeWing-config/profile[name=key1]/ip_igmp_snooping_querier"
			DEFVAL { false }
			::= { extremeWingCfgProfIgsEntry 3 }

		
		-- 1.3.6.1.4.1.1916.2.131.50.1.3.16.22.1.1.4
		extremeWingCfgProfIgsIpIgmpSnoopingQuerierAddress OBJECT-TYPE
			SYNTAX IpAddress 
			MAX-ACCESS read-write
			STATUS current
			DESCRIPTION
				"IP Address used by IGMP querier
				
				XPath: /extremeWing-config/profile[name=key1]/ip_igmp_snooping_querier_address"
			DEFVAL { '00000000'h }
			::= { extremeWingCfgProfIgsEntry 4 }

		
		-- 1.3.6.1.4.1.1916.2.131.50.1.3.16.22.1.1.5
		extremeWingCfgProfIgsIpIgmpSnoopingQuerierMaxResponseTime OBJECT-TYPE
			SYNTAX Unsigned32 (1..25)
			UNITS "seconds"
			MAX-ACCESS read-write
			STATUS current
			DESCRIPTION
				"Maximum query response time
				
				XPath: /extremeWing-config/profile[name=key1]/ip_igmp_snooping_querier_max_response_time"
			DEFVAL { 10 }
			::= { extremeWingCfgProfIgsEntry 5 }

		
		-- 1.3.6.1.4.1.1916.2.131.50.1.3.16.22.1.1.6
		extremeWingCfgProfIgsIpIgmpSnoopingQuerierOtherQuerierTimerExpiry OBJECT-TYPE
			SYNTAX Unsigned32 (60..300)
			UNITS "seconds"
			MAX-ACCESS read-write
			STATUS current
			DESCRIPTION
				"other querier time out value for the IGMP Querier
				
				XPath: /extremeWing-config/profile[name=key1]/ip_igmp_snooping_querier_other_querier_timer_expiry"
			DEFVAL { 60 }
			::= { extremeWingCfgProfIgsEntry 6 }

		
		-- 1.3.6.1.4.1.1916.2.131.50.1.3.16.22.1.1.7
		extremeWingCfgProfIgsIpIgmpSnoopingQuerierVersion OBJECT-TYPE
			SYNTAX Unsigned32 (1..3)
			MAX-ACCESS read-write
			STATUS current
			DESCRIPTION
				"IGMP version for the querier
				
				XPath: /extremeWing-config/profile[name=key1]/ip_igmp_snooping_querier_version"
			DEFVAL { 3 }
			::= { extremeWingCfgProfIgsEntry 7 }

		
		-- 1.3.6.1.4.1.1916.2.131.50.1.3.16.22.1.1.8
		extremeWingCfgProfIgsIpIgmpSnoopingQuerierQueryInterval OBJECT-TYPE
			SYNTAX Unsigned32 (1..18000)
			UNITS "seconds"
			MAX-ACCESS read-write
			STATUS current
			DESCRIPTION
				"
				
				XPath: /extremeWing-config/profile[name=key1]/ip_igmp_snooping_querier_query_interval"
			DEFVAL { 60 }
			::= { extremeWingCfgProfIgsEntry 8 }

		
		-- 1.3.6.1.4.1.1916.2.131.50.1.3.16.22.1.1.9
		extremeWingCfgProfIgsIpIgmpSnoopingQuerierRobustnessVariable OBJECT-TYPE
			SYNTAX Unsigned32 (1..7)
			MAX-ACCESS read-write
			STATUS current
			DESCRIPTION
				"
				
				XPath: /extremeWing-config/profile[name=key1]/ip_igmp_snooping_querier_robustness_variable"
			DEFVAL { 2 }
			::= { extremeWingCfgProfIgsEntry 9 }

		
-- /extremeWing-config/profile/critical_resources
		-- 1.3.6.1.4.1.1916.2.131.50.1.3.16.23
		extremeWingCfgProfCriticalRes OBJECT IDENTIFIER ::= { extremeWingCfgProf 23 }

		
		-- 1.3.6.1.4.1.1916.2.131.50.1.3.16.23.1
		extremeWingCfgProfCriticalResMonitorTable OBJECT-TYPE
			SYNTAX SEQUENCE OF ExtremeWingCfgProfCriticalResMonitorEntry
			MAX-ACCESS not-accessible
			STATUS current
			DESCRIPTION
				"
				
				/extremeWing-config/profile"
			::= { extremeWingCfgProfCriticalRes 1 }

		
		-- 1.3.6.1.4.1.1916.2.131.50.1.3.16.23.1.1
		extremeWingCfgProfCriticalResMonitorEntry OBJECT-TYPE
			SYNTAX ExtremeWingCfgProfCriticalResMonitorEntry
			MAX-ACCESS not-accessible
			STATUS current
			DESCRIPTION
				"An entry in the table."
			INDEX { extremeWingCfgProfName }
			::= { extremeWingCfgProfCriticalResMonitorTable 1 }

		
		ExtremeWingCfgProfCriticalResMonitorEntry ::=
			SEQUENCE { 
				extremeWingCfgProfCriticalResMonitorInt
					Unsigned32
			 }

		-- 1.3.6.1.4.1.1916.2.131.50.1.3.16.23.1.1.1
		extremeWingCfgProfCriticalResMonitorInt OBJECT-TYPE
			SYNTAX Unsigned32 (5..86400)
			UNITS "seconds"
			MAX-ACCESS read-write
			STATUS current
			DESCRIPTION
				"Monitoring frequency
				
				XPath: /extremeWing-config/profile[name=key1]/crm_monitor_interval"
			DEFVAL { 30 }
			::= { extremeWingCfgProfCriticalResMonitorEntry 1 }

		
		-- 1.3.6.1.4.1.1916.2.131.50.1.3.16.23.2
		extremeWingCfgProfCriticalResPolicyTable OBJECT-TYPE
			SYNTAX SEQUENCE OF ExtremeWingCfgProfCriticalResPolicyEntry
			MAX-ACCESS not-accessible
			STATUS current
			DESCRIPTION
				"
				
				/extremeWing-config/profile/critical_resources"
			::= { extremeWingCfgProfCriticalRes 2 }

		
		-- 1.3.6.1.4.1.1916.2.131.50.1.3.16.23.2.1
		extremeWingCfgProfCriticalResPolicyEntry OBJECT-TYPE
			SYNTAX ExtremeWingCfgProfCriticalResPolicyEntry
			MAX-ACCESS not-accessible
			STATUS current
			DESCRIPTION
				"An entry in the table."
			INDEX { extremeWingCfgProfName, extremeWingCfgProfCriticalResPolicyVia }
			::= { extremeWingCfgProfCriticalResPolicyTable 1 }

		
		ExtremeWingCfgProfCriticalResPolicyEntry ::=
			SEQUENCE { 
				extremeWingCfgProfCriticalResPolicyVia
					ExtremeWingIdentifier,
				extremeWingCfgProfCriticalResPolicyAnyAll
					DisplayString
			 }

		-- 1.3.6.1.4.1.1916.2.131.50.1.3.16.23.2.1.1
		extremeWingCfgProfCriticalResPolicyVia OBJECT-TYPE
			SYNTAX ExtremeWingIdentifier
			MAX-ACCESS read-only
			STATUS current
			DESCRIPTION
				"
				
				XPath: /extremeWing-config/profile[name=key1]/critical_resources[via=key2]/via"
			::= { extremeWingCfgProfCriticalResPolicyEntry 1 }

		
		-- 1.3.6.1.4.1.1916.2.131.50.1.3.16.23.2.1.3
		extremeWingCfgProfCriticalResPolicyAnyAll OBJECT-TYPE
			SYNTAX DisplayString
			MAX-ACCESS read-write
			STATUS current
			DESCRIPTION
				"
				
				Values:
				any,
				all
				
				XPath: /extremeWing-config/profile[name=key1]/critical_resources[via=key2]/any_all"
			DEFVAL { "any" }
			::= { extremeWingCfgProfCriticalResPolicyEntry 3 }

		
		-- 1.3.6.1.4.1.1916.2.131.50.1.3.16.23.3
		extremeWingCfgProfCriticalResourcesTable OBJECT-TYPE
			SYNTAX SEQUENCE OF ExtremeWingCfgProfCriticalResourcesEntry
			MAX-ACCESS not-accessible
			STATUS current
			DESCRIPTION
				"
				
				/extremeWing-config/profile/critical_resources/resources"
			::= { extremeWingCfgProfCriticalRes 3 }

		
		-- 1.3.6.1.4.1.1916.2.131.50.1.3.16.23.3.1
		extremeWingCfgProfCriticalResourcesEntry OBJECT-TYPE
			SYNTAX ExtremeWingCfgProfCriticalResourcesEntry
			MAX-ACCESS not-accessible
			STATUS current
			DESCRIPTION
				"An entry in the table."
			INDEX { extremeWingCfgProfName, extremeWingCfgProfCriticalResPolicyVia, extremeWingCfgProfCriticalResourcesAddr }
			::= { extremeWingCfgProfCriticalResourcesTable 1 }

		
		ExtremeWingCfgProfCriticalResourcesEntry ::=
			SEQUENCE { 
				extremeWingCfgProfCriticalResourcesAddr
					ExtremeWingIdentifier,
				extremeWingCfgProfCriticalResourcesMonitorType
					DisplayString,
				extremeWingCfgProfCriticalResourcesVlan
					Unsigned32,
				extremeWingCfgProfCriticalResourcesPort
					DisplayString
			 }

		-- 1.3.6.1.4.1.1916.2.131.50.1.3.16.23.3.1.1
		extremeWingCfgProfCriticalResourcesAddr OBJECT-TYPE
			SYNTAX ExtremeWingIdentifier
			MAX-ACCESS read-only
			STATUS current
			DESCRIPTION
				"
				
				XPath: /extremeWing-config/profile[name=key1]/critical_resources[via=key2]/resources[address=key3]/address"
			::= { extremeWingCfgProfCriticalResourcesEntry 1 }

		
		-- 1.3.6.1.4.1.1916.2.131.50.1.3.16.23.3.1.3
		extremeWingCfgProfCriticalResourcesMonitorType OBJECT-TYPE
			SYNTAX DisplayString
			MAX-ACCESS read-write
			STATUS current
			DESCRIPTION
				"
				
				Values:
				arp-only,
				arp-and-ping
				
				XPath: /extremeWing-config/profile[name=key1]/critical_resources[via=key2]/resources[address=key3]/monitor_type"
			DEFVAL { "arp-and-ping" }
			::= { extremeWingCfgProfCriticalResourcesEntry 3 }

		
		-- 1.3.6.1.4.1.1916.2.131.50.1.3.16.23.3.1.4
		extremeWingCfgProfCriticalResourcesVlan OBJECT-TYPE
			SYNTAX Unsigned32 (1..4094)
			MAX-ACCESS read-write
			STATUS current
			DESCRIPTION
				"
				
				XPath: /extremeWing-config/profile[name=key1]/critical_resources[via=key2]/resources[address=key3]/vlan"
			::= { extremeWingCfgProfCriticalResourcesEntry 4 }

		
		-- 1.3.6.1.4.1.1916.2.131.50.1.3.16.23.3.1.5
		extremeWingCfgProfCriticalResourcesPort OBJECT-TYPE
			SYNTAX DisplayString
			MAX-ACCESS read-write
			STATUS current
			DESCRIPTION
				"
				
				Values:
				ge1, ge2, ge3, ge4, ge5, ge6, ge7, ge8, xge1, xge2, fe1, fe2, fe3, fe4, me1, up1
				
				XPath: /extremeWing-config/profile[name=key1]/critical_resources[via=key2]/resources[address=key3]/port"
			::= { extremeWingCfgProfCriticalResourcesEntry 5 }

		
-- /extremeWing-config/profile/l2tpv3
		-- 1.3.6.1.4.1.1916.2.131.50.1.3.16.24
		extremeWingCfgProfl2tpv3 OBJECT IDENTIFIER ::= { extremeWingCfgProf 24 }

		
-- /extremeWing-config/profile/l2tpv3
		-- 1.3.6.1.4.1.1916.2.131.50.1.3.16.24.1
		extremeWingCfgProfl2tpv3Table OBJECT-TYPE
			SYNTAX SEQUENCE OF ExtremeWingCfgProfl2tpv3Entry
			MAX-ACCESS not-accessible
			STATUS current
			DESCRIPTION
				"/extremeWing-config/profile/l2tpv3"
			::= { extremeWingCfgProfl2tpv3 1 }

		
		-- 1.3.6.1.4.1.1916.2.131.50.1.3.16.24.1.1
		extremeWingCfgProfl2tpv3Entry OBJECT-TYPE
			SYNTAX ExtremeWingCfgProfl2tpv3Entry
			MAX-ACCESS not-accessible
			STATUS current
			DESCRIPTION
				"An entry in the table."
			INDEX { extremeWingCfgProfName }
			::= { extremeWingCfgProfl2tpv3Table 1 }

		
		ExtremeWingCfgProfl2tpv3Entry ::=
			SEQUENCE { 
				extremeWingCfgProfl2tpv3lUdpListenPort
					Unsigned32,
				extremeWingCfgProfl2tpv3RouterId
					DisplayString,
				extremeWingCfgProfl2tpv3HostName
					DisplayString,
				extremeWingCfgProfl2tpv3InterTunnelBridging
					TruthValue
			 }

		-- 1.3.6.1.4.1.1916.2.131.50.1.3.16.24.1.1.1
		extremeWingCfgProfl2tpv3lUdpListenPort OBJECT-TYPE
			SYNTAX Unsigned32
			MAX-ACCESS read-write
			STATUS current
			DESCRIPTION
				"The UDP port on which incoming requests are listened.
				
				XPath: /extremeWing-config/profile[name=key1]/l2tpv3_udp_listen_port"
			::= { extremeWingCfgProfl2tpv3Entry 1 }

		
		-- 1.3.6.1.4.1.1916.2.131.50.1.3.16.24.1.1.2
		extremeWingCfgProfl2tpv3RouterId OBJECT-TYPE
			SYNTAX DisplayString
			MAX-ACCESS read-write
			STATUS current
			DESCRIPTION
				"Router Id used in AVP message for the tunnel.
				
				XPath: /extremeWing-config/profile[name=key1]/l2tpv3_router_id"
			::= { extremeWingCfgProfl2tpv3Entry 2 }

		
		-- 1.3.6.1.4.1.1916.2.131.50.1.3.16.24.1.1.3
		extremeWingCfgProfl2tpv3HostName OBJECT-TYPE
			SYNTAX DisplayString
			MAX-ACCESS read-write
			STATUS current
			DESCRIPTION
				"Host name sent in AVP message for the tunnel.
				
				XPath: /extremeWing-config/profile[name=key1]/l2tpv3_host_name"
			::= { extremeWingCfgProfl2tpv3Entry 3 }

		
		-- 1.3.6.1.4.1.1916.2.131.50.1.3.16.24.1.1.4
		extremeWingCfgProfl2tpv3InterTunnelBridging OBJECT-TYPE
			SYNTAX TruthValue
			MAX-ACCESS read-write
			STATUS current
			DESCRIPTION
				"Enable/Disable Bridge packets between tunnels.
				
				XPath: /extremeWing-config/profile[name=key1]/l2tpv3_inter_tunnel_bridging"
			::= { extremeWingCfgProfl2tpv3Entry 4 }

		
-- /extremeWing-config/profile/l2tpv3_tunnel
		-- 1.3.6.1.4.1.1916.2.131.50.1.3.16.24.2
		extremeWingCfgProfl2tpv3TunnelTable OBJECT-TYPE
			SYNTAX SEQUENCE OF ExtremeWingCfgProfl2tpv3TunnelEntry
			MAX-ACCESS not-accessible
			STATUS current
			DESCRIPTION
				"/extremeWing-config/profile/l2tpv3_tunnel"
			::= { extremeWingCfgProfl2tpv3 2 }

		
		-- 1.3.6.1.4.1.1916.2.131.50.1.3.16.24.2.1
		extremeWingCfgProfl2tpv3TunnelEntry OBJECT-TYPE
			SYNTAX ExtremeWingCfgProfl2tpv3TunnelEntry
			MAX-ACCESS not-accessible
			STATUS current
			DESCRIPTION
				"An entry in the table."
			INDEX { extremeWingCfgProfName, extremeWingCfgProfl2tpv3TunnelName }
			::= { extremeWingCfgProfl2tpv3TunnelTable 1 }

		
		ExtremeWingCfgProfl2tpv3TunnelEntry ::=
			SEQUENCE { 
				extremeWingCfgProfl2tpv3TunnelName
					ExtremeWingIdentifier,
				extremeWingCfgProfl2tpv3TunnelLocalIpAddrss
					IpAddress,
				extremeWingCfgProfl2tpv3TunnelMtu
					Unsigned32,
				extremeWingCfgProfl2tpv3TunnelUseTunnelPolicy
					DisplayString,
				extremeWingCfgProfl2tpv3TunnelHostname
					DisplayString,
				extremeWingCfgProfl2tpv3TunnelRouterId
					DisplayString
			 }

		-- 1.3.6.1.4.1.1916.2.131.50.1.3.16.24.2.1.1
		extremeWingCfgProfl2tpv3TunnelName OBJECT-TYPE
			SYNTAX ExtremeWingIdentifier
			MAX-ACCESS read-only
			STATUS current
			DESCRIPTION
				"tunnel name.
				
				XPath: /extremeWing-config/profile[name=key1]/l2tpv3_tunnel[name=key2]/name"
			::= { extremeWingCfgProfl2tpv3TunnelEntry 1 }

		
		-- 1.3.6.1.4.1.1916.2.131.50.1.3.16.24.2.1.3
		extremeWingCfgProfl2tpv3TunnelLocalIpAddrss OBJECT-TYPE
			SYNTAX IpAddress
			MAX-ACCESS read-write
			STATUS current
			DESCRIPTION
				"Use this IP as local tunnel endpoint address, instead of the interface IP.
				
				XPath: /extremeWing-config/profile[name=key1]/l2tpv3_tunnel[name=key2]/local_ip_address"
			::= { extremeWingCfgProfl2tpv3TunnelEntry 3 }

		
		-- 1.3.6.1.4.1.1916.2.131.50.1.3.16.24.2.1.4
		extremeWingCfgProfl2tpv3TunnelMtu OBJECT-TYPE
			SYNTAX Unsigned32
			MAX-ACCESS read-write
			STATUS current
			DESCRIPTION
				"MTU for the tunnel.
				
				XPath: /extremeWing-config/profile[name=key1]/l2tpv3_tunnel[name=key2]/mtu"
			::= { extremeWingCfgProfl2tpv3TunnelEntry 4 }

		
		-- 1.3.6.1.4.1.1916.2.131.50.1.3.16.24.2.1.5
		extremeWingCfgProfl2tpv3TunnelUseTunnelPolicy OBJECT-TYPE
			SYNTAX DisplayString
			MAX-ACCESS read-write
			STATUS current
			DESCRIPTION
				"Policy used for the tunnel.
				
				XPath: /extremeWing-config/profile[name=key1]/l2tpv3_tunnel[name=key2]/use_tunnel_policy"
			::= { extremeWingCfgProfl2tpv3TunnelEntry 5 }

		
		-- 1.3.6.1.4.1.1916.2.131.50.1.3.16.24.2.1.6
		extremeWingCfgProfl2tpv3TunnelHostname OBJECT-TYPE
			SYNTAX DisplayString
			MAX-ACCESS read-write
			STATUS current
			DESCRIPTION
				"Tunnel specific hostname.
				
				XPath: /extremeWing-config/profile[name=key1]/l2tpv3_tunnel[name=key2]/tunnel_hostname"
			::= { extremeWingCfgProfl2tpv3TunnelEntry 6 }

		
		-- 1.3.6.1.4.1.1916.2.131.50.1.3.16.24.2.1.7
		extremeWingCfgProfl2tpv3TunnelRouterId OBJECT-TYPE
			SYNTAX DisplayString
			MAX-ACCESS read-write
			STATUS current
			DESCRIPTION
				"Local router-id
				
				XPath: /extremeWing-config/profile[name=key1]/l2tpv3_tunnel[name=key2]/tunnel_router_id"
			::= { extremeWingCfgProfl2tpv3TunnelEntry 7 }

		
-- /extremeWing-config/profile/l2tpv3_tunnel/peer
		-- 1.3.6.1.4.1.1916.2.131.50.1.3.16.24.3
		extremeWingCfgProfl2tpv3TunnelPeerTable OBJECT-TYPE
			SYNTAX SEQUENCE OF ExtremeWingCfgProfl2tpv3TunnelPeerEntry
			MAX-ACCESS not-accessible
			STATUS current
			DESCRIPTION
				"/extremeWing-config/profile/l2tpv3_tunnel/peer"
			::= { extremeWingCfgProfl2tpv3 3 }

		
		-- 1.3.6.1.4.1.1916.2.131.50.1.3.16.24.3.1
		extremeWingCfgProfl2tpv3TunnelPeerEntry OBJECT-TYPE
			SYNTAX ExtremeWingCfgProfl2tpv3TunnelPeerEntry
			MAX-ACCESS not-accessible
			STATUS current
			DESCRIPTION
				"An entry in the table."
			INDEX { extremeWingCfgProfName, extremeWingCfgProfl2tpv3TunnelName, extremeWingCfgProfl2tpv3TunnelPeerId }
			::= { extremeWingCfgProfl2tpv3TunnelPeerTable 1 }

		
		ExtremeWingCfgProfl2tpv3TunnelPeerEntry ::=
			SEQUENCE { 
				extremeWingCfgProfl2tpv3TunnelPeerId
					Unsigned32,
				extremeWingCfgProfl2tpv3TunnelPeerIp
					IpAddress,
				extremeWingCfgProfl2tpv3TunnelPeerHostName
					DisplayString,
				extremeWingCfgProfl2tpv3TunnelPeerRouterId
					DisplayString,
				extremeWingCfgProfl2tpv3TunnelPeerEncapsulation
					DisplayString,
				extremeWingCfgProfl2tpv3TunnelPeerUDPPort
					Unsigned32
			 }

		-- 1.3.6.1.4.1.1916.2.131.50.1.3.16.24.3.1.1
		extremeWingCfgProfl2tpv3TunnelPeerId OBJECT-TYPE
			SYNTAX Unsigned32 (1..2)
			MAX-ACCESS read-only
			STATUS current
			DESCRIPTION
				"Primary peer to establish the tunnel and secondary peer for failover.
				
				XPath: /extremeWing-config/profile[name=key1]/l2tpv3_tunnel[name=key2]/peer[peer_id=key3]/peer_id"
			::= { extremeWingCfgProfl2tpv3TunnelPeerEntry 1 }

		
		-- 1.3.6.1.4.1.1916.2.131.50.1.3.16.24.3.1.3
		extremeWingCfgProfl2tpv3TunnelPeerIp OBJECT-TYPE
			SYNTAX IpAddress
			MAX-ACCESS read-write
			STATUS current
			DESCRIPTION
				"Peer IP value.
				
				XPath: /extremeWing-config/profile[name=key1]/l2tpv3_tunnel[name=key2]/peer[peer_id=key3]/ip"
			::= { extremeWingCfgProfl2tpv3TunnelPeerEntry 3 }

		
		-- 1.3.6.1.4.1.1916.2.131.50.1.3.16.24.3.1.4
		extremeWingCfgProfl2tpv3TunnelPeerHostName OBJECT-TYPE
			SYNTAX DisplayString
			MAX-ACCESS read-write
			STATUS current
			DESCRIPTION
				"Peer hostname.
				
				XPath: /extremeWing-config/profile[name=key1]/l2tpv3_tunnel[name=key2]/peer[peer_id=key3]/hostname"
			::= { extremeWingCfgProfl2tpv3TunnelPeerEntry 4 }

		
		-- 1.3.6.1.4.1.1916.2.131.50.1.3.16.24.3.1.5
		extremeWingCfgProfl2tpv3TunnelPeerRouterId OBJECT-TYPE
			SYNTAX DisplayString
			MAX-ACCESS read-write
			STATUS current
			DESCRIPTION
				"Peer router-id.
				
				XPath: /extremeWing-config/profile[name=key1]/l2tpv3_tunnel[name=key2]/peer[peer_id=key3]/router_id"
			::= { extremeWingCfgProfl2tpv3TunnelPeerEntry 5 }

		
		-- 1.3.6.1.4.1.1916.2.131.50.1.3.16.24.3.1.6
		extremeWingCfgProfl2tpv3TunnelPeerEncapsulation OBJECT-TYPE
			SYNTAX DisplayString
			MAX-ACCESS read-write
			STATUS current
			DESCRIPTION
				"Peer encapsulation protocol.
				
				XPath: /extremeWing-config/profile[name=key1]/l2tpv3_tunnel[name=key2]/peer[peer_id=key3]/encapsulation"
			::= { extremeWingCfgProfl2tpv3TunnelPeerEntry 6 }

		
		-- 1.3.6.1.4.1.1916.2.131.50.1.3.16.24.3.1.7
		extremeWingCfgProfl2tpv3TunnelPeerUDPPort OBJECT-TYPE
			SYNTAX Unsigned32
			MAX-ACCESS read-write
			STATUS current
			DESCRIPTION
				"Peer UDP encapsualtion port.
				
				XPath: /extremeWing-config/profile[name=key1]/l2tpv3_tunnel[name=key2]/peer[peer_id=key3]/udpport"
			::= { extremeWingCfgProfl2tpv3TunnelPeerEntry 7 }

		
-- /extremeWing-config/profile/l2tpv3_tunnel/session
		-- 1.3.6.1.4.1.1916.2.131.50.1.3.16.24.4
		extremeWingCfgProfl2tpv3TunnelSessionTable OBJECT-TYPE
			SYNTAX SEQUENCE OF ExtremeWingCfgProfl2tpv3TunnelSessionEntry
			MAX-ACCESS not-accessible
			STATUS current
			DESCRIPTION
				"/extremeWing-config/profile/l2tpv3_tunnel/session"
			::= { extremeWingCfgProfl2tpv3 4 }

		
		-- 1.3.6.1.4.1.1916.2.131.50.1.3.16.24.4.1
		extremeWingCfgProfl2tpv3TunnelSessionEntry OBJECT-TYPE
			SYNTAX ExtremeWingCfgProfl2tpv3TunnelSessionEntry
			MAX-ACCESS not-accessible
			STATUS current
			DESCRIPTION
				"An entry in the table."
			INDEX { extremeWingCfgProfName, extremeWingCfgProfl2tpv3TunnelName, extremeWingCfgProfl2tpv3TunnelSessionName }
			::= { extremeWingCfgProfl2tpv3TunnelSessionTable 1 }

		
		ExtremeWingCfgProfl2tpv3TunnelSessionEntry ::=
			SEQUENCE { 
				extremeWingCfgProfl2tpv3TunnelSessionName
					ExtremeWingIdentifier,
				extremeWingCfgProfl2tpv3TunnelSessionPseudoWireId
					Unsigned32,
				extremeWingCfgProfl2tpv3TunnelSessionTrafficSourceType
					DisplayString,
				extremeWingCfgProfl2tpv3TunnelSessionTrafficSourceValue
					Unsigned32,
				extremeWingCfgProfl2tpv3TunnelSessionNativeVlan
					DisplayString
			 }

		-- 1.3.6.1.4.1.1916.2.131.50.1.3.16.24.4.1.1
		extremeWingCfgProfl2tpv3TunnelSessionName OBJECT-TYPE
			SYNTAX ExtremeWingIdentifier
			MAX-ACCESS read-only
			STATUS current
			DESCRIPTION
				"Name of the Session.
				
				XPath: /extremeWing-config/profile[name=key1]/l2tpv3_tunnel[name=key2]/session[name=key3]/name"
			::= { extremeWingCfgProfl2tpv3TunnelSessionEntry 1 }

		
		-- 1.3.6.1.4.1.1916.2.131.50.1.3.16.24.4.1.3
		extremeWingCfgProfl2tpv3TunnelSessionPseudoWireId OBJECT-TYPE
			SYNTAX Unsigned32
			MAX-ACCESS read-write
			STATUS current
			DESCRIPTION
				"Pseudowire Id for the Session.
				
				XPath: /extremeWing-config/profile[name=key1]/l2tpv3_tunnel[name=key2]/session[name=key3]/pseudowire_id"
			::= { extremeWingCfgProfl2tpv3TunnelSessionEntry 3 }

		
		-- 1.3.6.1.4.1.1916.2.131.50.1.3.16.24.4.1.4
		extremeWingCfgProfl2tpv3TunnelSessionTrafficSourceType OBJECT-TYPE
			SYNTAX DisplayString
			MAX-ACCESS read-write
			STATUS current
			DESCRIPTION
				"Tunneled traffic type.
				
				XPath: /extremeWing-config/profile[name=key1]/l2tpv3_tunnel[name=key2]/session[name=key3]/traffic_source_type"
			::= { extremeWingCfgProfl2tpv3TunnelSessionEntry 4 }

		
		-- 1.3.6.1.4.1.1916.2.131.50.1.3.16.24.4.1.5
		extremeWingCfgProfl2tpv3TunnelSessionTrafficSourceValue OBJECT-TYPE
			SYNTAX Unsigned32
			MAX-ACCESS read-only
			STATUS current
			DESCRIPTION
				"The range of VLAN that is tunneled.
				
				XPath: /extremeWing-config/profile[name=key1]/l2tpv3_tunnel[name=key2]/session[name=key3]/traffic_source_value"
			::= { extremeWingCfgProfl2tpv3TunnelSessionEntry 5 }

		
		-- 1.3.6.1.4.1.1916.2.131.50.1.3.16.24.4.1.6
		extremeWingCfgProfl2tpv3TunnelSessionNativeVlan OBJECT-TYPE
			SYNTAX DisplayString
			MAX-ACCESS read-write
			STATUS current
			DESCRIPTION
				"Vlan id which will not be tagged.
				
				XPath: /extremeWing-config/profile[name=key1]/l2tpv3_tunnel[name=key2]/session[name=key3]/native_vlan"
			::= { extremeWingCfgProfl2tpv3TunnelSessionEntry 6 }

		
-- /extremeWing-config/profile/l2tpv3_manual_session
		-- 1.3.6.1.4.1.1916.2.131.50.1.3.16.24.5
		extremeWingCfgProfl2tpv3ManualSessionTable OBJECT-TYPE
			SYNTAX SEQUENCE OF ExtremeWingCfgProfl2tpv3ManualSessionEntry
			MAX-ACCESS not-accessible
			STATUS current
			DESCRIPTION
				"/extremeWing-config/profile/l2tpv3_manual_session"
			::= { extremeWingCfgProfl2tpv3 5 }

		
		-- 1.3.6.1.4.1.1916.2.131.50.1.3.16.24.5.1
		extremeWingCfgProfl2tpv3ManualSessionEntry OBJECT-TYPE
			SYNTAX ExtremeWingCfgProfl2tpv3ManualSessionEntry
			MAX-ACCESS not-accessible
			STATUS current
			DESCRIPTION
				"An entry in the table."
			INDEX { extremeWingCfgProfName, extremeWingCfgProfl2tpv3ManualSessionName }
			::= { extremeWingCfgProfl2tpv3ManualSessionTable 1 }

		
		ExtremeWingCfgProfl2tpv3ManualSessionEntry ::=
			SEQUENCE { 
				extremeWingCfgProfl2tpv3ManualSessionName
					ExtremeWingIdentifier,
				extremeWingCfgProfl2tpv3ManualSessionLocalIpAddr
					IpAddress,
				extremeWingCfgProfl2tpv3ManualSessionPeerIp
					IpAddress,
				extremeWingCfgProfl2tpv3ManualSessionPeerEncapsulation
					DisplayString,
				extremeWingCfgProfl2tpv3ManualSessionPeerUDPPort
					Unsigned32,
				extremeWingCfgProfl2tpv3ManualSessionMtu
					Unsigned32,
				extremeWingCfgProfl2tpv3ManualSessionTrafficSource
					DisplayString,
				extremeWingCfgProfl2tpv3ManualSessionTrafficSourceValue
					Unsigned32,
				extremeWingCfgProfl2tpv3ManualSessionNativeVlan
					DisplayString,
				extremeWingCfgProfl2tpv3ManualSessionLocalSessionId
					Unsigned32,
				extremeWingCfgProfl2tpv3ManualSessionRemoteSessionId
					Unsigned32
			 }

		-- 1.3.6.1.4.1.1916.2.131.50.1.3.16.24.5.1.1
		extremeWingCfgProfl2tpv3ManualSessionName OBJECT-TYPE
			SYNTAX ExtremeWingIdentifier
			MAX-ACCESS read-only
			STATUS current
			DESCRIPTION
				"Name of the session.
				
				XPath: /extremeWing-config/profile[name=key1]/l2tpv3_manual_session[name=key2]/name"
			::= { extremeWingCfgProfl2tpv3ManualSessionEntry 1 }

		
		-- 1.3.6.1.4.1.1916.2.131.50.1.3.16.24.5.1.3
		extremeWingCfgProfl2tpv3ManualSessionLocalIpAddr OBJECT-TYPE
			SYNTAX IpAddress
			MAX-ACCESS read-write
			STATUS current
			DESCRIPTION
				"Use this IP as local tunnel endpoint address, instead of the interface IP.
				
				XPath: /extremeWing-config/profile[name=key1]/l2tpv3_manual_session[name=key2]/local_ip_address"
			::= { extremeWingCfgProfl2tpv3ManualSessionEntry 3 }

		
		-- 1.3.6.1.4.1.1916.2.131.50.1.3.16.24.5.1.4
		extremeWingCfgProfl2tpv3ManualSessionPeerIp OBJECT-TYPE
			SYNTAX IpAddress
			MAX-ACCESS read-write
			STATUS current
			DESCRIPTION
				"Peer IP value.
				
				XPath: /extremeWing-config/profile[name=key1]/l2tpv3_manual_session[name=key2]/peer/ip"
			::= { extremeWingCfgProfl2tpv3ManualSessionEntry 4 }

		
		-- 1.3.6.1.4.1.1916.2.131.50.1.3.16.24.5.1.5
		extremeWingCfgProfl2tpv3ManualSessionPeerEncapsulation OBJECT-TYPE
			SYNTAX DisplayString
			MAX-ACCESS read-write
			STATUS current
			DESCRIPTION
				"Peer encapsulation protocol.
				
				XPath: /extremeWing-config/profile[name=key1]/l2tpv3_manual_session[name=key2]/peer/encapsulation"
			::= { extremeWingCfgProfl2tpv3ManualSessionEntry 5 }

		
		-- 1.3.6.1.4.1.1916.2.131.50.1.3.16.24.5.1.6
		extremeWingCfgProfl2tpv3ManualSessionPeerUDPPort OBJECT-TYPE
			SYNTAX Unsigned32
			MAX-ACCESS read-write
			STATUS current
			DESCRIPTION
				"Peer UDP encapsualtion port.
				
				XPath: /extremeWing-config/profile[name=key1]/l2tpv3_manual_session[name=key2]/peer/udpport"
			::= { extremeWingCfgProfl2tpv3ManualSessionEntry 6 }

		
		-- 1.3.6.1.4.1.1916.2.131.50.1.3.16.24.5.1.7
		extremeWingCfgProfl2tpv3ManualSessionMtu OBJECT-TYPE
			SYNTAX Unsigned32
			MAX-ACCESS read-write
			STATUS current
			DESCRIPTION
				"MTU for the tunnel.
				
				XPath: /extremeWing-config/profile[name=key1]/l2tpv3_manual_session[name=key2]/mtu"
			::= { extremeWingCfgProfl2tpv3ManualSessionEntry 7 }

		
		-- 1.3.6.1.4.1.1916.2.131.50.1.3.16.24.5.1.8
		extremeWingCfgProfl2tpv3ManualSessionTrafficSource OBJECT-TYPE
			SYNTAX DisplayString
			MAX-ACCESS read-write
			STATUS current
			DESCRIPTION
				"Tunneled traffic type.
				
				XPath: /extremeWing-config/profile[name=key1]/l2tpv3_manual_session[name=key2]/traffic_source/traffic_source_type"
			::= { extremeWingCfgProfl2tpv3ManualSessionEntry 8 }

		
		-- 1.3.6.1.4.1.1916.2.131.50.1.3.16.24.5.1.9
		extremeWingCfgProfl2tpv3ManualSessionTrafficSourceValue OBJECT-TYPE
			SYNTAX Unsigned32
			MAX-ACCESS read-only
			STATUS current
			DESCRIPTION
				"The range of VLAN that is tunneled.
				
				XPath: /extremeWing-config/profile[name=key1]/l2tpv3_manual_session[name=key2]/traffic_source/traffic_source_value"
			::= { extremeWingCfgProfl2tpv3ManualSessionEntry 9 }

		
		-- 1.3.6.1.4.1.1916.2.131.50.1.3.16.24.5.1.10
		extremeWingCfgProfl2tpv3ManualSessionNativeVlan OBJECT-TYPE
			SYNTAX DisplayString
			MAX-ACCESS read-write
			STATUS current
			DESCRIPTION
				"Vlan id which will not be tagged.
				
				XPath: /extremeWing-config/profile[name=key1]/l2tpv3_manual_session[name=key2]/traffic_source/native_vlan"
			::= { extremeWingCfgProfl2tpv3ManualSessionEntry 10 }

		
		-- 1.3.6.1.4.1.1916.2.131.50.1.3.16.24.5.1.11
		extremeWingCfgProfl2tpv3ManualSessionLocalSessionId OBJECT-TYPE
			SYNTAX Unsigned32
			MAX-ACCESS read-write
			STATUS current
			DESCRIPTION
				"Local Session Id. Max limit is platform specific.
				
				XPath: /extremeWing-config/profile[name=key1]/l2tpv3_manual_session[name=key2]/local_session_id"
			::= { extremeWingCfgProfl2tpv3ManualSessionEntry 11 }

		
		-- 1.3.6.1.4.1.1916.2.131.50.1.3.16.24.5.1.12
		extremeWingCfgProfl2tpv3ManualSessionRemoteSessionId OBJECT-TYPE
			SYNTAX Unsigned32
			MAX-ACCESS read-write
			STATUS current
			DESCRIPTION
				"Remote Session Id.
				
				XPath: /extremeWing-config/profile[name=key1]/l2tpv3_manual_session[name=key2]/remote_session_id"
			::= { extremeWingCfgProfl2tpv3ManualSessionEntry 12 }

		
-- /extremeWing-config/profile/l2tpv3_manual_session/cookie
		-- 1.3.6.1.4.1.1916.2.131.50.1.3.16.24.6
		extremeWingCfgProfl2tpv3ManualSessionCookieTable OBJECT-TYPE
			SYNTAX SEQUENCE OF ExtremeWingCfgProfl2tpv3ManualSessionCookieEntry
			MAX-ACCESS not-accessible
			STATUS current
			DESCRIPTION
				"/extremeWing-config/profile/l2tpv3_manual_session/cookie"
			::= { extremeWingCfgProfl2tpv3 6 }

		
		-- 1.3.6.1.4.1.1916.2.131.50.1.3.16.24.6.1
		extremeWingCfgProfl2tpv3ManualSessionCookieEntry OBJECT-TYPE
			SYNTAX ExtremeWingCfgProfl2tpv3ManualSessionCookieEntry
			MAX-ACCESS not-accessible
			STATUS current
			DESCRIPTION
				"An entry in the table."
			INDEX { extremeWingCfgProfName, extremeWingCfgProfl2tpv3ManualSessionName, extremeWingCfgProfl2tpv3ManualSessionCookieEndpoint }
			::= { extremeWingCfgProfl2tpv3ManualSessionCookieTable 1 }

		
		ExtremeWingCfgProfl2tpv3ManualSessionCookieEntry ::=
			SEQUENCE { 
				extremeWingCfgProfl2tpv3ManualSessionCookieEndpoint
					ExtremeWingIdentifier,
				extremeWingCfgProfl2tpv3ManualSessionCookieSize
					DisplayString,
				extremeWingCfgProfl2tpv3ManualSessionCookieVal1
					DisplayString,
				extremeWingCfgProfl2tpv3ManualSessionCookieVal2
					DisplayString
			 }

		-- 1.3.6.1.4.1.1916.2.131.50.1.3.16.24.6.1.1
		extremeWingCfgProfl2tpv3ManualSessionCookieEndpoint OBJECT-TYPE
			SYNTAX ExtremeWingIdentifier
			MAX-ACCESS read-only
			STATUS current
			DESCRIPTION
				"Local or Remote endpoint.
				
				XPath: /extremeWing-config/profile[name=key1]/l2tpv3_manual_session[name=key2]/cookie[endpoint=key3]/endpoint"
			::= { extremeWingCfgProfl2tpv3ManualSessionCookieEntry 1 }

		
		-- 1.3.6.1.4.1.1916.2.131.50.1.3.16.24.6.1.3
		extremeWingCfgProfl2tpv3ManualSessionCookieSize OBJECT-TYPE
			SYNTAX DisplayString
			MAX-ACCESS read-write
			STATUS current
			DESCRIPTION
				"Cookie Size  0 or 4 or 8.
				
				XPath: /extremeWing-config/profile[name=key1]/l2tpv3_manual_session[name=key2]/cookie[endpoint=key3]/cookie_size"
			::= { extremeWingCfgProfl2tpv3ManualSessionCookieEntry 3 }

		
		-- 1.3.6.1.4.1.1916.2.131.50.1.3.16.24.6.1.4
		extremeWingCfgProfl2tpv3ManualSessionCookieVal1 OBJECT-TYPE
			SYNTAX DisplayString
			MAX-ACCESS read-write
			STATUS current
			DESCRIPTION
				"cookie value firstword.
				
				XPath: /extremeWing-config/profile[name=key1]/l2tpv3_manual_session[name=key2]/cookie[endpoint=key3]/cookie_val_1"
			::= { extremeWingCfgProfl2tpv3ManualSessionCookieEntry 4 }

		
		-- 1.3.6.1.4.1.1916.2.131.50.1.3.16.24.6.1.5
		extremeWingCfgProfl2tpv3ManualSessionCookieVal2 OBJECT-TYPE
			SYNTAX DisplayString
			MAX-ACCESS read-write
			STATUS current
			DESCRIPTION
				"cookie value secondword.
				
				XPath: /extremeWing-config/profile[name=key1]/l2tpv3_manual_session[name=key2]/cookie[endpoint=key3]/cookie_val_2"
			::= { extremeWingCfgProfl2tpv3ManualSessionCookieEntry 5 }

		
		-- 1.3.6.1.4.1.1916.2.131.50.1.3.16.25
		extremeWingCfgProfMcx OBJECT IDENTIFIER ::= { extremeWingCfgProf 25 }

		
		-- 1.3.6.1.4.1.1916.2.131.50.1.3.16.25.1
		extremeWingCfgProfMeshpointDevTable OBJECT-TYPE
			SYNTAX SEQUENCE OF ExtremeWingCfgProfMeshpointDevEntry
			MAX-ACCESS not-accessible
			STATUS current
			DESCRIPTION
				"
				
				/extremeWing-config/profile/meshpoint_device"
			::= { extremeWingCfgProfMcx 1 }

		
		-- 1.3.6.1.4.1.1916.2.131.50.1.3.16.25.1.1
		extremeWingCfgProfMeshpointDevEntry OBJECT-TYPE
			SYNTAX ExtremeWingCfgProfMeshpointDevEntry
			MAX-ACCESS not-accessible
			STATUS current
			DESCRIPTION
				"An entry in the table."
			INDEX { extremeWingCfgProfName, extremeWingCfgProfMeshpointDevName }
			::= { extremeWingCfgProfMeshpointDevTable 1 }

		
		ExtremeWingCfgProfMeshpointDevEntry ::=
			SEQUENCE { 
				extremeWingCfgProfMeshpointDevName
					ExtremeWingIdentifier,
				extremeWingCfgProfMeshpointDevIsRootDev
					DisplayString,
				extremeWingCfgProfMeshpointDevPreferredRoot
					DisplayString,
				extremeWingCfgProfMeshpointDevPreferredNeighbor
					MacAddress,
				extremeWingCfgProfMeshpointDevPreferredIf
					DisplayString,
				extremeWingCfgProfMeshpointDevPathMethod
					DisplayString,
				extremeWingCfgProfMeshpointDevMonitorCriticalResources
					TruthValue,
				extremeWingCfgProfMeshpointDevMonitorPriPortLink
					TruthValue,
				extremeWingCfgProfMeshpointDevHysteresisPeriod
					Unsigned32,
				extremeWingCfgProfMeshpointDevHysteresisSnrDelta
					Unsigned32,
				extremeWingCfgProfMeshpointDevHysteresisSnrMin
					Integer32,
				extremeWingCfgProfMeshpointDevExcludeWiredPeer
 					TruthValue,
				extremeWingCfgProfMeshpointDevHysteresisRootSelSnrDelta
					Unsigned32,
				extremeWingCfgProfMeshpointDevRootSelectMethod
					DisplayString,
				extremeWingCfgProfMeshpointDevRootSelectCostRoot
					TruthValue
			 }

		-- 1.3.6.1.4.1.1916.2.131.50.1.3.16.25.1.1.1
		extremeWingCfgProfMeshpointDevName OBJECT-TYPE
			SYNTAX ExtremeWingIdentifier
			MAX-ACCESS read-only
			STATUS current
			DESCRIPTION
				"Meshpoints that have device specific properties
				
				XPath: /extremeWing-config/profile[name=key1]/meshpoint_device[name=key2]/name"
			::= { extremeWingCfgProfMeshpointDevEntry 1 }

		
		-- 1.3.6.1.4.1.1916.2.131.50.1.3.16.25.1.1.3
		extremeWingCfgProfMeshpointDevIsRootDev OBJECT-TYPE
			SYNTAX DisplayString
			MAX-ACCESS read-write
			STATUS current
			DESCRIPTION
				"Overrides whether the meshpoint is a root or not
				
				Values:
				none,
				true,
				false
				
				XPath: /extremeWing-config/profile[name=key1]/meshpoint_device[name=key2]/is_root_dev"
			DEFVAL { "none" }
			::= { extremeWingCfgProfMeshpointDevEntry 3 }

		
		-- 1.3.6.1.4.1.1916.2.131.50.1.3.16.25.1.1.4
		extremeWingCfgProfMeshpointDevPreferredRoot OBJECT-TYPE
			SYNTAX DisplayString
			MAX-ACCESS read-write
			STATUS current
			DESCRIPTION
				"Preferred root MAC address
				
				XPath: /extremeWing-config/profile[name=key1]/meshpoint_device[name=key2]/preferred_root"
			::= { extremeWingCfgProfMeshpointDevEntry 4 }

		
		-- 1.3.6.1.4.1.1916.2.131.50.1.3.16.25.1.1.5
		extremeWingCfgProfMeshpointDevPreferredNeighbor OBJECT-TYPE
			SYNTAX MacAddress
			MAX-ACCESS read-write
			STATUS current
			DESCRIPTION
				"Preferred neighbor MAC address
				
				XPath: /extremeWing-config/profile[name=key1]/meshpoint_device[name=key2]/preferred_neighbor"
			::= { extremeWingCfgProfMeshpointDevEntry 5 }

		
		-- 1.3.6.1.4.1.1916.2.131.50.1.3.16.25.1.1.6
		extremeWingCfgProfMeshpointDevPreferredIf OBJECT-TYPE
			SYNTAX DisplayString
			MAX-ACCESS read-write
			STATUS current
			DESCRIPTION
				"Preferred interface
				
				Values:
				none,
				2.4GHz,
				5GHz
				
				XPath: /extremeWing-config/profile[name=key1]/meshpoint_device[name=key2]/preferred_interface"
			DEFVAL { "none" }
			::= { extremeWingCfgProfMeshpointDevEntry 6 }

		-- 1.3.6.1.4.1.1916.2.131.50.1.3.16.25.1.1.7
		extremeWingCfgProfMeshpointDevPathMethod OBJECT-TYPE
			SYNTAX DisplayString
			MAX-ACCESS read-write
			STATUS current
			DESCRIPTION
				"Path selection method for determining the root path
				
				Values:
				none,
				uniform,
				mobile-snr-leaf
				
				XPath: /extremeWing-config/profile[name=key1]/meshpoint_device[name=key2]/path_method"
			DEFVAL { "none" }
			::= { extremeWingCfgProfMeshpointDevEntry 7 }

		-- 1.3.6.1.4.1.1916.2.131.50.1.3.16.25.1.1.8
		extremeWingCfgProfMeshpointDevMonitorCriticalResources OBJECT-TYPE
			SYNTAX TruthValue
			MAX-ACCESS read-write
			STATUS current
			DESCRIPTION
				"
				
				XPath:/extremeWing-config/profile[name=key1]/meshpoint_device[name=key2]/monitor_critical_resources"
			DEFVAL { false }
			::= { extremeWingCfgProfMeshpointDevEntry 8 }

		-- 1.3.6.1.4.1.1916.2.131.50.1.3.16.25.1.1.9
		extremeWingCfgProfMeshpointDevMonitorPriPortLink OBJECT-TYPE
			SYNTAX TruthValue
			MAX-ACCESS read-write
			STATUS current
			DESCRIPTION
				"
				
				XPath: /extremeWing-config/profile[name=key1]/meshpoint_device[name=key2]/monitor_pri_port_link"
			DEFVAL { false }
			::= { extremeWingCfgProfMeshpointDevEntry 9 }


		-- 1.3.6.1.4.1.1916.2.131.50.1.3.16.25.1.1.10
		extremeWingCfgProfMeshpointDevHysteresisPeriod OBJECT-TYPE
			SYNTAX Unsigned32 (0..600)
			MAX-ACCESS read-write
			STATUS current
			DESCRIPTION
				"Path method hysteresis of candidate must be sustained for period of time
				XPath: /extremeWing-config/profile[name=key1]/meshpoint_device[name=key2]/hysteresis_period"
			DEFVAL { 1 }
			::= { extremeWingCfgProfMeshpointDevEntry 10 }


		-- 1.3.6.1.4.1.1916.2.131.50.1.3.16.25.1.1.11
		extremeWingCfgProfMeshpointDevHysteresisSnrDelta OBJECT-TYPE
			SYNTAX Unsigned32 (0..100)
			UNITS "db"
			MAX-ACCESS read-write
			STATUS current
			DESCRIPTION
				"Path method hysteresis SNR of candidate must have dB level better than current
				XPath: /extremeWing-config/profile[name=key1]/meshpoint_device[name=key2]/hysteresis_snr_delta
				"
			DEFVAL { 1 }
			::= { extremeWingCfgProfMeshpointDevEntry 11 }

		
		-- 1.3.6.1.4.1.1916.2.131.50.1.3.16.25.1.1.12
		extremeWingCfgProfMeshpointDevHysteresisSnrMin OBJECT-TYPE
			SYNTAX Integer32 (-100..0)
			UNITS "db"
			MAX-ACCESS read-write
			STATUS current
			DESCRIPTION
				"Path method hysteresis SNR of candidate must be above minimum threshold
				XPath: /extremeWing-config/profile[name=key1]/meshpoint_device[name=key2]/hysteresis_snr_min
				"
			DEFVAL { 0 }
			::= { extremeWingCfgProfMeshpointDevEntry 12 }

		
		-- 1.3.6.1.4.1.1916.2.131.50.1.3.16.25.1.1.13
		extremeWingCfgProfMeshpointDevExcludeWiredPeer OBJECT-TYPE
			SYNTAX TruthValue
			MAX-ACCESS read-write
			STATUS current
			DESCRIPTION
				"Excluded a mesh link from forming with a mesh device that is a wired peer
				XPath: /extremeWing-config/profile[name=key1]/meshpoint_device[name=key2]/exclude_wired_peer
				"
			DEFVAL { false }
			::= { extremeWingCfgProfMeshpointDevEntry 13 }


		-- 1.3.6.1.4.1.1916.2.131.50.1.3.16.25.1.1.14
		extremeWingCfgProfMeshpointDevHysteresisRootSelSnrDelta OBJECT-TYPE
			SYNTAX Unsigned32 (1..100)
			UNITS "db"
			MAX-ACCESS read-write
			STATUS current
			DESCRIPTION
				"Root selection method hysteresis SNR delta range that a candidate must sustain
				
				XPATH:/extremeWing-config/profile[name=key1]/meshpoint_device[name=key2]/hysteresis_root_sel_snr_delta"
			DEFVAL { 1 }
			::= { extremeWingCfgProfMeshpointDevEntry 14 }


		-- 1.3.6.1.4.1.1916.2.131.50.1.3.16.25.1.1.15
		extremeWingCfgProfMeshpointDevRootSelectMethod OBJECT-TYPE
			SYNTAX DisplayString
			MAX-ACCESS read-write
			STATUS current
			DESCRIPTION
				"Root selection method for determining whether the meshpoint is a root or non-root
				
				none
				auto-mint
				
				XPath: /extremeWing-config/profile[name=key1]/meshpoint_device[name=key2]/root_select_method"
			DEFVAL { "none" }
			::= { extremeWingCfgProfMeshpointDevEntry 15 }


		-- 1.3.6.1.4.1.1916.2.131.50.1.3.16.25.1.1.16
		extremeWingCfgProfMeshpointDevRootSelectCostRoot OBJECT-TYPE
			SYNTAX TruthValue
			MAX-ACCESS read-write
			STATUS current
			DESCRIPTION
				"Set as cost root for meshpoint root selection
				
				XPath: /extremeWing-config/profile[name=key1]/meshpoint_device[name=key2]/root_select_cost_root"
			DEFVAL { false }
			::= { extremeWingCfgProfMeshpointDevEntry 16 }



-- /extremeWing-config/profile/environmental_sensor
                -- 1.3.6.1.4.1.1916.2.131.50.1.3.16.27
                extremeWingCfgProfSensor OBJECT IDENTIFIER ::= { extremeWingCfgProf 27 }


-- /extremeWing-config/profile/envirvironmental_sensor
                -- 1.3.6.1.4.1.1916.2.131.50.1.3.16.27.1
                extremeWingCfgProfEnvSensorTable OBJECT-TYPE
                        SYNTAX SEQUENCE OF ExtremeWingCfgProfEnvSensorEntry
                        MAX-ACCESS not-accessible
                        STATUS current
                        DESCRIPTION
                                "Description."
                        ::= { extremeWingCfgProfSensor 1 }


                -- 1.3.6.1.4.1.1916.2.131.50.1.3.16.27.1.1
                extremeWingCfgProfEnvSensorEntry OBJECT-TYPE
                        SYNTAX ExtremeWingCfgProfEnvSensorEntry
                        MAX-ACCESS not-accessible
                        STATUS current
                        DESCRIPTION
                                "An entry in the table."
                        INDEX { extremeWingCfgProfName }
                        ::= { extremeWingCfgProfEnvSensorTable 1 }


                ExtremeWingCfgProfEnvSensorEntry ::=
                        SEQUENCE {
                                extremeWingCfgProfEnvSensorHumidity
                                        TruthValue,
                                extremeWingCfgProfEnvSensorMotion
                                        TruthValue,
                                extremeWingCfgProfEnvSensorTemperature
                                        TruthValue
                         }

                -- 1.3.6.1.4.1.1916.2.131.50.1.3.16.27.1.1.1
                extremeWingCfgProfEnvSensorHumidity OBJECT-TYPE
                        SYNTAX TruthValue
                        MAX-ACCESS read-write
                        STATUS current
                        DESCRIPTION
                                "Enable (turn on) the humidity sensor.

                                XPath: /extremeWing-config/profile[name=key1]/environmental_sensor/humidity"
                        DEFVAL { true }
                        ::= { extremeWingCfgProfEnvSensorEntry 1 }


                -- 1.3.6.1.4.1.1916.2.131.50.1.3.16.27.1.1.2
                extremeWingCfgProfEnvSensorMotion OBJECT-TYPE
                        SYNTAX TruthValue
                        MAX-ACCESS read-write
                        STATUS current
                        DESCRIPTION
                                "Enable (turn on) the motion sensor.

                                XPath: /extremeWing-config/profile[name=key1]/environmental_sensor/motion"
                        DEFVAL { true }
                        ::= { extremeWingCfgProfEnvSensorEntry 2 }


                -- 1.3.6.1.4.1.1916.2.131.50.1.3.16.27.1.1.3
                extremeWingCfgProfEnvSensorTemperature OBJECT-TYPE
                        SYNTAX TruthValue
                        MAX-ACCESS read-write
                        STATUS current
                        DESCRIPTION
                                "Enable (turn on) the temperature sensor.

                                XPath: /extremeWing-config/profile[name=key1]/environmental_sensor/temperature"
                        DEFVAL { true }
                        ::= { extremeWingCfgProfEnvSensorEntry 3 }


-- /extremeWing-config/profile/environmental_sensor
                -- 1.3.6.1.4.1.1916.2.131.50.1.3.16.27.2
                extremeWingCfgProfLightSensorTable OBJECT-TYPE
                        SYNTAX SEQUENCE OF ExtremeWingCfgProfLightSensorEntry
                        MAX-ACCESS not-accessible
                        STATUS current
                        DESCRIPTION
                                "Description."
                        ::= { extremeWingCfgProfSensor 2 }


                -- 1.3.6.1.4.1.1916.2.131.50.1.3.16.27.2.1
                extremeWingCfgProfLightSensorEntry OBJECT-TYPE
                        SYNTAX ExtremeWingCfgProfLightSensorEntry
                        MAX-ACCESS not-accessible
                        STATUS current
                        DESCRIPTION
                                "An entry in the table."
                        INDEX { extremeWingCfgProfName }
                        ::= { extremeWingCfgProfLightSensorTable 1 }


                ExtremeWingCfgProfLightSensorEntry ::=
                        SEQUENCE {
                                extremeWingCfgProfLightSensor
                                        TruthValue,
                                extremeWingCfgProfLightSensorHoldTime
                                        Integer32,
                                extremeWingCfgProfLightSensorThresholdRadioShutdown
                                        DisplayString,
                                extremeWingCfgProfLightSensorLowLimitThreshold
                                        Integer32,
                                extremeWingCfgProfLightSensorHighLimitThreshold
                                        Integer32
                         }

                -- 1.3.6.1.4.1.1916.2.131.50.1.3.16.27.2.1.1
                extremeWingCfgProfLightSensor OBJECT-TYPE
                        SYNTAX TruthValue
                        UNITS "true"
                        MAX-ACCESS read-write
                        STATUS current
                        DESCRIPTION
                                "Enable (turn on) the light sensor..

                                XPath: /extremeWing-config/profile[name=key1]/environmental_sensor/light"
                        ::= { extremeWingCfgProfLightSensorEntry 1 }


                -- 1.3.6.1.4.1.1916.2.131.50.1.3.16.27.2.1.2
                extremeWingCfgProfLightSensorHoldTime OBJECT-TYPE
                        SYNTAX Integer32 (2..201)
                        UNITS "seconds"
                        MAX-ACCESS read-write
                        STATUS current
                        DESCRIPTION
                                "The interval of time (in seconds) during which the light sensor polls the environment for light intensity to determine whehter the light is on or off.

                                XPath: /extremeWing-config/profile[name=key1]/environmental_sensor/light_holdtime"
                        ::= { extremeWingCfgProfLightSensorEntry 2 }


                -- 1.3.6.1.4.1.1916.2.131.50.1.3.16.27.2.1.3
                extremeWingCfgProfLightSensorThresholdRadioShutdown OBJECT-TYPE
                        SYNTAX DisplayString
                        MAX-ACCESS read-write
                        STATUS current
                        DESCRIPTION
                                "Shutdown the AP radio(s) when the light intensity drops below the lower limit -- signifying that the light is off and the facility is unoccupied..

                                enum all,
                                enum radio-1,
                                enum radio-2


                                XPath: /extremeWing-config/profile[name=key1]/environmental_sensor/light_radio_shutdown"
                        DEFVAL { "none" }
                        ::= { extremeWingCfgProfLightSensorEntry 3 }


                -- 1.3.6.1.4.1.1916.2.131.50.1.3.16.27.2.1.4
                extremeWingCfgProfLightSensorLowLimitThreshold OBJECT-TYPE
                        SYNTAX Integer32 (0..1000)
                        UNITS "lux"
                        MAX-ACCESS read-write
                        STATUS current
                        DESCRIPTION
                                "The lower limit (in lux) at which the light sensor determines the lighting is off.


                                XPath: /extremeWing-config/profile[name=key1]/environmental_sensor/light_threshold_low"
                        ::= { extremeWingCfgProfLightSensorEntry 4 }


                -- 1.3.6.1.4.1.1916.2.131.50.1.3.16.27.2.1.5
                extremeWingCfgProfLightSensorHighLimitThreshold OBJECT-TYPE
                        SYNTAX Integer32 (100..10000)
                        UNITS "lux"
                        MAX-ACCESS read-write
                        STATUS current
                        DESCRIPTION
                                "The upper limit (in lux) at which the light sensor determines the lighting is on.

                                XPath: /extremeWing-config/profile[name=key1]/environmental_sensor/light_threshold_high"
                        ::= { extremeWingCfgProfLightSensorEntry 5 }


-- /extremeWing-config/profile/environmental_sensor
                -- 1.3.6.1.4.1.1916.2.131.50.1.3.16.27.3
                extremeWingCfgProfSharedSensorConfTable OBJECT-TYPE
                        SYNTAX SEQUENCE OF ExtremeWingCfgProfSharedSensorConfEntry
                        MAX-ACCESS not-accessible
                        STATUS current
                        DESCRIPTION
                                "Description."
                        ::= { extremeWingCfgProfSensor 3 }


                -- 1.3.6.1.4.1.1916.2.131.50.1.3.16.27.3.1
                extremeWingCfgProfSharedSensorConfEntry OBJECT-TYPE
                        SYNTAX ExtremeWingCfgProfSharedSensorConfEntry
                        MAX-ACCESS not-accessible
                        STATUS current
                        DESCRIPTION
                                "An entry in the table."
                        INDEX { extremeWingCfgProfName }
                        ::= { extremeWingCfgProfSharedSensorConfTable 1 }


                ExtremeWingCfgProfSharedSensorConfEntry ::=
                        SEQUENCE {
                                extremeWingCfgProfSharedSensorPollingInterval
                                        Integer32
                         }

                -- 1.3.6.1.4.1.1916.2.131.50.1.3.16.27.3.1.1
                extremeWingCfgProfSharedSensorPollingInterval OBJECT-TYPE
                        SYNTAX Integer32 (1..100)
                        UNITS "seconds"
                        MAX-ACCESS read-write
                        STATUS current
                        DESCRIPTION
                                "The upper limit (in lux) at which the light sensor determines the lighting is on.

                                XPath: /extremeWing-config/profile[name=key1]/environmental_sensor/polling_interval"
                        ::= { extremeWingCfgProfSharedSensorConfEntry 1 }


		
-- /extremeWing-config/rf_domain
		-- 1.3.6.1.4.1.1916.2.131.50.1.3.17
		extremeWingCfgRfd OBJECT IDENTIFIER ::= { extremeWingConfig 17 }

		
		-- 1.3.6.1.4.1.1916.2.131.50.1.3.17.1
		extremeWingCfgRfdTable OBJECT-TYPE
			SYNTAX SEQUENCE OF ExtremeWingCfgRfdEntry
			MAX-ACCESS not-accessible
			STATUS current
			DESCRIPTION
				"
				
				/extremeWing-config/rf_domain"
			::= { extremeWingCfgRfd 1 }

		
		-- 1.3.6.1.4.1.1916.2.131.50.1.3.17.1.1
		extremeWingCfgRfdEntry OBJECT-TYPE
			SYNTAX ExtremeWingCfgRfdEntry
			MAX-ACCESS not-accessible
			STATUS current
			DESCRIPTION
				"An entry in the table."
			INDEX { extremeWingCfgRfdName }
			::= { extremeWingCfgRfdTable 1 }

		
		ExtremeWingCfgRfdEntry ::=
			SEQUENCE { 
				extremeWingCfgRfdName
					ExtremeWingIdentifier,
				extremeWingCfgRfdLocation
					DisplayString,
				extremeWingCfgRfdContact
					DisplayString,
				extremeWingCfgRfdTimezone
					DisplayString,
				extremeWingCfgRfdCountryCode
					DisplayString,
				extremeWingCfgRfdSmartRfPolicy
					ExtremeWingIdentifier,
				extremeWingCfgRfdWipsPolicyName
					ExtremeWingIdentifier,
				extremeWingCfgRfdNocUpdateInterval
					Unsigned32,
				extremeWingCfgRfdControlVlan
					Unsigned32,
				extremeWingCfgRfdSmartscanChanlistDynamic
					TruthValue,
				extremeWingCfgRfdStatsUpdateInterval
					Unsigned32
			 }

		-- 1.3.6.1.4.1.1916.2.131.50.1.3.17.1.1.1
		extremeWingCfgRfdName OBJECT-TYPE
			SYNTAX ExtremeWingIdentifier
			MAX-ACCESS read-only
			STATUS current
			DESCRIPTION
				"
				
				XPath: /extremeWing-config/rf_domain[name=key1]/name"
			::= { extremeWingCfgRfdEntry 1 }

		
		-- 1.3.6.1.4.1.1916.2.131.50.1.3.17.1.1.3
		extremeWingCfgRfdLocation OBJECT-TYPE
			SYNTAX DisplayString (SIZE (64))
			MAX-ACCESS read-write
			STATUS current
			DESCRIPTION
				"
				
				XPath: /extremeWing-config/rf_domain[name=key1]/location"
			::= { extremeWingCfgRfdEntry 3 }

		
		-- 1.3.6.1.4.1.1916.2.131.50.1.3.17.1.1.4
		extremeWingCfgRfdContact OBJECT-TYPE
			SYNTAX DisplayString (SIZE (64))
			MAX-ACCESS read-write
			STATUS current
			DESCRIPTION
				"
				
				XPath: /extremeWing-config/rf_domain[name=key1]/contact"
			::= { extremeWingCfgRfdEntry 4 }

		
		-- 1.3.6.1.4.1.1916.2.131.50.1.3.17.1.1.5
		extremeWingCfgRfdTimezone OBJECT-TYPE
			SYNTAX DisplayString
			MAX-ACCESS read-write
			STATUS current
			DESCRIPTION
				"
				
				Values:
				Pacific/Tongatapu
				Pacific/Fiji
				Pacific/Auckland
				Asia/Magadan
				Asia/Vladivostok
				Australia/Hobart
				Pacific/Guam
				Australia/Sydney
				Australia/Brisbane
				Australia/Adelaide
				Asia/Yakutsk
				Asia/Seoul
				Asia/Tokyo
				Australia/Perth
				Asia/Kuala_Lumpur
				Asia/Irkutsk
				Asia/Hong_Kong
				Asia/Singapore
				Asia/Chongqing
				Asia/Shanghai
				Asia/Taipei
				Asia/Krasnoyarsk
				Asia/Bangkok
				Asia/Rangoon
				Asia/Colombo
				Asia/Dhaka
				Asia/Almaty
				Asia/Katmandu
				Asia/Calcutta
				Asia/Karachi
				Asia/Yekaterinburg
				Asia/Kabul
				Asia/Baku
				Asia/Dubai
				Asia/Tehran
				Africa/Nairobi
				Europe/Moscow
				Asia/Kuwait
				Asia/Baghdad
				Asia/Jerusalem
				Europe/Istanbul
				Europe/Helsinki
				Africa/Harare
				Africa/Cairo
				Africa/Johannesburg
				Europe/Bucharest
				Europe/Athens
				EET
				Africa/Lagos
				Europe/Warsaw
				Europe/Prague
				Europe/Belgrade
				Europe/Stockholm
				Europe/Zurich
				Europe/Copenhagen
				Europe/Berlin
				Europe/Rome
				Europe/Brussels
				Europe/Paris
				Europe/Madrid
				Europe/Amsterdam
				CET
				Africa/Casablanca
				Europe/Lisbon
				Europe/London
				Europe/Dublin
				Atlantic/Reykjavik
				Atlantic/Azores
				Atlantic/Cape_Verde
				Atlantic/South_Georgia
				America/Sao_Paulo
				America/Buenos_Aires
				America/Thule
				America/St_Johns
				America/Montreal
				America/Caracas
				America/Santiago
				America/Bogota
				EST5EDT
				America/New_York
				America/Indianapolis
				America/Costa_Rica
				CST6CDT
				America/Chicago
				America/Mexico_City
				America/Winnipeg
				America/Phoenix
				America/Tegucigalpa
				MST7MDT
				America/Denver
				PST8PDT
				America/Los_Angeles
				America/Anchorage
				Pacific/Honolulu
				Pacific/Apia
				Etc/GMT+12
				Etc/GMT+11
				Etc/GMT+10
				Etc/GMT+9
				Etc/GMT+8
				Etc/GMT+7
				Etc/GMT+6
				Etc/GMT+5
				Etc/GMT+4
				Etc/GMT+3
				Etc/GMT+2
				Etc/GMT+1
				Etc/UTC
				Etc/GMT-1
				Etc/GMT-2
				Etc/GMT-3
				Etc/GMT-4
				Etc/GMT-5
				Etc/GMT-6
				Etc/GMT-7
				Etc/GMT-8
				Etc/GMT-9
				Etc/GMT-10
				Etc/GMT-11
				Etc/GMT-12
				Etc/GMT-13
				Etc/GMT-14
				
				XPath: /extremeWing-config/rf_domain[name=key1]/timezone"
			::= { extremeWingCfgRfdEntry 5 }

		
		-- 1.3.6.1.4.1.1916.2.131.50.1.3.17.1.1.6
		extremeWingCfgRfdCountryCode OBJECT-TYPE
			SYNTAX DisplayString
			MAX-ACCESS read-write
			STATUS current
			DESCRIPTION
				"
				
				Values:
				not-set
				ae
				ai
				an
				ar
				at
				au
				ba
				bb
				be
				bg
				bh
				bm
				bo
				br
				bs
				bw
				by
				ca
				ch
				cl
				cn
				co
				cr
				cx
				cy
				cz
				de
				dk
				do
				dz
				ec
				ee
				eg
				es
				fi
				fk
				fr
				gb
				gf
				gp
				gr
				gt
				gu
				gy
				hk
				hn
				hr
				ht
				hu
				id
				ie
				il
				in
				is
				it
				jm
				jo
				jp
				ke
				kr
				kw
				ky
				kz
				lb
				li
				lk
				lt
				lu
				lv
				ma
				md
				mk
				mq
				mt
				mx
				my
				mp
				me
				nf
				ng
				ni
				nl
				no
				nu
				nz
				na
				om
				pa
				pe
				ph
				pk
				pl
				pr
				pt
				py
				qa
				ro
				rs
				ru
				sa
				se
				sg
				si
				sk
				sv
				th
				tr
				tn
				tt
				tw
				ua
				us
				uy
				ve
				vg
				vi
				vn
				za
				
				XPath: /extremeWing-config/rf_domain[name=key1]/country_code"
			::= { extremeWingCfgRfdEntry 6 }

		
		-- 1.3.6.1.4.1.1916.2.131.50.1.3.17.1.1.7
		extremeWingCfgRfdSmartRfPolicy OBJECT-TYPE
			SYNTAX ExtremeWingIdentifier
			MAX-ACCESS read-write
			STATUS current
			DESCRIPTION
				"
				
				XPath: /extremeWing-config/rf_domain[name=key1]/smart_rf_policy"
			::= { extremeWingCfgRfdEntry 7 }

		
		-- 1.3.6.1.4.1.1916.2.131.50.1.3.17.1.1.8
		extremeWingCfgRfdWipsPolicyName OBJECT-TYPE
			SYNTAX ExtremeWingIdentifier
			MAX-ACCESS read-write
			STATUS current
			DESCRIPTION
				"
				
				XPath: /extremeWing-config/rf_domain[name=key1]/wips_policy_name"
			::= { extremeWingCfgRfdEntry 8 }

		
		-- 1.3.6.1.4.1.1916.2.131.50.1.3.17.1.1.9
		extremeWingCfgRfdNocUpdateInterval OBJECT-TYPE
			SYNTAX Unsigned32 (0 | 5..3600)
			UNITS "seconds"
			MAX-ACCESS read-write
			STATUS current
			DESCRIPTION
				"Statistics update interval from RF-domain manager to its
				adopting controller.  The special value of 0 is allowed
				to indicate auto mode, in which the interval is automatically
				adjusted by the controller based upon the load information.
				
				XPath: /extremeWing-config/rf_domain[name=key1]/noc_update_interval"
			DEFVAL { 0 }
			::= { extremeWingCfgRfdEntry 9 }

		
		-- 1.3.6.1.4.1.1916.2.131.50.1.3.17.1.1.10
		extremeWingCfgRfdControlVlan OBJECT-TYPE
			SYNTAX Unsigned32 (1..4094)
			MAX-ACCESS read-write
			STATUS current
			DESCRIPTION
				"VLAN for control traffic on this RF Domain
				
				XPath: /extremeWing-config/rf_domain[name=key1]/control_vlan"
			::= { extremeWingCfgRfdEntry 10 }

		
		-- 1.3.6.1.4.1.1916.2.131.50.1.3.17.1.1.11
		extremeWingCfgRfdSmartscanChanlistDynamic OBJECT-TYPE
			SYNTAX TruthValue
			MAX-ACCESS read-write
			STATUS current
			DESCRIPTION
				"Configure dynamic channel listing mode for smart-scan
				
				XPath: /extremeWing-config/rf_domain[name=key1]/smartscan_chanlist_dynamic"
			DEFVAL { false }
			::= { extremeWingCfgRfdEntry 11 }

		
		-- 1.3.6.1.4.1.1916.2.131.50.1.3.17.1.1.12
		extremeWingCfgRfdStatsUpdateInterval OBJECT-TYPE
			SYNTAX Unsigned32 (0 | 5..300)
			UNITS "seconds"
			MAX-ACCESS read-write
			STATUS current
			DESCRIPTION
				"Statistics update interval for this RF Domain.  The special value of 0 is allowed to indicate auto mode, in which the interval is automatically adjusted by the RF Domain Manager based upon the load information.
				
				XPath: /extremeWing-config/rf_domain[name=key1]/stats_update_interval"
			DEFVAL { 0 }
			::= { extremeWingCfgRfdEntry 12 }

		
		-- 1.3.6.1.4.1.1916.2.131.50.1.3.17.2
		extremeWingCfgRfdSensorSvrTable OBJECT-TYPE
			SYNTAX SEQUENCE OF ExtremeWingCfgRfdSensorSvrEntry
			MAX-ACCESS not-accessible
			STATUS current
			DESCRIPTION
				"
				
				/extremeWing-config/rf_domain/sensor_server"
			::= { extremeWingCfgRfd 2 }

		
		-- 1.3.6.1.4.1.1916.2.131.50.1.3.17.2.1
		extremeWingCfgRfdSensorSvrEntry OBJECT-TYPE
			SYNTAX ExtremeWingCfgRfdSensorSvrEntry
			MAX-ACCESS not-accessible
			STATUS current
			DESCRIPTION
				"An entry in the table."
			INDEX { extremeWingCfgRfdName, extremeWingCfgRfdSensorSvrIdx }
			::= { extremeWingCfgRfdSensorSvrTable 1 }

		
		ExtremeWingCfgRfdSensorSvrEntry ::=
			SEQUENCE { 
				extremeWingCfgRfdSensorSvrIdx
					Unsigned32,
				extremeWingCfgRfdSensorSvrIp
					DisplayString,
				extremeWingCfgRfdSensorSvrPort
					Unsigned32
			 }

		-- 1.3.6.1.4.1.1916.2.131.50.1.3.17.2.1.1
		extremeWingCfgRfdSensorSvrIdx OBJECT-TYPE
			SYNTAX Unsigned32 (1..3)
			MAX-ACCESS read-only
			STATUS current
			DESCRIPTION
				"The index into the list of servers.
				
				XPath: /extremeWing-config/rf_domain[name=key1]/sensor_server[server_idx=key2]/server_idx"
			::= { extremeWingCfgRfdSensorSvrEntry 1 }

		
		-- 1.3.6.1.4.1.1916.2.131.50.1.3.17.2.1.3
		extremeWingCfgRfdSensorSvrIp OBJECT-TYPE
			SYNTAX DisplayString
			MAX-ACCESS read-write
			STATUS current
			DESCRIPTION
				"The IP address of the sensor server.
				
				XPath: /extremeWing-config/rf_domain[name=key1]/sensor_server[server_idx=key2]/ip"
			::= { extremeWingCfgRfdSensorSvrEntry 3 }

		
		-- 1.3.6.1.4.1.1916.2.131.50.1.3.17.2.1.4
		extremeWingCfgRfdSensorSvrPort OBJECT-TYPE
			SYNTAX Unsigned32 (1..65535)
			MAX-ACCESS read-write
			STATUS current
			DESCRIPTION
				"The port number of the sensor server.
				
				XPath: /extremeWing-config/rf_domain[name=key1]/sensor_server[server_idx=key2]/port"
			DEFVAL { 443 }
			::= { extremeWingCfgRfdSensorSvrEntry 4 }

		
-- /extremeWing-config/rf_domain
		-- 1.3.6.1.4.1.1916.2.131.50.1.3.17.3
		extremeWingCfgRfdWlan OBJECT IDENTIFIER ::= { extremeWingCfgRfd 3 }

		
		-- 1.3.6.1.4.1.1916.2.131.50.1.3.17.3.1
		extremeWingCfgRfdWlanSsidOverrideTable OBJECT-TYPE
			SYNTAX SEQUENCE OF ExtremeWingCfgRfdWlanSsidOverrideEntry
			MAX-ACCESS not-accessible
			STATUS current
			DESCRIPTION
				"Override wlan ssid at the rf_domain level
				
				/extremeWing-config/rf_domain/wlan_override_ssid"
			::= { extremeWingCfgRfdWlan 1 }

		
		-- 1.3.6.1.4.1.1916.2.131.50.1.3.17.3.1.1
		extremeWingCfgRfdWlanSsidOverrideEntry OBJECT-TYPE
			SYNTAX ExtremeWingCfgRfdWlanSsidOverrideEntry
			MAX-ACCESS not-accessible
			STATUS current
			DESCRIPTION
				"An entry in the table."
			INDEX { extremeWingCfgRfdName, extremeWingCfgRfdWlanSsidOverrideWlan }
			::= { extremeWingCfgRfdWlanSsidOverrideTable 1 }

		
		ExtremeWingCfgRfdWlanSsidOverrideEntry ::=
			SEQUENCE { 
				extremeWingCfgRfdWlanSsidOverrideWlan
					ExtremeWingIdentifier,
				extremeWingCfgRfdWlanSsidOverrideSsid
					DisplayString
			 }

		-- 1.3.6.1.4.1.1916.2.131.50.1.3.17.3.1.1.1
		extremeWingCfgRfdWlanSsidOverrideWlan OBJECT-TYPE
			SYNTAX ExtremeWingIdentifier
			MAX-ACCESS read-only
			STATUS current
			DESCRIPTION
				"
				
				XPath: /extremeWing-config/rf_domain[name=key1]/wlan_override_ssid[wlan=key2]/wlan"
			::= { extremeWingCfgRfdWlanSsidOverrideEntry 1 }

		
		-- 1.3.6.1.4.1.1916.2.131.50.1.3.17.3.1.1.3
		extremeWingCfgRfdWlanSsidOverrideSsid OBJECT-TYPE
			SYNTAX DisplayString (SIZE (1..32))
			MAX-ACCESS read-write
			STATUS current
			DESCRIPTION
				"The Service Set Identifier for this WLAN.
				
				XPath: /extremeWing-config/rf_domain[name=key1]/wlan_override_ssid[wlan=key2]/ssid"
			::= { extremeWingCfgRfdWlanSsidOverrideEntry 3 }

		
		-- 1.3.6.1.4.1.1916.2.131.50.1.3.17.3.2
		extremeWingCfgRfdWlanVlanOverrideTable OBJECT-TYPE
			SYNTAX SEQUENCE OF ExtremeWingCfgRfdWlanVlanOverrideEntry
			MAX-ACCESS not-accessible
			STATUS current
			DESCRIPTION
				"Override WLAN VLANs at the RF Domain level.
				
				/extremeWing-config/rf_domain/wlan_override_vlan"
			::= { extremeWingCfgRfdWlan 2 }

		
		-- 1.3.6.1.4.1.1916.2.131.50.1.3.17.3.2.1
		extremeWingCfgRfdWlanVlanOverrideEntry OBJECT-TYPE
			SYNTAX ExtremeWingCfgRfdWlanVlanOverrideEntry
			MAX-ACCESS not-accessible
			STATUS current
			DESCRIPTION
				"An entry in the table."
			INDEX { extremeWingCfgRfdName, extremeWingCfgRfdWlanVlanOverrideWlan }
			::= { extremeWingCfgRfdWlanVlanOverrideTable 1 }

		
		ExtremeWingCfgRfdWlanVlanOverrideEntry ::=
			SEQUENCE { 
				extremeWingCfgRfdWlanVlanOverrideWlan
					ExtremeWingIdentifier
			 }

		-- 1.3.6.1.4.1.1916.2.131.50.1.3.17.3.2.1.1
		extremeWingCfgRfdWlanVlanOverrideWlan OBJECT-TYPE
			SYNTAX ExtremeWingIdentifier
			MAX-ACCESS read-only
			STATUS current
			DESCRIPTION
				"
				
				XPath: /extremeWing-config/rf_domain[name=key1]/wlan_override_vlan[wlan=key2]/wlan"
			::= { extremeWingCfgRfdWlanVlanOverrideEntry 1 }

		
		-- 1.3.6.1.4.1.1916.2.131.50.1.3.17.3.3
		extremeWingCfgRfdWlanVlanOverrideInstTable OBJECT-TYPE
			SYNTAX SEQUENCE OF ExtremeWingCfgRfdWlanVlanOverrideInstEntry
			MAX-ACCESS not-accessible
			STATUS current
			DESCRIPTION
				"
				
				/extremeWing-config/rf_domain/wlan_override_vlan/vlans"
			::= { extremeWingCfgRfdWlan 3 }

		
		-- 1.3.6.1.4.1.1916.2.131.50.1.3.17.3.3.1
		extremeWingCfgRfdWlanVlanOverrideInstEntry OBJECT-TYPE
			SYNTAX ExtremeWingCfgRfdWlanVlanOverrideInstEntry
			MAX-ACCESS not-accessible
			STATUS current
			DESCRIPTION
				"An entry in the table."
			INDEX { extremeWingCfgRfdName, extremeWingCfgRfdWlanVlanOverrideWlan, extremeWingCfgRfdWlanVlanOverrideInstVlan }
			::= { extremeWingCfgRfdWlanVlanOverrideInstTable 1 }

		
		ExtremeWingCfgRfdWlanVlanOverrideInstEntry ::=
			SEQUENCE { 
				extremeWingCfgRfdWlanVlanOverrideInstVlan
					Unsigned32,
				extremeWingCfgRfdWlanVlanOverrideInstLimit
					Unsigned32
			 }

		-- 1.3.6.1.4.1.1916.2.131.50.1.3.17.3.3.1.1
		extremeWingCfgRfdWlanVlanOverrideInstVlan OBJECT-TYPE
			SYNTAX Unsigned32 (1..4094)
			MAX-ACCESS read-only
			STATUS current
			DESCRIPTION
				"The VLAN identifier.
				
				XPath: /extremeWing-config/rf_domain[name=key1]/wlan_override_vlan[wlan=key2]/vlans[vlan=key3]/vlan"
			::= { extremeWingCfgRfdWlanVlanOverrideInstEntry 1 }

		
		-- 1.3.6.1.4.1.1916.2.131.50.1.3.17.3.3.1.3
		extremeWingCfgRfdWlanVlanOverrideInstLimit OBJECT-TYPE
			SYNTAX Unsigned32 (0..8192)
			MAX-ACCESS read-write
			STATUS current
			DESCRIPTION
				"The number of users allowed (0 implies unlimited).
				
				XPath: /extremeWing-config/rf_domain[name=key1]/wlan_override_vlan[wlan=key2]/vlans[vlan=key3]/limit"
			DEFVAL { 0 }
			::= { extremeWingCfgRfdWlanVlanOverrideInstEntry 3 }

		
		-- 1.3.6.1.4.1.1916.2.131.50.1.3.17.4
		extremeWingCfgRfdStatsWindowTable OBJECT-TYPE
			SYNTAX SEQUENCE OF ExtremeWingCfgRfdStatsWindowEntry
			MAX-ACCESS not-accessible
			STATUS current
			DESCRIPTION
				"
				
				/extremeWing-config/rf_domain/stats_window"
			::= { extremeWingCfgRfd 4 }

		
		-- 1.3.6.1.4.1.1916.2.131.50.1.3.17.4.1
		extremeWingCfgRfdStatsWindowEntry OBJECT-TYPE
			SYNTAX ExtremeWingCfgRfdStatsWindowEntry
			MAX-ACCESS not-accessible
			STATUS current
			DESCRIPTION
				"An entry in the table."
			INDEX { extremeWingCfgRfdName, extremeWingCfgRfdStatsWindowIdx }
			::= { extremeWingCfgRfdStatsWindowTable 1 }

		
		ExtremeWingCfgRfdStatsWindowEntry ::=
			SEQUENCE { 
				extremeWingCfgRfdStatsWindowIdx
					Unsigned32,
				extremeWingCfgRfdStatsWindowSampleInterval
					Unsigned32,
				extremeWingCfgRfdStatsWindowWindowSize
					Unsigned32
			 }

		-- 1.3.6.1.4.1.1916.2.131.50.1.3.17.4.1.1
		extremeWingCfgRfdStatsWindowIdx OBJECT-TYPE
			SYNTAX Unsigned32 (1..2)
			MAX-ACCESS read-only
			STATUS current
			DESCRIPTION
				"The index into the list of stats-windows
				
				XPath: /extremeWing-config/rf_domain[name=key1]/stats_window[window_idx=key2]/window_idx"
			::= { extremeWingCfgRfdStatsWindowEntry 1 }

		
		-- 1.3.6.1.4.1.1916.2.131.50.1.3.17.4.1.3
		extremeWingCfgRfdStatsWindowSampleInterval OBJECT-TYPE
			SYNTAX Unsigned32 (5..86640)
			MAX-ACCESS read-write
			STATUS current
			DESCRIPTION
				"sample interval in seconds for the window
				
				XPath: /extremeWing-config/rf_domain[name=key1]/stats_window[window_idx=key2]/sample_interval"
			DEFVAL { 5 }
			::= { extremeWingCfgRfdStatsWindowEntry 3 }

		
		-- 1.3.6.1.4.1.1916.2.131.50.1.3.17.4.1.4
		extremeWingCfgRfdStatsWindowWindowSize OBJECT-TYPE
			SYNTAX Unsigned32 (3..100)
			MAX-ACCESS read-write
			STATUS current
			DESCRIPTION
				"number of samples in the window
				
				XPath: /extremeWing-config/rf_domain[name=key1]/stats_window[window_idx=key2]/window_size"
			DEFVAL { 3 }
			::= { extremeWingCfgRfdStatsWindowEntry 4 }

		
-- /extremeWing-config/device
		-- 1.3.6.1.4.1.1916.2.131.50.1.3.18
		extremeWingCfgDev OBJECT IDENTIFIER ::= { extremeWingConfig 18 }

		
		-- 1.3.6.1.4.1.1916.2.131.50.1.3.18.1
		extremeWingCfgDevTable OBJECT-TYPE
			SYNTAX SEQUENCE OF ExtremeWingCfgDevEntry
			MAX-ACCESS not-accessible
			STATUS current
			DESCRIPTION
				"
				
				/extremeWing-config/device"
			::= { extremeWingCfgDev 1 }

		
		-- 1.3.6.1.4.1.1916.2.131.50.1.3.18.1.1
		extremeWingCfgDevEntry OBJECT-TYPE
			SYNTAX ExtremeWingCfgDevEntry
			MAX-ACCESS not-accessible
			STATUS current
			DESCRIPTION
				"An entry in the table."
			INDEX { extremeWingCfgDevMac }
			::= { extremeWingCfgDevTable 1 }

		
		ExtremeWingCfgDevEntry ::=
			SEQUENCE { 
				extremeWingCfgDevMac
					MacAddress,
				extremeWingCfgDevHostname
					DisplayString,
				extremeWingCfgDevBuilding
					DisplayString,
				extremeWingCfgDevFloor
					DisplayString,
				extremeWingCfgDevNumRadios
					Unsigned32,
				extremeWingCfgDevProfileName
					ExtremeWingIdentifier,
				extremeWingCfgDevRfDomainName
					ExtremeWingIdentifier,
				extremeWingCfgDevHttpsTrustpoint
					DisplayString,
				extremeWingCfgDevRadiusCaTrustpoint
					DisplayString,
				extremeWingCfgDevRadiusServerTrustpoint
					DisplayString,
				extremeWingCfgDevSshRsaKey
					ExtremeWingIdentifier,
				extremeWingCfgDevHasOverrides
					TruthValue,
				extremeWingCfgDevTunnelController
					DisplayString,
				extremeWingCfgDevPreferredTunnelController
					DisplayString,
				extremeWingCfgDevDot1xSysAuthCtrl
					TruthValue,
				extremeWingCfgDevDot1xGuestVlanCtrl
					TruthValue,
				extremeWingCfgDevDot1xAaaPolicy
					ExtremeWingIdentifier,
				extremeWingCfgDevRaidAlarmEnable
					TruthValue
			 }

		-- 1.3.6.1.4.1.1916.2.131.50.1.3.18.1.1.1
		extremeWingCfgDevMac OBJECT-TYPE
			SYNTAX MacAddress
			MAX-ACCESS read-only
			STATUS current
			DESCRIPTION
				"
				
				XPath: /extremeWing-config/device[mac=key1]/mac"
			::= { extremeWingCfgDevEntry 1 }

		
		-- 1.3.6.1.4.1.1916.2.131.50.1.3.18.1.1.3
		extremeWingCfgDevHostname OBJECT-TYPE
			SYNTAX DisplayString (SIZE (64))
			MAX-ACCESS read-write
			STATUS current
			DESCRIPTION
				"
				
				XPath: /extremeWing-config/device[mac=key1]/hostname"
			::= { extremeWingCfgDevEntry 3 }

		
		-- 1.3.6.1.4.1.1916.2.131.50.1.3.18.1.1.4
		extremeWingCfgDevBuilding OBJECT-TYPE
			SYNTAX DisplayString (SIZE (64))
			MAX-ACCESS read-write
			STATUS current
			DESCRIPTION
				"
				
				XPath: /extremeWing-config/device[mac=key1]/building"
			::= { extremeWingCfgDevEntry 4 }

		
		-- 1.3.6.1.4.1.1916.2.131.50.1.3.18.1.1.5
		extremeWingCfgDevFloor OBJECT-TYPE
			SYNTAX DisplayString (SIZE (32))
			MAX-ACCESS read-write
			STATUS current
			DESCRIPTION
				"
				
				XPath: /extremeWing-config/device[mac=key1]/floor"
			::= { extremeWingCfgDevEntry 5 }

		
		-- 1.3.6.1.4.1.1916.2.131.50.1.3.18.1.1.6
		extremeWingCfgDevNumRadios OBJECT-TYPE
			SYNTAX Unsigned32 (0..3)
			MAX-ACCESS read-write
			STATUS current
			DESCRIPTION
				"
				
				XPath: /extremeWing-config/device[mac=key1]/num_radios"
			::= { extremeWingCfgDevEntry 6 }

		
		-- 1.3.6.1.4.1.1916.2.131.50.1.3.18.1.1.7
		extremeWingCfgDevProfileName OBJECT-TYPE
			SYNTAX ExtremeWingIdentifier
			MAX-ACCESS read-write
			STATUS current
			DESCRIPTION
				"
				
				XPath: /extremeWing-config/device[mac=key1]/profile_name"
			::= { extremeWingCfgDevEntry 7 }

		
		-- 1.3.6.1.4.1.1916.2.131.50.1.3.18.1.1.8
		extremeWingCfgDevRfDomainName OBJECT-TYPE
			SYNTAX ExtremeWingIdentifier
			MAX-ACCESS read-write
			STATUS current
			DESCRIPTION
				"
				
				XPath: /extremeWing-config/device[mac=key1]/rf_domain_name"
			::= { extremeWingCfgDevEntry 8 }

		
		-- 1.3.6.1.4.1.1916.2.131.50.1.3.18.1.1.9
		extremeWingCfgDevHttpsTrustpoint OBJECT-TYPE
			SYNTAX DisplayString (SIZE (1..32))
			MAX-ACCESS read-write
			STATUS current
			DESCRIPTION
				"
				
				XPath: /extremeWing-config/device[mac=key1]/https-trustpoint"
			DEFVAL { "default-trustpoint" }
			::= { extremeWingCfgDevEntry 9 }

		
		-- 1.3.6.1.4.1.1916.2.131.50.1.3.18.1.1.10
		extremeWingCfgDevRadiusCaTrustpoint OBJECT-TYPE
			SYNTAX DisplayString (SIZE (1..32))
			MAX-ACCESS read-write
			STATUS current
			DESCRIPTION
				"
				
				XPath: /extremeWing-config/device[mac=key1]/radius-ca-trustpoint"
			::= { extremeWingCfgDevEntry 10 }

		
		-- 1.3.6.1.4.1.1916.2.131.50.1.3.18.1.1.11
		extremeWingCfgDevRadiusServerTrustpoint OBJECT-TYPE
			SYNTAX DisplayString (SIZE (1..32))
			MAX-ACCESS read-write
			STATUS current
			DESCRIPTION
				"
				
				XPath: /extremeWing-config/device[mac=key1]/radius-server-trustpoint"
			DEFVAL { "default-trustpoint" }
			::= { extremeWingCfgDevEntry 11 }

		
		-- 1.3.6.1.4.1.1916.2.131.50.1.3.18.1.1.12
		extremeWingCfgDevSshRsaKey OBJECT-TYPE
			SYNTAX ExtremeWingIdentifier
			MAX-ACCESS read-write
			STATUS current
			DESCRIPTION
				"
				
				XPath: /extremeWing-config/device[mac=key1]/ssh-rsa-key"
			DEFVAL { "default_rsa_key" }
			::= { extremeWingCfgDevEntry 12 }

		
		-- 1.3.6.1.4.1.1916.2.131.50.1.3.18.1.1.13
		extremeWingCfgDevHasOverrides OBJECT-TYPE
			SYNTAX TruthValue
			MAX-ACCESS read-only
			STATUS current
			DESCRIPTION
				"read only value to indicate whether the device has at least one override
				
				XPath: /extremeWing-config/device[mac=key1]/has_overrides"
			DEFVAL { false }
			::= { extremeWingCfgDevEntry 13 }

		
		-- 1.3.6.1.4.1.1916.2.131.50.1.3.18.1.1.14
		extremeWingCfgDevTunnelController OBJECT-TYPE
			SYNTAX DisplayString
			MAX-ACCESS read-write
			STATUS current
			DESCRIPTION
				"Name of this tunneled-wlan-controller
				
				XPath: /extremeWing-config/device[mac=key1]/tunnel_controller"
			::= { extremeWingCfgDevEntry 14 }

		
		-- 1.3.6.1.4.1.1916.2.131.50.1.3.18.1.1.15
		extremeWingCfgDevPreferredTunnelController OBJECT-TYPE
			SYNTAX DisplayString
			MAX-ACCESS read-write
			STATUS current
			DESCRIPTION
				"Controller this AP will prefer to tunnel tunnelled-wlan a.k.a extended-vlan traffic to
				
				XPath: /extremeWing-config/device[mac=key1]/preferred_tunnel_controller"
			::= { extremeWingCfgDevEntry 15 }

		
		-- 1.3.6.1.4.1.1916.2.131.50.1.3.18.1.1.16
		extremeWingCfgDevDot1xSysAuthCtrl OBJECT-TYPE
			SYNTAX TruthValue
			MAX-ACCESS read-write
			STATUS current
			DESCRIPTION
				"Globally enable 802.1x authentication
				
				XPath: /extremeWing-config/device[mac=key1]/dot1x_sys_auth_ctrl"
			DEFVAL { false }
			::= { extremeWingCfgDevEntry 16 }

		
		-- 1.3.6.1.4.1.1916.2.131.50.1.3.18.1.1.17
		extremeWingCfgDevDot1xGuestVlanCtrl OBJECT-TYPE
			SYNTAX TruthValue
			MAX-ACCESS read-write
			STATUS current
			DESCRIPTION
				"Globally enable 802.1x guest vlans
				
				XPath: /extremeWing-config/device[mac=key1]/dot1x_guest_vlan_ctrl"
			DEFVAL { false }
			::= { extremeWingCfgDevEntry 17 }

		
		-- 1.3.6.1.4.1.1916.2.131.50.1.3.18.1.1.18
		extremeWingCfgDevDot1xAaaPolicy OBJECT-TYPE
			SYNTAX ExtremeWingIdentifier
			MAX-ACCESS read-write
			STATUS current
			DESCRIPTION
				"AAA Authentication policy for 802.1x Authentication
				
				XPath: /extremeWing-config/device[mac=key1]/dot1x_aaa_policy"
			::= { extremeWingCfgDevEntry 18 }


		-- 1.3.6.1.4.1.1916.2.131.50.1.3.18.1.1.19
		extremeWingCfgDevRaidAlarmEnable OBJECT-TYPE
			SYNTAX TruthValue
			MAX-ACCESS read-write
			STATUS current
			DESCRIPTION
				"The chassis alarm will sound on RAID degrade events.
				XPath: /extremeWing-config/device[mac=key1]/raid_alarm_enable"
			DEFVAL { true }
			::= { extremeWingCfgDevEntry 19 }

		
--  /extremeWing-config/device/interface
		-- 1.3.6.1.4.1.1916.2.131.50.1.3.18.3
		extremeWingCfgDevIf OBJECT IDENTIFIER ::= { extremeWingCfgDev 3 }

		
		-- 1.3.6.1.4.1.1916.2.131.50.1.3.18.3.1
		extremeWingCfgDevIfTable OBJECT-TYPE
			SYNTAX SEQUENCE OF ExtremeWingCfgDevIfEntry
			MAX-ACCESS not-accessible
			STATUS current
			DESCRIPTION
				"
				
				/extremeWing-config/device/interface"
			::= { extremeWingCfgDevIf 1 }

		
		-- 1.3.6.1.4.1.1916.2.131.50.1.3.18.3.1.1
		extremeWingCfgDevIfEntry OBJECT-TYPE
			SYNTAX ExtremeWingCfgDevIfEntry
			MAX-ACCESS not-accessible
			STATUS current
			DESCRIPTION
				"An entry in the table."
			INDEX { extremeWingCfgDevMac, extremeWingCfgDevIfName }
			::= { extremeWingCfgDevIfTable 1 }

		
		ExtremeWingCfgDevIfEntry ::=
			SEQUENCE { 
				extremeWingCfgDevIfName
					ExtremeWingIdentifier,
				extremeWingCfgDevIfDescription
					DisplayString,
				extremeWingCfgDevIfType
					DisplayString,
				extremeWingCfgDevIfShutdown
					TruthValue,
				extremeWingCfgDevIfIpInAcl
					ExtremeWingIdentifier,
				extremeWingCfgDevIfMacInAcl
					ExtremeWingIdentifier
			 }

		-- 1.3.6.1.4.1.1916.2.131.50.1.3.18.3.1.1.1
		extremeWingCfgDevIfName OBJECT-TYPE
			SYNTAX ExtremeWingIdentifier
			MAX-ACCESS read-only
			STATUS current
			DESCRIPTION
				"
				
				XPath: /extremeWing-config/device[mac=key1]/interface[name=key2]/name"
			::= { extremeWingCfgDevIfEntry 1 }

		
		-- 1.3.6.1.4.1.1916.2.131.50.1.3.18.3.1.1.3
		extremeWingCfgDevIfDescription OBJECT-TYPE
			SYNTAX DisplayString
			MAX-ACCESS read-write
			STATUS current
			DESCRIPTION
				"
				
				XPath: /extremeWing-config/device[mac=key1]/interface[name=key2]/description"
			::= { extremeWingCfgDevIfEntry 3 }

		
		-- 1.3.6.1.4.1.1916.2.131.50.1.3.18.3.1.1.4
		extremeWingCfgDevIfType OBJECT-TYPE
			SYNTAX DisplayString
			MAX-ACCESS read-write
			STATUS current
			DESCRIPTION
				"Hardware type of the network interface
				
				Values:
				ethernet
				vlan
				radio
				port_channel
				
				XPath: /extremeWing-config/device[mac=key1]/interface[name=key2]/type"
			::= { extremeWingCfgDevIfEntry 4 }

		
		-- 1.3.6.1.4.1.1916.2.131.50.1.3.18.3.1.1.5
		extremeWingCfgDevIfShutdown OBJECT-TYPE
			SYNTAX TruthValue
			MAX-ACCESS read-write
			STATUS current
			DESCRIPTION
				"
				
				XPath: /extremeWing-config/device[mac=key1]/interface[name=key2]/shutdown"
			DEFVAL { false }
			::= { extremeWingCfgDevIfEntry 5 }

		
		-- 1.3.6.1.4.1.1916.2.131.50.1.3.18.3.1.1.6
		extremeWingCfgDevIfIpInAcl OBJECT-TYPE
			SYNTAX ExtremeWingIdentifier
			MAX-ACCESS read-write
			STATUS current
			DESCRIPTION
				"
				
				XPath: /extremeWing-config/device[mac=key1]/interface[name=key2]/ip_in_acl"
			::= { extremeWingCfgDevIfEntry 6 }

		
		-- 1.3.6.1.4.1.1916.2.131.50.1.3.18.3.1.1.7
		extremeWingCfgDevIfMacInAcl OBJECT-TYPE
			SYNTAX ExtremeWingIdentifier
			MAX-ACCESS read-write
			STATUS current
			DESCRIPTION
				"
				
				XPath: /extremeWing-config/device[mac=key1]/interface[name=key2]/mac_in_acl"
			::= { extremeWingCfgDevIfEntry 7 }

		
		-- 1.3.6.1.4.1.1916.2.131.50.1.3.18.3.2
		extremeWingCfgDevIfEthTable OBJECT-TYPE
			SYNTAX SEQUENCE OF ExtremeWingCfgDevIfEthEntry
			MAX-ACCESS not-accessible
			STATUS current
			DESCRIPTION
				"
				
				/extremeWing-config/device/interface"
			::= { extremeWingCfgDevIf 2 }

		
		-- 1.3.6.1.4.1.1916.2.131.50.1.3.18.3.2.1
		extremeWingCfgDevIfEthEntry OBJECT-TYPE
			SYNTAX ExtremeWingCfgDevIfEthEntry
			MAX-ACCESS not-accessible
			STATUS current
			DESCRIPTION
				"An entry in the table."
			INDEX { extremeWingCfgDevMac, extremeWingCfgDevIfName }
			::= { extremeWingCfgDevIfEthTable 1 }

		
		ExtremeWingCfgDevIfEthEntry ::=
			SEQUENCE { 
				extremeWingCfgDevIfEthSpeed
					DisplayString,
				extremeWingCfgDevIfEthDuplex
					DisplayString,
				extremeWingCfgDevIfEthSwitchportMode
					DisplayString,
				extremeWingCfgDevIfEthSwitchportNativeVlan
					Unsigned32,
				extremeWingCfgDevIfEthSwitchportNativeVlanTagged
					TruthValue,
				extremeWingCfgDevIfEthArpTrust
					TruthValue,
				extremeWingCfgDevIfEthDhcpTrust
					TruthValue,
				extremeWingCfgDevIfEthArpHeaderMismatchValidation
					TruthValue,
				extremeWingCfgDevIfEthQosTrustDscp
					TruthValue,
				extremeWingCfgDevIfEthQosTrust802dot1p
					TruthValue,
				extremeWingCfgDevIfEthStaticChannelGroup
					Unsigned32,
				extremeWingCfgDevIfEthPoeSupported
					TruthValue,
				extremeWingCfgDevIfEthPoePower
					TruthValue,
				extremeWingCfgDevIfEthPoeLimit
					Unsigned32,
				extremeWingCfgDevIfEthPoePriority
					DisplayString,
				extremeWingCfgDevIfEthDot1xSupported
					TruthValue,
				extremeWingCfgDevIfEthDot1xEnable
					TruthValue,
				extremeWingCfgDevIfEthDot1xUsername
					DisplayString,
				extremeWingCfgDevIfEthDot1xPassword
					DisplayString,
				extremeWingCfgDevIfEthCdpReceive
					TruthValue,
				extremeWingCfgDevIfEthCdpTransmit
					TruthValue,
				extremeWingCfgDevIfEthLldpReceive
					TruthValue,
				extremeWingCfgDevIfEthLldpTransmit
					TruthValue,
				extremeWingCfgDevIfEthPortChannelLoadBalance
					DisplayString
			 }

		-- 1.3.6.1.4.1.1916.2.131.50.1.3.18.3.2.1.1
		extremeWingCfgDevIfEthSpeed OBJECT-TYPE
			SYNTAX DisplayString
			MAX-ACCESS read-write
			STATUS current
			DESCRIPTION
				"
				Values:
				10
				100
				1000
				auto
				
				XPath: /extremeWing-config/device[mac=key1]/interface[name=key2]/speed"
			DEFVAL { "auto" }
			::= { extremeWingCfgDevIfEthEntry 1 }

		
		-- 1.3.6.1.4.1.1916.2.131.50.1.3.18.3.2.1.2
		extremeWingCfgDevIfEthDuplex OBJECT-TYPE
			SYNTAX DisplayString
			MAX-ACCESS read-write
			STATUS current
			DESCRIPTION
				"
				Values:
				half
				full
				auto
				
				XPath: /extremeWing-config/device[mac=key1]/interface[name=key2]/duplex"
			DEFVAL { "auto" }
			::= { extremeWingCfgDevIfEthEntry 2 }

		
		-- 1.3.6.1.4.1.1916.2.131.50.1.3.18.3.2.1.3
		extremeWingCfgDevIfEthSwitchportMode OBJECT-TYPE
			SYNTAX DisplayString
			MAX-ACCESS read-write
			STATUS current
			DESCRIPTION
				"Mode of the Layer 2 interface.
				
				Values:
				access
				trunk
				
				XPath: /extremeWing-config/device[mac=key1]/interface[name=key2]/switchport/mode"
			DEFVAL { "access" }
			::= { extremeWingCfgDevIfEthEntry 3 }

		
		-- 1.3.6.1.4.1.1916.2.131.50.1.3.18.3.2.1.4
		extremeWingCfgDevIfEthSwitchportNativeVlan OBJECT-TYPE
			SYNTAX Unsigned32 (1..4094)
			MAX-ACCESS read-write
			STATUS current
			DESCRIPTION
				"Native VLAN for classifying untagged traffic.
				
				XPath: /extremeWing-config/device[mac=key1]/interface[name=key2]/switchport/native_vlan"
			DEFVAL { 1 }
			::= { extremeWingCfgDevIfEthEntry 4 }

		
		-- 1.3.6.1.4.1.1916.2.131.50.1.3.18.3.2.1.5
		extremeWingCfgDevIfEthSwitchportNativeVlanTagged OBJECT-TYPE
			SYNTAX TruthValue
			MAX-ACCESS read-write
			STATUS current
			DESCRIPTION
				"Tag the native VLAN.
				
				XPath: /extremeWing-config/device[mac=key1]/interface[name=key2]/switchport/native_vlan_tagged"
			DEFVAL { false }
			::= { extremeWingCfgDevIfEthEntry 5 }

		
		-- 1.3.6.1.4.1.1916.2.131.50.1.3.18.3.2.1.6
		extremeWingCfgDevIfEthArpTrust OBJECT-TYPE
			SYNTAX TruthValue
			MAX-ACCESS read-write
			STATUS current
			DESCRIPTION
				"Trust ARP request on this port.
				
				XPath: /extremeWing-config/device[mac=key1]/interface[name=key2]/arp_trust"
			DEFVAL { false }
			::= { extremeWingCfgDevIfEthEntry 6 }

		
		-- 1.3.6.1.4.1.1916.2.131.50.1.3.18.3.2.1.7
		extremeWingCfgDevIfEthDhcpTrust OBJECT-TYPE
			SYNTAX TruthValue
			MAX-ACCESS read-write
			STATUS current
			DESCRIPTION
				"Trust DHCP responses on this port
				
				XPath: /extremeWing-config/device[mac=key1]/interface[name=key2]/dhcp_trust"
			DEFVAL { true }
			::= { extremeWingCfgDevIfEthEntry 7 }

		
		-- 1.3.6.1.4.1.1916.2.131.50.1.3.18.3.2.1.8
		extremeWingCfgDevIfEthArpHeaderMismatchValidation OBJECT-TYPE
			SYNTAX TruthValue
			MAX-ACCESS read-write
			STATUS current
			DESCRIPTION
				"Check mismatch for source MAC in ARP header and ethernet header.
				
				XPath: /extremeWing-config/device[mac=key1]/interface[name=key2]/arp_header_mismatch_validation"
			DEFVAL { false }
			::= { extremeWingCfgDevIfEthEntry 8 }

		
		-- 1.3.6.1.4.1.1916.2.131.50.1.3.18.3.2.1.9
		extremeWingCfgDevIfEthQosTrustDscp OBJECT-TYPE
			SYNTAX TruthValue
			MAX-ACCESS read-write
			STATUS current
			DESCRIPTION
				"Trust IP DSCP values on this port.
				
				XPath: /extremeWing-config/device[mac=key1]/interface[name=key2]/qos_trust_dscp"
			DEFVAL { true }
			::= { extremeWingCfgDevIfEthEntry 9 }

		
		-- 1.3.6.1.4.1.1916.2.131.50.1.3.18.3.2.1.10
		extremeWingCfgDevIfEthQosTrust802dot1p OBJECT-TYPE
			SYNTAX TruthValue
			MAX-ACCESS read-write
			STATUS current
			DESCRIPTION
				"Trust 802.1p COS values on this port.
				
				XPath: /extremeWing-config/device[mac=key1]/interface[name=key2]/qos_trust_802dot1p"
			DEFVAL { true }
			::= { extremeWingCfgDevIfEthEntry 10 }

		
		-- 1.3.6.1.4.1.1916.2.131.50.1.3.18.3.2.1.11
		extremeWingCfgDevIfEthStaticChannelGroup OBJECT-TYPE
			SYNTAX Unsigned32 (1..5)
			MAX-ACCESS read-write
			STATUS current
			DESCRIPTION
				"Channel group to which the port belongs.
				
				XPath: /extremeWing-config/device[mac=key1]/interface[name=key2]/static_channel_group"
			::= { extremeWingCfgDevIfEthEntry 11 }

		
		-- 1.3.6.1.4.1.1916.2.131.50.1.3.18.3.2.1.12
		extremeWingCfgDevIfEthPoeSupported OBJECT-TYPE
			SYNTAX TruthValue
			MAX-ACCESS read-write
			STATUS current
			DESCRIPTION
				"POE supported on this port when true.
				
				XPath: /extremeWing-config/device[mac=key1]/interface[name=key2]/poe_supported"
			DEFVAL { false }
			::= { extremeWingCfgDevIfEthEntry 12 }

		
		-- 1.3.6.1.4.1.1916.2.131.50.1.3.18.3.2.1.13
		extremeWingCfgDevIfEthPoePower OBJECT-TYPE
			SYNTAX TruthValue
			MAX-ACCESS read-write
			STATUS current
			DESCRIPTION
				"Enable/Disable POE Power.
				
				XPath: /extremeWing-config/device[mac=key1]/interface[name=key2]/poe_power"
			DEFVAL { true }
			::= { extremeWingCfgDevIfEthEntry 13 }

		
		-- 1.3.6.1.4.1.1916.2.131.50.1.3.18.3.2.1.14
		extremeWingCfgDevIfEthPoeLimit OBJECT-TYPE
			SYNTAX Unsigned32 (0..40)
			UNITS "watts"
			MAX-ACCESS read-write
			STATUS current
			DESCRIPTION
				"
				
				XPath: /extremeWing-config/device[mac=key1]/interface[name=key2]/poe_limit"
			DEFVAL { 0 }
			::= { extremeWingCfgDevIfEthEntry 14 }

		
		-- 1.3.6.1.4.1.1916.2.131.50.1.3.18.3.2.1.15
		extremeWingCfgDevIfEthPoePriority OBJECT-TYPE
			SYNTAX DisplayString
			MAX-ACCESS read-write
			STATUS current
			DESCRIPTION
				"
				Values:
				critical
				high
				low
				
				XPath: /extremeWing-config/device[mac=key1]/interface[name=key2]/poe_priority"
			DEFVAL { "low" }
			::= { extremeWingCfgDevIfEthEntry 15 }

		
		-- 1.3.6.1.4.1.1916.2.131.50.1.3.18.3.2.1.16
		extremeWingCfgDevIfEthDot1xSupported OBJECT-TYPE
			SYNTAX TruthValue
			MAX-ACCESS read-write
			STATUS current
			DESCRIPTION
				"Dot1x supported on port when enabled.
				
				XPath: /extremeWing-config/device[mac=key1]/interface[name=key2]/dot1x_supported"
			DEFVAL { false }
			::= { extremeWingCfgDevIfEthEntry 16 }

		
		-- 1.3.6.1.4.1.1916.2.131.50.1.3.18.3.2.1.17
		extremeWingCfgDevIfEthDot1xEnable OBJECT-TYPE
			SYNTAX TruthValue
			MAX-ACCESS read-write
			STATUS current
			DESCRIPTION
				"
				
				XPath: /extremeWing-config/device[mac=key1]/interface[name=key2]/dot1x/enable"
			DEFVAL { false }
			::= { extremeWingCfgDevIfEthEntry 17 }

		
		-- 1.3.6.1.4.1.1916.2.131.50.1.3.18.3.2.1.18
		extremeWingCfgDevIfEthDot1xUsername OBJECT-TYPE
			SYNTAX DisplayString (SIZE (1..32))
			MAX-ACCESS read-write
			STATUS current
			DESCRIPTION
				"
				
				XPath: /extremeWing-config/device[mac=key1]/interface[name=key2]/dot1x/username"
			::= { extremeWingCfgDevIfEthEntry 18 }

		
		-- 1.3.6.1.4.1.1916.2.131.50.1.3.18.3.2.1.19
		extremeWingCfgDevIfEthDot1xPassword OBJECT-TYPE
			SYNTAX DisplayString
			MAX-ACCESS read-write
			STATUS current
			DESCRIPTION
				"
				
				XPath: /extremeWing-config/device[mac=key1]/interface[name=key2]/dot1x/password"
			::= { extremeWingCfgDevIfEthEntry 19 }

		
		-- 1.3.6.1.4.1.1916.2.131.50.1.3.18.3.2.1.20
		extremeWingCfgDevIfEthCdpReceive OBJECT-TYPE
			SYNTAX TruthValue
			MAX-ACCESS read-write
			STATUS current
			DESCRIPTION
				"Snoop CDP on port
				
				XPath: /extremeWing-config/device[mac=key1]/interface[name=key2]/cdp_receive"
			DEFVAL { true }
			::= { extremeWingCfgDevIfEthEntry 20 }

		
		-- 1.3.6.1.4.1.1916.2.131.50.1.3.18.3.2.1.21
		extremeWingCfgDevIfEthCdpTransmit OBJECT-TYPE
			SYNTAX TruthValue
			MAX-ACCESS read-write
			STATUS current
			DESCRIPTION
				"Transmit CDP packets on port
				
				XPath: /extremeWing-config/device[mac=key1]/interface[name=key2]/cdp_transmit"
			DEFVAL { false }
			::= { extremeWingCfgDevIfEthEntry 21 }

		
		-- 1.3.6.1.4.1.1916.2.131.50.1.3.18.3.2.1.22
		extremeWingCfgDevIfEthLldpReceive OBJECT-TYPE
			SYNTAX TruthValue
			MAX-ACCESS read-write
			STATUS current
			DESCRIPTION
				"Snoop LLDP on port
				
				XPath: /extremeWing-config/device[mac=key1]/interface[name=key2]/lldp_receive"
			DEFVAL { true }
			::= { extremeWingCfgDevIfEthEntry 22 }

		
		-- 1.3.6.1.4.1.1916.2.131.50.1.3.18.3.2.1.23
		extremeWingCfgDevIfEthLldpTransmit OBJECT-TYPE
			SYNTAX TruthValue
			MAX-ACCESS read-write
			STATUS current
			DESCRIPTION
				"Transmit LLDP PDUs on port
				
				XPath: /extremeWing-config/device[mac=key1]/interface[name=key2]/lldp_transmit"
			DEFVAL { false }
			::= { extremeWingCfgDevIfEthEntry 23 }

		
		-- 1.3.6.1.4.1.1916.2.131.50.1.3.18.3.2.1.24
		extremeWingCfgDevIfEthPortChannelLoadBalance OBJECT-TYPE
			SYNTAX DisplayString
			MAX-ACCESS read-write
			STATUS current
			DESCRIPTION
				"
				Values:
				src-dst-ip
				src-dst-mac
				
				XPath: /extremeWing-config/device[mac=key1]/interface[name=key2]/poe_priority"
			DEFVAL { "src-dst-ip" }
			::= { extremeWingCfgDevIfEthEntry 24 }

		
		-- 1.3.6.1.4.1.1916.2.131.50.1.3.18.3.3
		extremeWingCfgDevIfVlanTable OBJECT-TYPE
			SYNTAX SEQUENCE OF ExtremeWingCfgDevIfVlanEntry
			MAX-ACCESS not-accessible
			STATUS current
			DESCRIPTION
				"
				
				/extremeWing-config/device/interface"
			::= { extremeWingCfgDevIf 3 }

		
		-- 1.3.6.1.4.1.1916.2.131.50.1.3.18.3.3.1
		extremeWingCfgDevIfVlanEntry OBJECT-TYPE
			SYNTAX ExtremeWingCfgDevIfVlanEntry
			MAX-ACCESS not-accessible
			STATUS current
			DESCRIPTION
				"An entry in the table."
			INDEX { extremeWingCfgDevMac, extremeWingCfgDevIfName }
			::= { extremeWingCfgDevIfVlanTable 1 }

		
		ExtremeWingCfgDevIfVlanEntry ::=
			SEQUENCE { 
				extremeWingCfgDevIfVlanVlan
					Unsigned32,
				extremeWingCfgDevIfVlanDhcpcOptAll
					TruthValue,
				extremeWingCfgDevIfVlanNatDirection
					DisplayString,
				extremeWingCfgDevIfVlanCryptoMap
					ExtremeWingIdentifier,
				extremeWingCfgDevIfVlanDhcpRelayIncoming
					TruthValue,
				extremeWingCfgDevIfVlanRowStatus
					RowStatus
			 }

		-- 1.3.6.1.4.1.1916.2.131.50.1.3.18.3.3.1.1
		extremeWingCfgDevIfVlanVlan OBJECT-TYPE
			SYNTAX Unsigned32 (1..4094)
			MAX-ACCESS read-write
			STATUS current
			DESCRIPTION
				"
				
				XPath: /extremeWing-config/device[mac=key1]/interface[name=key2]/vlan"
			::= { extremeWingCfgDevIfVlanEntry 1 }

		
		-- 1.3.6.1.4.1.1916.2.131.50.1.3.18.3.3.1.2
		extremeWingCfgDevIfVlanDhcpcOptAll OBJECT-TYPE
			SYNTAX TruthValue
			MAX-ACCESS read-write
			STATUS current
			DESCRIPTION
				"Learn default gateway, name servers, domain name on this
				interface.
				
				XPath: /extremeWing-config/device[mac=key1]/interface[name=key2]/dhcpc_opt_all"
			DEFVAL { false }
			::= { extremeWingCfgDevIfVlanEntry 2 }

		
		-- 1.3.6.1.4.1.1916.2.131.50.1.3.18.3.3.1.3
		extremeWingCfgDevIfVlanNatDirection OBJECT-TYPE
			SYNTAX DisplayString
			MAX-ACCESS read-write
			STATUS current
			DESCRIPTION
				"
				
				Values:
				inside
				outside
				none
				
				XPath: /extremeWing-config/device[mac=key1]/interface[name=key2]/nat_direction"
			DEFVAL { "none" }
			::= { extremeWingCfgDevIfVlanEntry 3 }

		
		-- 1.3.6.1.4.1.1916.2.131.50.1.3.18.3.3.1.4
		extremeWingCfgDevIfVlanCryptoMap OBJECT-TYPE
			SYNTAX ExtremeWingIdentifier
			MAX-ACCESS read-write
			STATUS current
			DESCRIPTION
				"Attach an already configured crypto map to this interface.
				
				XPath: /extremeWing-config/device[mac=key1]/interface[name=key2]/crypto_map"
			::= { extremeWingCfgDevIfVlanEntry 4 }

		
		-- 1.3.6.1.4.1.1916.2.131.50.1.3.18.3.3.1.5
		extremeWingCfgDevIfVlanDhcpRelayIncoming OBJECT-TYPE
			SYNTAX TruthValue
			MAX-ACCESS read-write
			STATUS current
			DESCRIPTION
				"Allow on-board DHCP server to respond to relayed DHCP packets on this interface
				
				XPath: /extremeWing-config/device[mac=key1]/interface[name=key2]/dhcp_relay_incoming"
			DEFVAL { false }
			::= { extremeWingCfgDevIfVlanEntry 5 }

		-- 1.3.6.1.4.1.1916.2.131.50.1.3.18.3.3.1.6
		extremeWingCfgDevIfVlanRowStatus OBJECT-TYPE
			SYNTAX RowStatus
				{
				active(1),
				createAndGo(4),
				destroy(6)
				}
			MAX-ACCESS read-create
			STATUS current
			DESCRIPTION
				"The status of this conceptual row.
				XPath: /extremeWing-config/device[mac=key1]//interface[name=key2]/vlan_row_status"
			::= { extremeWingCfgDevIfVlanEntry 6 }


		-- 1.3.6.1.4.1.1916.2.131.50.1.3.18.3.5
		extremeWingCfgDevIfRadioTable OBJECT-TYPE
			SYNTAX SEQUENCE OF ExtremeWingCfgDevIfRadioEntry
			MAX-ACCESS not-accessible
			STATUS current
			DESCRIPTION
				"
				
				/extremeWing-config/device/interface"
			::= { extremeWingCfgDevIf 5 }

		
		-- 1.3.6.1.4.1.1916.2.131.50.1.3.18.3.5.1
		extremeWingCfgDevIfRadioEntry OBJECT-TYPE
			SYNTAX ExtremeWingCfgDevIfRadioEntry
			MAX-ACCESS not-accessible
			STATUS current
			DESCRIPTION
				"An entry in the table."
			INDEX { extremeWingCfgDevMac, extremeWingCfgDevIfName }
			::= { extremeWingCfgDevIfRadioTable 1 }

		
		ExtremeWingCfgDevIfRadioEntry ::=
			SEQUENCE { 
				extremeWingCfgDevIfRadioRfMode
					DisplayString,
				extremeWingCfgDevIfRadioChannel
					DisplayString,
				extremeWingCfgDevIfRadioPower
					Unsigned32,
				extremeWingCfgDevIfRadioPlacement
					DisplayString,
				extremeWingCfgDevIfRadioBeaconInterval
					DisplayString,
				extremeWingCfgDevIfRadioRtsThreshold
					Unsigned32,
				extremeWingCfgDevIfRadioOffChannelScan
					TruthValue,
				extremeWingCfgDevIfRadioPreambleShort
					TruthValue,
				extremeWingCfgDevIfRadioGuardInterval
					DisplayString,
				extremeWingCfgDevIfRadioAmpduMode
					DisplayString,
				extremeWingCfgDevIfRadioAmsduMode
					DisplayString,
				extremeWingCfgDevIfRadioRifsMode
					DisplayString,
				extremeWingCfgDevIfRadioAmpduMaxAggrSizeRx
					DisplayString,
				extremeWingCfgDevIfRadioAmpduMaxAggrSizeTx
					Unsigned32,
				extremeWingCfgDevIfRadioAmpduMinSpacing
					DisplayString,
				extremeWingCfgDevIfRadioAntennaMode
					DisplayString,
				extremeWingCfgDevIfRadioNonUnicastForwarding
					DisplayString,
				extremeWingCfgDevIfRadioDynamicChainSelection
					TruthValue,
				extremeWingCfgDevIfRadioLockRfMode
					TruthValue,
				extremeWingCfgDevIfRadioSnifferRedirHost
					IpAddress,
				extremeWingCfgDevIfRadioSnifferRedirChannel
					DisplayString,
				extremeWingCfgDevIfRadioMesh
					DisplayString,
				extremeWingCfgDevIfRadioMeshLinks
					Unsigned32,
				extremeWingCfgDevIfRadioProbeResponseRetry
					TruthValue,
				extremeWingCfgDevIfRadioProbeResponseRate
					DisplayString,
				extremeWingCfgDevIfRadioMaxClients
					Unsigned32,
				extremeWingCfgDevIfRadioRadioTapMode
					DisplayString,
				extremeWingCfgDevIfRadioWirelessClientPower
					Unsigned32,
				extremeWingCfgDevIfRadioLoadBalLfCount
					Unsigned32,
				extremeWingCfgDevIfRadioLoadBalLfThroughput
					Unsigned32,
				extremeWingCfgDevIfRadioLoadBalWmCount
					Unsigned32,
				extremeWingCfgDevIfRadioLoadBalWmTput
					Unsigned32,
				extremeWingCfgDevIfRadioAssocAcl
					ExtremeWingIdentifier,
				extremeWingCfgDevIfRadioQosPolicy
					ExtremeWingIdentifier,
                                extremeWingCfgDevIfRadioAntennaDowntilt
                                        TruthValue,
                                extremeWingCfgDevIfRadioExtendedRange
                                        Unsigned32,
				extremeWingCfgDevIfRadioOperMode
					Integer32
			 }

		-- 1.3.6.1.4.1.1916.2.131.50.1.3.18.3.5.1.1
		extremeWingCfgDevIfRadioRfMode OBJECT-TYPE
			SYNTAX DisplayString
			MAX-ACCESS read-write
			STATUS current
			DESCRIPTION
				"
				
				Values:
				2.4GHz-wlan
				5GHz-wlan
				sensor
				
				Notes:
				On a WM3400 the radio-mode of radio1 can only be 2.4|sensor.
				radio2 can only be 5|sensor(so the 2.4-wlan and 5-wlan modes
				cant be interchanged) 
				
				On an AP4700 radio3 can only be sensor. It can never be
				2.4-wlan/5-wlan 
				
				XPath: /extremeWing-config/device[mac=key1]/interface[name=key2]/rf_mode"
			::= { extremeWingCfgDevIfRadioEntry 1 }

		
		-- 1.3.6.1.4.1.1916.2.131.50.1.3.18.3.5.1.2
		extremeWingCfgDevIfRadioChannel OBJECT-TYPE
			SYNTAX DisplayString
			MAX-ACCESS read-write
			STATUS current
			DESCRIPTION
				"Channel of operation for this radio.
				
				Values:
                                1, 1w, 2, 2w, 3, 3w, 4, 4w, 5, 5w, 6, 6w, 7, 7w, 8, 8w, 9,
                                9w, 10, 10w, 11, 11w, 12, 12w, 13, 13w, 14, 36, 36w,
                                36ww, 40, 40w, 40ww, 44, 44w, 44ww, 48, 48w, 48ww, 52,
                                52w, 52ww, 56, 56w, 56ww, 60, 60w, 60ww, 64, 64w, 64ww,
                                74, 100, 100w, 100ww, 104, 104w, 104ww, 108, 108w, 108ww,
                                112, 112w, 112ww, 116, 116w, 116ww, 120, 120w, 120ww, 124,
                                124w, 124ww, 128, 128w, 128ww, 132, 132w, 136, 136w, 140,
                                149, 149w, 149ww, 153, 153w, 153ww, 157, 157w, 157ww, 161,
                                161w, 161ww, 165, 34, 38, 42, 46, 21, 25, 184, 184w, 188,
                                188w, 192, 192w, 196, 196w, smart, acs
	
				
				When 'rf_mode' is set to '2.4GHz-wlan', valid channels are
				'1' through '14' and 'smart'.
				
				When 'rf_mode' is set to '5GHz-wlan', '1' through '14'
				are not allowed. Rest of the channels (including 'smart' are
				allowed)
				
				When 'rf_mode' is set to 'sensor', 'channel' setting
				is ignored.
				
				XPath: /extremeWing-config/device[mac=key1]/interface[name=key2]/channel"
			DEFVAL { "smart" }
			::= { extremeWingCfgDevIfRadioEntry 2 }

		
		-- 1.3.6.1.4.1.1916.2.131.50.1.3.18.3.5.1.3
		extremeWingCfgDevIfRadioPower OBJECT-TYPE
			SYNTAX Unsigned32 (0..27)
			UNITS "dBm"
			MAX-ACCESS read-write
			STATUS current
			DESCRIPTION
				"Transmit power of the radio.  A setting of 0 indicates
				Smart RF is managing the power.
				
				XPath: /extremeWing-config/device[mac=key1]/interface[name=key2]/power"
			DEFVAL { 20 }
			::= { extremeWingCfgDevIfRadioEntry 3 }

		
		-- 1.3.6.1.4.1.1916.2.131.50.1.3.18.3.5.1.4
		extremeWingCfgDevIfRadioPlacement OBJECT-TYPE
			SYNTAX DisplayString
			MAX-ACCESS read-write
			STATUS current
			DESCRIPTION
				"Location where this radio is operating.
				
				Values:
				indoor
				outdoor
				
				XPath: /extremeWing-config/device[mac=key1]/interface[name=key2]/placement"
			DEFVAL { "indoor" }
			::= { extremeWingCfgDevIfRadioEntry 4 }

		
		-- 1.3.6.1.4.1.1916.2.131.50.1.3.18.3.5.1.5
		extremeWingCfgDevIfRadioBeaconInterval OBJECT-TYPE
			SYNTAX DisplayString
			UNITS "milliseconds"
			MAX-ACCESS read-write
			STATUS current
			DESCRIPTION
				"Interval between radio beacons.
				
				Values:
				50
				100
				200
				
				XPath: /extremeWing-config/device[mac=key1]/interface[name=key2]/beacon_interval"
			DEFVAL { "100" }
			::= { extremeWingCfgDevIfRadioEntry 5 }

		
		-- 1.3.6.1.4.1.1916.2.131.50.1.3.18.3.5.1.6
		extremeWingCfgDevIfRadioRtsThreshold OBJECT-TYPE
			SYNTAX Unsigned32 (0..65536)
			UNITS "bytes"
			MAX-ACCESS read-write
			STATUS current
			DESCRIPTION
				"Ready to Send threshold on this radio.
				
				XPath: /extremeWing-config/device[mac=key1]/interface[name=key2]/rts_threshold"
			DEFVAL { 65536 }
			::= { extremeWingCfgDevIfRadioEntry 6 }

		
		-- 1.3.6.1.4.1.1916.2.131.50.1.3.18.3.5.1.7
		extremeWingCfgDevIfRadioOffChannelScan OBJECT-TYPE
			SYNTAX TruthValue
			MAX-ACCESS read-write
			STATUS current
			DESCRIPTION
				"Enable off-channel scanning on this radio.
				
				XPath: /extremeWing-config/device[mac=key1]/interface[name=key2]/off_channel_scan"
			DEFVAL { false }
			::= { extremeWingCfgDevIfRadioEntry 7 }

		
		-- 1.3.6.1.4.1.1916.2.131.50.1.3.18.3.5.1.8
		extremeWingCfgDevIfRadioPreambleShort OBJECT-TYPE
			SYNTAX TruthValue
			MAX-ACCESS read-write
			STATUS current
			DESCRIPTION
				"Configure use of short preamble.
				
				XPath: /extremeWing-config/device[mac=key1]/interface[name=key2]/preamble_short"
			DEFVAL { false }
			::= { extremeWingCfgDevIfRadioEntry 8 }

		
		-- 1.3.6.1.4.1.1916.2.131.50.1.3.18.3.5.1.9
		extremeWingCfgDevIfRadioGuardInterval OBJECT-TYPE
			SYNTAX DisplayString
			MAX-ACCESS read-write
			STATUS current
			DESCRIPTION
				"802.11n guard interval.
				
				Values:
				any
				long
				
				XPath: /extremeWing-config/device[mac=key1]/interface[name=key2]/guard_interval"
			DEFVAL { "any" }
			::= { extremeWingCfgDevIfRadioEntry 9 }

		
		-- 1.3.6.1.4.1.1916.2.131.50.1.3.18.3.5.1.10
		extremeWingCfgDevIfRadioAmpduMode OBJECT-TYPE
			SYNTAX DisplayString
			MAX-ACCESS read-write
			STATUS current
			DESCRIPTION
				"Mode in which A-MPDU will be supported.
				
				Values:
				tx-only
				rx-only
				tx-rx
				none
				
				XPath: /extremeWing-config/device[mac=key1]/interface[name=key2]/ampdu_mode"
			DEFVAL { "tx-rx" }
			::= { extremeWingCfgDevIfRadioEntry 10 }

		
		-- 1.3.6.1.4.1.1916.2.131.50.1.3.18.3.5.1.11
		extremeWingCfgDevIfRadioAmsduMode OBJECT-TYPE
			SYNTAX DisplayString
			MAX-ACCESS read-write
			STATUS current
			DESCRIPTION
				"Mode in which A-MSDU will be supported.
				
				Values:
				rx-only
				tx-rx
				
				XPath: /extremeWing-config/device[mac=key1]/interface[name=key2]/amsdu_mode"
			DEFVAL { "rx-only" }
			::= { extremeWingCfgDevIfRadioEntry 11 }

		
		-- 1.3.6.1.4.1.1916.2.131.50.1.3.18.3.5.1.12
		extremeWingCfgDevIfRadioRifsMode OBJECT-TYPE
			SYNTAX DisplayString
			MAX-ACCESS read-write
			STATUS current
			DESCRIPTION
				"Modes in which RIFS will be supported.
				
				Values:
				tx-only
				rx-only
				tx-rx
				none
				
				XPath: /extremeWing-config/device[mac=key1]/interface[name=key2]/rifs_mode"
			DEFVAL { "tx-rx" }
			::= { extremeWingCfgDevIfRadioEntry 12 }

		
		-- 1.3.6.1.4.1.1916.2.131.50.1.3.18.3.5.1.13
		extremeWingCfgDevIfRadioAmpduMaxAggrSizeRx OBJECT-TYPE
			SYNTAX DisplayString
			UNITS "bytes"
			MAX-ACCESS read-write
			STATUS current
			DESCRIPTION
				"Advertised maximum limit on A-MPDU aggregated received frames.
				
				Values:
				8191
				16383
				32767
				65535
				
				XPath: /extremeWing-config/device[mac=key1]/interface[name=key2]/ampdu_max_aggr_size_rx"
			DEFVAL { "65535" }
			::= { extremeWingCfgDevIfRadioEntry 13 }

		
		-- 1.3.6.1.4.1.1916.2.131.50.1.3.18.3.5.1.14
		extremeWingCfgDevIfRadioAmpduMaxAggrSizeTx OBJECT-TYPE
			SYNTAX Unsigned32 (0..65535)
			UNITS "bytes"
			MAX-ACCESS read-write
			STATUS current
			DESCRIPTION
				"Limit on A-MPDU aggregated transmitted frames.
				
				XPath: /extremeWing-config/device[mac=key1]/interface[name=key2]/ampdu_max_aggr_size_tx"
			DEFVAL { 65535 }
			::= { extremeWingCfgDevIfRadioEntry 14 }

		
		-- 1.3.6.1.4.1.1916.2.131.50.1.3.18.3.5.1.15
		extremeWingCfgDevIfRadioAmpduMinSpacing OBJECT-TYPE
			SYNTAX DisplayString
			UNITS "microseconds"
			MAX-ACCESS read-write
			STATUS current
			DESCRIPTION
				"Minimum gap between A-MPDU frames (in microseconds).
				
				Values:
				0
				1
				2
				4
				8
				16
				
				XPath: /extremeWing-config/device[mac=key1]/interface[name=key2]/ampdu_min_spacing"
			DEFVAL { "4" }
			::= { extremeWingCfgDevIfRadioEntry 15 }

		
		-- 1.3.6.1.4.1.1916.2.131.50.1.3.18.3.5.1.16
		extremeWingCfgDevIfRadioAntennaMode OBJECT-TYPE
			SYNTAX DisplayString
			MAX-ACCESS read-write
			STATUS current
			DESCRIPTION
				"Number of transmit and receive antennas on the radio. 1x1 implies only the A antenna; 1x3 implies A for Tx and all three for Rx; default depends on the AP type, the type of power (802.3af etc), etc.
				
				Values:
				1x1
				1xALL
				2x2
				default
				
				XPath: /extremeWing-config/device[mac=key1]/interface[name=key2]/antenna_mode"
			DEFVAL { "default" }
			::= { extremeWingCfgDevIfRadioEntry 16 }

		
		-- 1.3.6.1.4.1.1916.2.131.50.1.3.18.3.5.1.17
		extremeWingCfgDevIfRadioNonUnicastForwarding OBJECT-TYPE
			SYNTAX DisplayString
			MAX-ACCESS read-write
			STATUS current
			DESCRIPTION
				"Whether broadcast and multicast packets should always follow
				DTIM, or do so only if some wireless clients are in
				power-save mode.
				
				Values:
				follow-dtim
				power-save-aware
				
				XPath: /extremeWing-config/device[mac=key1]/interface[name=key2]/non_unicast_forwarding"
			DEFVAL { "follow-dtim" }
			::= { extremeWingCfgDevIfRadioEntry 17 }

		
		-- 1.3.6.1.4.1.1916.2.131.50.1.3.18.3.5.1.18
		extremeWingCfgDevIfRadioDynamicChainSelection OBJECT-TYPE
			SYNTAX TruthValue
			MAX-ACCESS read-write
			STATUS current
			DESCRIPTION
				"Whether the radio should dynamically change the number of
				transmit chains used (use a single chain/antenna for frames
				at non-11n data-rates).
				
				XPath: /extremeWing-config/device[mac=key1]/interface[name=key2]/dynamic_chain_selection"
			DEFVAL { false }
			::= { extremeWingCfgDevIfRadioEntry 18 }

		
		-- 1.3.6.1.4.1.1916.2.131.50.1.3.18.3.5.1.19
		extremeWingCfgDevIfRadioLockRfMode OBJECT-TYPE
			SYNTAX TruthValue
			MAX-ACCESS read-write
			STATUS current
			DESCRIPTION
				"Lock Smart RF mode of operation for this radio.
				
				XPath: /extremeWing-config/device[mac=key1]/interface[name=key2]/lock_rf_mode"
			DEFVAL { false }
			::= { extremeWingCfgDevIfRadioEntry 19 }

		
		-- 1.3.6.1.4.1.1916.2.131.50.1.3.18.3.5.1.20
		extremeWingCfgDevIfRadioSnifferRedirHost OBJECT-TYPE
			SYNTAX IpAddress
			MAX-ACCESS read-write
			STATUS current
			DESCRIPTION
				"Address of host to which captured packets are redirected.
				
				XPath: /extremeWing-config/device[mac=key1]/interface[name=key2]/sniffer_redirect/host"
			::= { extremeWingCfgDevIfRadioEntry 20 }

		
		-- 1.3.6.1.4.1.1916.2.131.50.1.3.18.3.5.1.21
		extremeWingCfgDevIfRadioSnifferRedirChannel OBJECT-TYPE
			SYNTAX DisplayString
			MAX-ACCESS read-write
			STATUS current
			DESCRIPTION
				"Channel on which to capture packets.
				
				Values:
				1, 1+, 2, 2+, 3, 3+, 4, 4+, 5, 5+, 5-, 6, 6+, 6-, 7, 7+, 7-,
				8, 8+, 8-, 9, 9+, 9-, 10, 10-, 11, 11-, 12, 12-, 13, 13-, 14,
				36, 36+, 40, 40-, 44, 44+, 48, 48-, 52, 52+, 56, 56-, 60, 60+,
				64, 64-, 100, 100+, 104, 104-, 108, 108+, 112, 112-, 116,
				116+, 120, 120-, 124, 124+, 128, 128-, 132, 132+, 136, 136-,
				140, 149, 149+, 153, 153-, 157, 157+, 161, 161-, 165, 34, 38,
				42, and 46
				
				XPath: /extremeWing-config/device[mac=key1]/interface[name=key2]/sniffer_redirect/channel"
			DEFVAL { "1" }
			::= { extremeWingCfgDevIfRadioEntry 21 }

		
		-- 1.3.6.1.4.1.1916.2.131.50.1.3.18.3.5.1.22
		extremeWingCfgDevIfRadioMesh OBJECT-TYPE
			SYNTAX DisplayString
			MAX-ACCESS read-write
			STATUS current
			DESCRIPTION
				"Client operation scans for Mesh Portals, or nodes that have
				connectivity to Portals, and connects through them. 
				Portal operation begins beaconing immediately and accepting
				connections from other Mesh nodes.  Generally the Portal node
				is connected to the wired network.
				
				Values:
				disabled
				portal
				client
				
				XPath: /extremeWing-config/device[mac=key1]/interface[name=key2]/mesh"
			DEFVAL { "disabled" }
			::= { extremeWingCfgDevIfRadioEntry 22 }

		
		-- 1.3.6.1.4.1.1916.2.131.50.1.3.18.3.5.1.23
		extremeWingCfgDevIfRadioMeshLinks OBJECT-TYPE
			SYNTAX Unsigned32 (1..6)
			MAX-ACCESS read-write
			STATUS current
			DESCRIPTION
				"Maximum number of Mesh links that this radio will attempt to
				create.
				
				XPath: /extremeWing-config/device[mac=key1]/interface[name=key2]/mesh_links"
			DEFVAL { 3 }
			::= { extremeWingCfgDevIfRadioEntry 23 }

		
		-- 1.3.6.1.4.1.1916.2.131.50.1.3.18.3.5.1.24
		extremeWingCfgDevIfRadioProbeResponseRetry OBJECT-TYPE
			SYNTAX TruthValue
			MAX-ACCESS read-write
			STATUS current
			DESCRIPTION
				"Whether Probe-Responses are retried on the air if they are
				not acknowledged by the wireless client
				
				XPath: /extremeWing-config/device[mac=key1]/interface[name=key2]/probe_response_retry"
			DEFVAL { true }
			::= { extremeWingCfgDevIfRadioEntry 24 }

		
		-- 1.3.6.1.4.1.1916.2.131.50.1.3.18.3.5.1.25
		extremeWingCfgDevIfRadioProbeResponseRate OBJECT-TYPE
			SYNTAX DisplayString
			MAX-ACCESS read-write
			STATUS current
			DESCRIPTION
				"The data transmission rate used for sending Probe Responses
				
				Values:
				follow-probe-request
				highest-basic
				lowest-basic
				
				XPath: /extremeWing-config/device[mac=key1]/interface[name=key2]/probe_response_rate"
			DEFVAL { "follow-probe-request" }
			::= { extremeWingCfgDevIfRadioEntry 25 }

		
		-- 1.3.6.1.4.1.1916.2.131.50.1.3.18.3.5.1.26
		extremeWingCfgDevIfRadioMaxClients OBJECT-TYPE
			SYNTAX Unsigned32 (0..256)
			MAX-ACCESS read-write
			STATUS current
			DESCRIPTION
				"The maximum number of clients allowed to associate
				with this radio
				
				XPath: /extremeWing-config/device[mac=key1]/interface[name=key2]/max_clients"
			DEFVAL { 256 }
			::= { extremeWingCfgDevIfRadioEntry 26 }

		
		-- 1.3.6.1.4.1.1916.2.131.50.1.3.18.3.5.1.27
		extremeWingCfgDevIfRadioRadioTapMode OBJECT-TYPE
			SYNTAX DisplayString
			MAX-ACCESS read-write
			STATUS current
			DESCRIPTION
				"Radio tap mode of operation
				
				Values:
				off
				inline
				promiscuous
				
				Note:
				Radio tap can be enabled only on wlan radio and in 5.1,
				only when another radio on AP is sensor.
				
				XPath: /extremeWing-config/device[mac=key1]/interface[name=key2]/radio_tap_mode"
			DEFVAL { "off" }
			::= { extremeWingCfgDevIfRadioEntry 27 }

		
		-- 1.3.6.1.4.1.1916.2.131.50.1.3.18.3.5.1.28
		extremeWingCfgDevIfRadioWirelessClientPower OBJECT-TYPE
			SYNTAX Unsigned32 (0..20)
			UNITS "dBm"
			MAX-ACCESS read-write
			STATUS current
			DESCRIPTION
				"Transmit power indicated to wireless clients for transmission.
				
				XPath: /extremeWing-config/device[mac=key1]/interface[name=key2]/wireless_client_power"
			::= { extremeWingCfgDevIfRadioEntry 28 }

		
		-- 1.3.6.1.4.1.1916.2.131.50.1.3.18.3.5.1.29
		extremeWingCfgDevIfRadioLoadBalLfCount OBJECT-TYPE
			SYNTAX Unsigned32 (0..10)
			MAX-ACCESS read-write
			STATUS current
			DESCRIPTION
				"Consider the number of Wireless Clients in determining
				the load on an AP.  High numbers indicate a higher weight
				assigned to the criteria. 0 implies that count is
				not considered.
				
				XPath: /extremeWing-config/device[mac=key1]/interface[name=key2]/load_balance_lf_count"
			DEFVAL { 10 }
			::= { extremeWingCfgDevIfRadioEntry 29 }

		
		-- 1.3.6.1.4.1.1916.2.131.50.1.3.18.3.5.1.30
		extremeWingCfgDevIfRadioLoadBalLfThroughput OBJECT-TYPE
			SYNTAX Unsigned32 (0..10)
			MAX-ACCESS read-write
			STATUS current
			DESCRIPTION
				"Consider the throughput of traffic in determining the load
				on an AP.  High numbers indicate a higher weight assigned
				to the criteria.  0 implies that throughput is not considered.
				
				XPath: /extremeWing-config/device[mac=key1]/interface[name=key2]/load_balance_lf_throughput"
			DEFVAL { 0 }
			::= { extremeWingCfgDevIfRadioEntry 30 }

		
		-- 1.3.6.1.4.1.1916.2.131.50.1.3.18.3.5.1.31
		extremeWingCfgDevIfRadioLoadBalWmCount OBJECT-TYPE
			SYNTAX Unsigned32 (1..255)
			MAX-ACCESS read-write
			STATUS current
			DESCRIPTION
				"The number of clients that can associate with a radio before
				load-balancing would be triggered
				
				XPath: /extremeWing-config/device[mac=key1]/interface[name=key2]/load_balance_wm_count"
			DEFVAL { 10 }
			::= { extremeWingCfgDevIfRadioEntry 31 }

		
		-- 1.3.6.1.4.1.1916.2.131.50.1.3.18.3.5.1.32
		extremeWingCfgDevIfRadioLoadBalWmTput OBJECT-TYPE
			SYNTAX Unsigned32 (1..1000)
			MAX-ACCESS read-write
			STATUS current
			DESCRIPTION
				"When the average throughput of a radio exceeds this threshold
				(in Mbps) load balancing would be triggered
				
				XPath: /extremeWing-config/device[mac=key1]/interface[name=key2]/load_balance_wm_tput_mbps"
			DEFVAL { 10 }
			::= { extremeWingCfgDevIfRadioEntry 32 }

		
		-- 1.3.6.1.4.1.1916.2.131.50.1.3.18.3.5.1.33
		extremeWingCfgDevIfRadioAssocAcl OBJECT-TYPE
			SYNTAX ExtremeWingIdentifier
			MAX-ACCESS read-write
			STATUS current
			DESCRIPTION
				"
				
				XPath: /extremeWing-config/device[mac=key1]/interface[name=key2]/assoc_acl"
			::= { extremeWingCfgDevIfRadioEntry 33 }

		
		-- 1.3.6.1.4.1.1916.2.131.50.1.3.18.3.5.1.34
		extremeWingCfgDevIfRadioQosPolicy OBJECT-TYPE
			SYNTAX ExtremeWingIdentifier
			MAX-ACCESS read-write
			STATUS current
			DESCRIPTION
				"
				
				XPath: /extremeWing-config/device[mac=key1]/interface[name=key2]/qos_policy"
			::= { extremeWingCfgDevIfRadioEntry 34 }

                -- 1.3.6.1.4.1.1916.2.131.50.1.3.18.3.5.1.35
                extremeWingCfgDevIfRadioAntennaDowntilt OBJECT-TYPE
                        SYNTAX TruthValue
                        MAX-ACCESS read-write
                        STATUS current
                        DESCRIPTION
                                "Whether the radio should enable ADEPT antenna modes.
 
                                XPath: /extremeWing-config/device[mac=key1]/interface[name=key2]/antenna_downtilt"
                        DEFVAL { false }
                        ::= { extremeWingCfgDevIfRadioEntry 35 }
 
 
                -- 1.3.6.1.4.1.1916.2.131.50.1.3.18.3.5.1.36
                extremeWingCfgDevIfRadioExtendedRange OBJECT-TYPE
                        SYNTAX Unsigned32
                        MAX-ACCESS read-write
                        STATUS current
                        DESCRIPTION
                                "Configure extended rate selection.

				Default Value
                                for 2.4 Ghz : 7 Kilometer
                                    5 GHz   : 2 Kilometer
                                XPath: /extremeWing-config/device[mac=key1]/interface[name=key2]/extended_range"
                        DEFVAL { "kilometer" }
                        ::= { extremeWingCfgDevIfRadioEntry 36 }

                -- 1.3.6.1.4.1.1916.2.131.50.1.3.18.3.5.1.37
                extremeWingCfgDevIfRadioOperMode OBJECT-TYPE
                        SYNTAX Integer32
                        MAX-ACCESS read-write
                        STATUS current
                        DESCRIPTION
                                "
                                Following is the list of operation modes for the radio:

                                bit position  meaning
                                ============  =======
                                1             dot11a
                                2             dot11b
                                4             dot11g
                                6             dot11bg
                                8             dot11n(for a-radio)
                                9             dot11an
                                16            dot11n(for g-radio)
                                20            dot11gn
                                22            dot11bgn

                                XPath: /extremeWing-config/device[mac=key1]/interface[name=key2]/oper_mode
                                "
                        ::= { extremeWingCfgDevIfRadioEntry 37 }
		
		-- 1.3.6.1.4.1.1916.2.131.50.1.3.18.3.6
		extremeWingCfgDevIfRadioBssmapTable OBJECT-TYPE
			SYNTAX SEQUENCE OF ExtremeWingCfgDevIfRadioBssmapEntry
			MAX-ACCESS not-accessible
			STATUS current
			DESCRIPTION
				"
				
				/extremeWing-config/device/interface/wlanbssmap"
			::= { extremeWingCfgDevIf 6 }

		
		-- 1.3.6.1.4.1.1916.2.131.50.1.3.18.3.6.1
		extremeWingCfgDevIfRadioBssmapEntry OBJECT-TYPE
			SYNTAX ExtremeWingCfgDevIfRadioBssmapEntry
			MAX-ACCESS not-accessible
			STATUS current
			DESCRIPTION
				"An entry in the table."
			INDEX { extremeWingCfgDevMac, extremeWingCfgDevIfName, extremeWingCfgDevIfRadioBssmapWlan }
			::= { extremeWingCfgDevIfRadioBssmapTable 1 }

		
		ExtremeWingCfgDevIfRadioBssmapEntry ::=
			SEQUENCE { 
				extremeWingCfgDevIfRadioBssmapWlan
					ExtremeWingIdentifier,
				extremeWingCfgDevIfRadioBssmapBss
					Unsigned32,
				extremeWingCfgDevIfRadioBssmapPrimary
					TruthValue
			 }

		-- 1.3.6.1.4.1.1916.2.131.50.1.3.18.3.6.1.1
		extremeWingCfgDevIfRadioBssmapWlan OBJECT-TYPE
			SYNTAX ExtremeWingIdentifier
			MAX-ACCESS read-only
			STATUS current
			DESCRIPTION
				"
				
				XPath: /extremeWing-config/device[mac=key1]/interface[name=key2]/wlanbssmap[wlan=key3]/wlan"
			::= { extremeWingCfgDevIfRadioBssmapEntry 1 }

		
		-- 1.3.6.1.4.1.1916.2.131.50.1.3.18.3.6.1.3
		extremeWingCfgDevIfRadioBssmapBss OBJECT-TYPE
			SYNTAX Unsigned32 (1..8)
			MAX-ACCESS read-write
			STATUS current
			DESCRIPTION
				"
				
				XPath: /extremeWing-config/device[mac=key1]/interface[name=key2]/wlanbssmap[wlan=key3]/bss"
			::= { extremeWingCfgDevIfRadioBssmapEntry 3 }

		
		-- 1.3.6.1.4.1.1916.2.131.50.1.3.18.3.6.1.4
		extremeWingCfgDevIfRadioBssmapPrimary OBJECT-TYPE
			SYNTAX TruthValue
			MAX-ACCESS read-write
			STATUS current
			DESCRIPTION
				"
				
				XPath: /extremeWing-config/device[mac=key1]/interface[name=key2]/wlanbssmap[wlan=key3]/primary"
			::= { extremeWingCfgDevIfRadioBssmapEntry 4 }

		
		-- 1.3.6.1.4.1.1916.2.131.50.1.3.18.3.8
		extremeWingCfgDevIfSpanTreeTable OBJECT-TYPE
			SYNTAX SEQUENCE OF ExtremeWingCfgDevIfSpanTreeEntry
			MAX-ACCESS not-accessible
			STATUS current
			DESCRIPTION
				"Interface Spanning Tree configuration
				
				/extremeWing-config/device/interface/spanningtree"
			::= { extremeWingCfgDevIf 8 }

		
		-- 1.3.6.1.4.1.1916.2.131.50.1.3.18.3.8.1
		extremeWingCfgDevIfSpanTreeEntry OBJECT-TYPE
			SYNTAX ExtremeWingCfgDevIfSpanTreeEntry
			MAX-ACCESS not-accessible
			STATUS current
			DESCRIPTION
				"An entry in the table."
			INDEX { extremeWingCfgDevMac, extremeWingCfgDevIfName }
			::= { extremeWingCfgDevIfSpanTreeTable 1 }

		
		ExtremeWingCfgDevIfSpanTreeEntry ::=
			SEQUENCE { 
				extremeWingCfgDevIfSpanTreeLinkType
					DisplayString,
				extremeWingCfgDevIfSpanTreePortfast
					TruthValue,
				extremeWingCfgDevIfSpanTreeEdgeport
					TruthValue,
				extremeWingCfgDevIfSpanTreeBpduguard
					DisplayString,
				extremeWingCfgDevIfSpanTreeBpdufilter
					DisplayString,
				extremeWingCfgDevIfSpanTreePortCiscoInterop
					DisplayString,
				extremeWingCfgDevIfSpanTreeForceVersion
					Unsigned32,
				extremeWingCfgDevIfSpanTreeGuard
					DisplayString
			 }

		-- 1.3.6.1.4.1.1916.2.131.50.1.3.18.3.8.1.1
		extremeWingCfgDevIfSpanTreeLinkType OBJECT-TYPE
			SYNTAX DisplayString
			MAX-ACCESS read-write
			STATUS current
			DESCRIPTION
				"Point-to-point enables rapid transition.  Shared disables
				rapid transition.
				
				Values:
				point-to-point
				shared
				
				XPath: /extremeWing-config/device[mac=key1]/interface[name=key2]/spanningtree/link_type"
			DEFVAL { "point-to-point" }
			::= { extremeWingCfgDevIfSpanTreeEntry 1 }

		
		-- 1.3.6.1.4.1.1916.2.131.50.1.3.18.3.8.1.2
		extremeWingCfgDevIfSpanTreePortfast OBJECT-TYPE
			SYNTAX TruthValue
			MAX-ACCESS read-write
			STATUS current
			DESCRIPTION
				"Enable fast transitions.
				
				XPath: /extremeWing-config/device[mac=key1]/interface[name=key2]/spanningtree/portfast"
			DEFVAL { false }
			::= { extremeWingCfgDevIfSpanTreeEntry 2 }

		
		-- 1.3.6.1.4.1.1916.2.131.50.1.3.18.3.8.1.3
		extremeWingCfgDevIfSpanTreeEdgeport OBJECT-TYPE
			SYNTAX TruthValue
			MAX-ACCESS read-write
			STATUS current
			DESCRIPTION
				"Enable the port as an edge port.
				
				XPath: /extremeWing-config/device[mac=key1]/interface[name=key2]/spanningtree/edgeport"
			DEFVAL { false }
			::= { extremeWingCfgDevIfSpanTreeEntry 3 }

		
		-- 1.3.6.1.4.1.1916.2.131.50.1.3.18.3.8.1.4
		extremeWingCfgDevIfSpanTreeBpduguard OBJECT-TYPE
			SYNTAX DisplayString
			MAX-ACCESS read-write
			STATUS current
			DESCRIPTION
				"Guard the port against reception of BPDUs.
				
				Values:
				none
				enable
				disable
				
				XPath: /extremeWing-config/device[mac=key1]/interface[name=key2]/spanningtree/bpduguard"
			DEFVAL { "none" }
			::= { extremeWingCfgDevIfSpanTreeEntry 4 }

		
		-- 1.3.6.1.4.1.1916.2.131.50.1.3.18.3.8.1.5
		extremeWingCfgDevIfSpanTreeBpdufilter OBJECT-TYPE
			SYNTAX DisplayString
			MAX-ACCESS read-write
			STATUS current
			DESCRIPTION
				"Set the PortFast BPDU filter for the port.  Enabling the BPDU
				filter ensures that PortFast enabled ports do not transmit or
				receive BPDUs.
				
				Values:
				none
				enable
				disable
				
				XPath: /extremeWing-config/device[mac=key1]/interface[name=key2]/spanningtree/bpdufilter"
			DEFVAL { "none" }
			::= { extremeWingCfgDevIfSpanTreeEntry 5 }

		
		-- 1.3.6.1.4.1.1916.2.131.50.1.3.18.3.8.1.6
		extremeWingCfgDevIfSpanTreePortCiscoInterop OBJECT-TYPE
			SYNTAX DisplayString
			MAX-ACCESS read-write
			STATUS current
			DESCRIPTION
				"Enable interoperability with Cisco's version of MSTP,
				which is incompatible with standard MSTP.
				
				Values:
				enable
				disable
				
				XPath: /extremeWing-config/device[mac=key1]/interface[name=key2]/spanningtree/port_cisco_interop"
			DEFVAL { "disable" }
			::= { extremeWingCfgDevIfSpanTreeEntry 6 }

		
		-- 1.3.6.1.4.1.1916.2.131.50.1.3.18.3.8.1.7
		extremeWingCfgDevIfSpanTreeForceVersion OBJECT-TYPE
			SYNTAX Unsigned32 (0..3)
			MAX-ACCESS read-write
			STATUS current
			DESCRIPTION
				"Version identifier where 0=STP, 1=Not Supported, 2=RSTP,
				3=MSTP.
				
				XPath: /extremeWing-config/device[mac=key1]/interface[name=key2]/spanningtree/force_version"
			DEFVAL { 3 }
			::= { extremeWingCfgDevIfSpanTreeEntry 7 }

		
		-- 1.3.6.1.4.1.1916.2.131.50.1.3.18.3.8.1.8
		extremeWingCfgDevIfSpanTreeGuard OBJECT-TYPE
			SYNTAX DisplayString
			MAX-ACCESS read-write
			STATUS current
			DESCRIPTION
				"Setting 'root' disables reception of superior BPDUs.
				
				Values:
				none
				root
				
				XPath: /extremeWing-config/device[mac=key1]/interface[name=key2]/spanningtree/guard"
			DEFVAL { "none" }
			::= { extremeWingCfgDevIfSpanTreeEntry 8 }

		
		-- 1.3.6.1.4.1.1916.2.131.50.1.3.18.3.11
		extremeWingCfgDevIfVlanOspfTable OBJECT-TYPE
			SYNTAX SEQUENCE OF ExtremeWingCfgDevIfVlanOspfEntry
			MAX-ACCESS not-accessible
			STATUS current
			DESCRIPTION
				"
				
				/extremeWing-config/device/interface"
			::= { extremeWingCfgDevIf 11 }

		
		-- 1.3.6.1.4.1.1916.2.131.50.1.3.18.3.11.1
		extremeWingCfgDevIfVlanOspfEntry OBJECT-TYPE
			SYNTAX ExtremeWingCfgDevIfVlanOspfEntry
			MAX-ACCESS not-accessible
			STATUS current
			DESCRIPTION
				"An entry in the table."
			INDEX { extremeWingCfgDevMac, extremeWingCfgDevIfName }
			::= { extremeWingCfgDevIfVlanOspfTable 1 }

		
		ExtremeWingCfgDevIfVlanOspfEntry ::=
			SEQUENCE { 
				extremeWingCfgDevIfVlanOspfOspfAuthentication
					DisplayString,
				extremeWingCfgDevIfVlanOspfOspfAuthKey
					DisplayString,
				extremeWingCfgDevIfVlanOspfOspfPriority
					Unsigned32,
				extremeWingCfgDevIfVlanOspfOspfCost
					Unsigned32,
				extremeWingCfgDevIfVlanOspfOspfBandWidth
					Unsigned32
			 }

		-- 1.3.6.1.4.1.1916.2.131.50.1.3.18.3.11.1.1
		extremeWingCfgDevIfVlanOspfOspfAuthentication OBJECT-TYPE
			SYNTAX DisplayString
			MAX-ACCESS read-write
			STATUS current
			DESCRIPTION
				"OSPF authentication type
				
				Values:
				simple-password,
				message-digest,
				none
				
				XPath: /extremeWing-config/device[mac=key1]/interface[name=key2]/ospf_authentication"
			DEFVAL { "none" }
			::= { extremeWingCfgDevIfVlanOspfEntry 1 }

		
		-- 1.3.6.1.4.1.1916.2.131.50.1.3.18.3.11.1.2
		extremeWingCfgDevIfVlanOspfOspfAuthKey OBJECT-TYPE
			SYNTAX DisplayString (SIZE (1..8))
			MAX-ACCESS read-write
			STATUS current
			DESCRIPTION
				"Simple auth key for OSPF.
				 Max 8 characters are accepted for the key.

				XPath: /extremeWing-config/device[mac=key1]/interface[name=key2]/ospf_auth_key"
			::= { extremeWingCfgDevIfVlanOspfEntry 2 }


		
		-- 1.3.6.1.4.1.1916.2.131.50.1.3.18.3.11.1.3
		extremeWingCfgDevIfVlanOspfOspfPriority OBJECT-TYPE
			SYNTAX Unsigned32 (0..255)
			MAX-ACCESS read-write
			STATUS current
			DESCRIPTION
				"OSPF priority used in DR election
				
				XPath: /extremeWing-config/device[mac=key1]/interface[name=key2]/ospf_priority"
			DEFVAL { 0 }
			::= { extremeWingCfgDevIfVlanOspfEntry 3 }

		
		-- 1.3.6.1.4.1.1916.2.131.50.1.3.18.3.11.1.4
		extremeWingCfgDevIfVlanOspfOspfCost OBJECT-TYPE
			SYNTAX Unsigned32 (1..65535)
			MAX-ACCESS read-write
			STATUS current
			DESCRIPTION
				"Cost of this OSPF interface
				
				XPath: /extremeWing-config/device[mac=key1]/interface[name=key2]/ospf_cost"
			DEFVAL { 10 }
			::= { extremeWingCfgDevIfVlanOspfEntry 4 }

		
		-- 1.3.6.1.4.1.1916.2.131.50.1.3.18.3.11.1.5
		extremeWingCfgDevIfVlanOspfOspfBandWidth OBJECT-TYPE
			SYNTAX Unsigned32 (1..10000000)
			MAX-ACCESS read-write
			STATUS current
			DESCRIPTION
				"Bandwidth of the interface in Kbps.
				
				XPath: /extremeWing-config/device[mac=key1]/interface[name=key2]/bandwidth"
			::= { extremeWingCfgDevIfVlanOspfEntry 5 }

		
		-- 1.3.6.1.4.1.1916.2.131.50.1.3.18.3.12
		extremeWingCfgDevIfVlanOspfMsgDigestTable OBJECT-TYPE
			SYNTAX SEQUENCE OF ExtremeWingCfgDevIfVlanOspfMsgDigestEntry
			MAX-ACCESS not-accessible
			STATUS current
			DESCRIPTION
				"
				
				/extremeWing-config/device/interface/ospf_message_digest_key"
			::= { extremeWingCfgDevIf 12 }

		
		-- 1.3.6.1.4.1.1916.2.131.50.1.3.18.3.12.1
		extremeWingCfgDevIfVlanOspfMsgDigestEntry OBJECT-TYPE
			SYNTAX ExtremeWingCfgDevIfVlanOspfMsgDigestEntry
			MAX-ACCESS not-accessible
			STATUS current
			DESCRIPTION
				"An entry in the table."
			INDEX { extremeWingCfgDevMac, extremeWingCfgDevIfName, extremeWingCfgDevIfVlanOspfMsgDigestKeyId }
			::= { extremeWingCfgDevIfVlanOspfMsgDigestTable 1 }

		
		ExtremeWingCfgDevIfVlanOspfMsgDigestEntry ::=
			SEQUENCE { 
				extremeWingCfgDevIfVlanOspfMsgDigestKeyId
					Unsigned32,
				extremeWingCfgDevIfVlanOspfMsgDigestMessageDigest
					DisplayString
			 }

		-- 1.3.6.1.4.1.1916.2.131.50.1.3.18.3.12.1.1
		extremeWingCfgDevIfVlanOspfMsgDigestKeyId OBJECT-TYPE
			SYNTAX Unsigned32 (1..255)
			MAX-ACCESS read-only
			STATUS current
			DESCRIPTION
				"OSPF message digest auth key ID.
				
				XPath: /extremeWing-config/device[mac=key1]/interface[name=key2]/ospf_message_digest_key[key_id=key3]/key_id"
			::= { extremeWingCfgDevIfVlanOspfMsgDigestEntry 1 }

		
		-- 1.3.6.1.4.1.1916.2.131.50.1.3.18.3.12.1.3
		extremeWingCfgDevIfVlanOspfMsgDigestMessageDigest OBJECT-TYPE
			SYNTAX DisplayString
			MAX-ACCESS read-write
			STATUS current
			DESCRIPTION
				"OSPF message digest key.
				
				XPath: /extremeWing-config/device[mac=key1]/interface[name=key2]/ospf_message_digest_key[key_id=key3]/message_digest"
			::= { extremeWingCfgDevIfVlanOspfMsgDigestEntry 3 }

		
		-- 1.3.6.1.4.1.1916.2.131.50.1.3.18.3.13
		extremeWingCfgDevIfPppoeTable OBJECT-TYPE
			SYNTAX SEQUENCE OF ExtremeWingCfgDevIfPppoeEntry
			MAX-ACCESS not-accessible
			STATUS current
			DESCRIPTION
				"
				
				/extremeWing-config/device/interface"
			::= { extremeWingCfgDevIf 13 }

		
		-- 1.3.6.1.4.1.1916.2.131.50.1.3.18.3.13.1
		extremeWingCfgDevIfPppoeEntry OBJECT-TYPE
			SYNTAX ExtremeWingCfgDevIfPppoeEntry
			MAX-ACCESS not-accessible
			STATUS current
			DESCRIPTION
				"An entry in the table."
			INDEX { extremeWingCfgDevMac, extremeWingCfgDevIfName }
			::= { extremeWingCfgDevIfPppoeTable 1 }

		
		ExtremeWingCfgDevIfPppoeEntry ::=
			SEQUENCE { 
				extremeWingCfgDevIfPppoeAuthType
					DisplayString,
				extremeWingCfgDevIfPppoeIdleTime
					Unsigned32,
				extremeWingCfgDevIfPppoeKeepalive
					TruthValue,
				extremeWingCfgDevIfPppoeUsername
					DisplayString,
				extremeWingCfgDevIfPppoePassword
					DisplayString,
				extremeWingCfgDevIfPppoeService
					DisplayString,
				extremeWingCfgDevIfPppoeLocalnetVlan
					Unsigned32,
				extremeWingCfgDevIfPppoeMtu
					Unsigned32,
				extremeWingCfgDevIfPppoeDefaultRoutePriority
					Unsigned32,
				extremeWingCfgDevIfPppoeIp
					DisplayString
			 }

		-- 1.3.6.1.4.1.1916.2.131.50.1.3.18.3.13.1.1
		extremeWingCfgDevIfPppoeAuthType OBJECT-TYPE
			SYNTAX DisplayString
			MAX-ACCESS read-write
			STATUS current
			DESCRIPTION
				"PPPoE Client authentication type.
				
				Values:
				none,
				chap,
				mschap,
				mschap-v2,
				pap
				
				XPath: /extremeWing-config/device[mac=key1]/interface[name=key2]/auth-type"
			DEFVAL { "pap" }
			::= { extremeWingCfgDevIfPppoeEntry 1 }

		
		-- 1.3.6.1.4.1.1916.2.131.50.1.3.18.3.13.1.2
		extremeWingCfgDevIfPppoeIdleTime OBJECT-TYPE
			SYNTAX Unsigned32 (1..65535)
			UNITS "seconds"
			MAX-ACCESS read-write
			STATUS current
			DESCRIPTION
				"PPPoE client Idle Timeout.
				
				XPath: /extremeWing-config/device[mac=key1]/interface[name=key2]/idle-time"
			DEFVAL { 600 }
			::= { extremeWingCfgDevIfPppoeEntry 2 }

		
		-- 1.3.6.1.4.1.1916.2.131.50.1.3.18.3.13.1.3
		extremeWingCfgDevIfPppoeKeepalive OBJECT-TYPE
			SYNTAX TruthValue
			MAX-ACCESS read-write
			STATUS current
			DESCRIPTION
				"PPPoE client keep-alive mode.
				
				XPath: /extremeWing-config/device[mac=key1]/interface[name=key2]/keepalive"
			DEFVAL { false }
			::= { extremeWingCfgDevIfPppoeEntry 3 }

		
		-- 1.3.6.1.4.1.1916.2.131.50.1.3.18.3.13.1.4
		extremeWingCfgDevIfPppoeUsername OBJECT-TYPE
			SYNTAX DisplayString (SIZE (0..64))
			MAX-ACCESS read-write
			STATUS current
			DESCRIPTION
				"PPPoE client username.
				
				XPath: /extremeWing-config/device[mac=key1]/interface[name=key2]/username"
			DEFVAL { "" }
			::= { extremeWingCfgDevIfPppoeEntry 4 }

		
		-- 1.3.6.1.4.1.1916.2.131.50.1.3.18.3.13.1.5
		extremeWingCfgDevIfPppoePassword OBJECT-TYPE
			SYNTAX DisplayString (SIZE (0..64))
			MAX-ACCESS read-write
			STATUS current
			DESCRIPTION
				"PPPoE client password.
				
				XPath: /extremeWing-config/device[mac=key1]/interface[name=key2]/password"
			DEFVAL { "" }
			::= { extremeWingCfgDevIfPppoeEntry 5 }

		
		-- 1.3.6.1.4.1.1916.2.131.50.1.3.18.3.13.1.6
		extremeWingCfgDevIfPppoeService OBJECT-TYPE
			SYNTAX DisplayString (SIZE (0..128))
			MAX-ACCESS read-write
			STATUS current
			DESCRIPTION
				"PPPoE client service-name.
				
				XPath: /extremeWing-config/device[mac=key1]/interface[name=key2]/service"
			DEFVAL { "" }
			::= { extremeWingCfgDevIfPppoeEntry 6 }

		
		-- 1.3.6.1.4.1.1916.2.131.50.1.3.18.3.13.1.7
		extremeWingCfgDevIfPppoeLocalnetVlan OBJECT-TYPE
			SYNTAX Unsigned32 (1..4094)
			MAX-ACCESS read-write
			STATUS current
			DESCRIPTION
				"PPPoE client local network(vlan) connected to DSL modem.
				
				XPath: /extremeWing-config/device[mac=key1]/interface[name=key2]/localnet_vlan"
			DEFVAL { 1 }
			::= { extremeWingCfgDevIfPppoeEntry 7 }

		
		-- 1.3.6.1.4.1.1916.2.131.50.1.3.18.3.13.1.8
		extremeWingCfgDevIfPppoeMtu OBJECT-TYPE
			SYNTAX Unsigned32 (500..1492)
			MAX-ACCESS read-write
			STATUS current
			DESCRIPTION
				"PPPoE client Maximum Transmission Unit(MTU).
				
				XPath: /extremeWing-config/device[mac=key1]/interface[name=key2]/mtu"
			DEFVAL { 1492 }
			::= { extremeWingCfgDevIfPppoeEntry 8 }

		
		-- 1.3.6.1.4.1.1916.2.131.50.1.3.18.3.13.1.9
		extremeWingCfgDevIfPppoeDefaultRoutePriority OBJECT-TYPE
			SYNTAX Unsigned32 (1..8000)
			MAX-ACCESS read-write
			STATUS current
			DESCRIPTION
				"Priority for the default route learnt via PPPoE
				
				XPath: /extremeWing-config/device[mac=key1]/interface[name=key2]/pppoe_default_route_priority"
			DEFVAL { 2000 }
			::= { extremeWingCfgDevIfPppoeEntry 9 }

		
		-- 1.3.6.1.4.1.1916.2.131.50.1.3.18.3.13.1.10
		extremeWingCfgDevIfPppoeIp OBJECT-TYPE
			SYNTAX DisplayString
			MAX-ACCESS read-write
			STATUS current
			DESCRIPTION
				"PPPoE client IP address.
				
				XPath: /extremeWing-config/device[mac=key1]/interface[name=key2]/ip"
			DEFVAL { "0.0.0.0" }
			::= { extremeWingCfgDevIfPppoeEntry 10 }

		
		-- 1.3.6.1.4.1.1916.2.131.50.1.3.18.3.14
		extremeWingCfgDevIfT1E1Table OBJECT-TYPE
			SYNTAX SEQUENCE OF ExtremeWingCfgDevIfT1E1Entry
			MAX-ACCESS not-accessible
			STATUS current
			DESCRIPTION
				"T1 or E1 interface (switched interface) configuration.
				
				/extremeWing-config/device/interface"
			::= { extremeWingCfgDevIf 14 }

		
		-- 1.3.6.1.4.1.1916.2.131.50.1.3.18.3.14.1
		extremeWingCfgDevIfT1E1Entry OBJECT-TYPE
			SYNTAX ExtremeWingCfgDevIfT1E1Entry
			MAX-ACCESS not-accessible
			STATUS current
			DESCRIPTION
				"An entry in the table."
			INDEX { extremeWingCfgDevMac, extremeWingCfgDevIfName }
			::= { extremeWingCfgDevIfT1E1Table 1 }

		
		ExtremeWingCfgDevIfT1E1Entry ::=
			SEQUENCE { 
				extremeWingCfgDevIfT1E1Media
					DisplayString,
				extremeWingCfgDevIfT1E1ClockMode
					DisplayString,
				extremeWingCfgDevIfT1E1HighImpedance
					DisplayString,
				extremeWingCfgDevIfT1E1LineBuildOut
					DisplayString,
				extremeWingCfgDevIfT1E1LineEncoding
					DisplayString,
				extremeWingCfgDevIfT1E1RxSensitivityLevel
					DisplayString
			 }

		-- 1.3.6.1.4.1.1916.2.131.50.1.3.18.3.14.1.1
		extremeWingCfgDevIfT1E1Media OBJECT-TYPE
			SYNTAX DisplayString
			MAX-ACCESS read-write
			STATUS current
			DESCRIPTION
				"The media type for the physical interface
				
				Values:
				t1
				e1
				
				XPath: /extremeWing-config/device[mac=key1]/interface[name=key2]/media"
			DEFVAL { "t1" }
			::= { extremeWingCfgDevIfT1E1Entry 1 }

		
		-- 1.3.6.1.4.1.1916.2.131.50.1.3.18.3.14.1.2
		extremeWingCfgDevIfT1E1ClockMode OBJECT-TYPE
			SYNTAX DisplayString
			MAX-ACCESS read-write
			STATUS current
			DESCRIPTION
				"The mode for the clock
				
				Values:
				normal
				master
				
				XPath: /extremeWing-config/device[mac=key1]/interface[name=key2]/clock_mode"
			DEFVAL { "normal" }
			::= { extremeWingCfgDevIfT1E1Entry 2 }

		
		-- 1.3.6.1.4.1.1916.2.131.50.1.3.18.3.14.1.3
		extremeWingCfgDevIfT1E1HighImpedance OBJECT-TYPE
			SYNTAX DisplayString
			MAX-ACCESS read-write
			STATUS current
			DESCRIPTION
				"High impedance mode
				
				Values:
				disable
				enable
				
				XPath: /extremeWing-config/device[mac=key1]/interface[name=key2]/high_impedance"
			DEFVAL { "disable" }
			::= { extremeWingCfgDevIfT1E1Entry 3 }

		
		-- 1.3.6.1.4.1.1916.2.131.50.1.3.18.3.14.1.4
		extremeWingCfgDevIfT1E1LineBuildOut OBJECT-TYPE
			SYNTAX DisplayString
			MAX-ACCESS read-write
			STATUS current
			DESCRIPTION
				"Line build out in decibels (dB) or feet (ft)
				
				Values:
				0-110ft
				0dB
				110-220ft
				15dB
				22.5dB
				220-330ft
				330-440ft
				440-550ft
				550-660ft
				7.5dB
				
				XPath: /extremeWing-config/device[mac=key1]/interface[name=key2]/line_build_out"
			DEFVAL { "0dB" }
			::= { extremeWingCfgDevIfT1E1Entry 4 }

		
		-- 1.3.6.1.4.1.1916.2.131.50.1.3.18.3.14.1.5
		extremeWingCfgDevIfT1E1LineEncoding OBJECT-TYPE
			SYNTAX DisplayString
			MAX-ACCESS read-write
			STATUS current
			DESCRIPTION
				"Line encoding type
				
				Values:
				ami
				b8zs
				
				XPath: /extremeWing-config/device[mac=key1]/interface[name=key2]/line_encoding"
			DEFVAL { "b8zs" }
			::= { extremeWingCfgDevIfT1E1Entry 5 }

		
		-- 1.3.6.1.4.1.1916.2.131.50.1.3.18.3.14.1.6
		extremeWingCfgDevIfT1E1RxSensitivityLevel OBJECT-TYPE
			SYNTAX DisplayString
			MAX-ACCESS read-write
			STATUS current
			DESCRIPTION
				"Receive sensitivity level in decibels
				
				Values:
				12dB
				18dB
				30dB
				36dB
				
				XPath: /extremeWing-config/device[mac=key1]/interface[name=key2]/rx_sensitivity_level"
			DEFVAL { "36dB" }
			::= { extremeWingCfgDevIfT1E1Entry 6 }

		
		-- 1.3.6.1.4.1.1916.2.131.50.1.3.18.3.15
		extremeWingCfgDevIfSerialTable OBJECT-TYPE
			SYNTAX SEQUENCE OF ExtremeWingCfgDevIfSerialEntry
			MAX-ACCESS not-accessible
			STATUS current
			DESCRIPTION
				"Serial interface (virtual interface) configuration.
				
				/extremeWing-config/device/interface"
			::= { extremeWingCfgDevIf 15 }

		
		-- 1.3.6.1.4.1.1916.2.131.50.1.3.18.3.15.1
		extremeWingCfgDevIfSerialEntry OBJECT-TYPE
			SYNTAX ExtremeWingCfgDevIfSerialEntry
			MAX-ACCESS not-accessible
			STATUS current
			DESCRIPTION
				"An entry in the table."
			INDEX { extremeWingCfgDevMac, extremeWingCfgDevIfName }
			::= { extremeWingCfgDevIfSerialTable 1 }

		
		ExtremeWingCfgDevIfSerialEntry ::=
			SEQUENCE { 
				extremeWingCfgDevIfSerialAuthentication
					DisplayString,
				extremeWingCfgDevIfSerialEncapsulation
					DisplayString,
				extremeWingCfgDevIfSerialLocalIpAddress
					DisplayString,
				extremeWingCfgDevIfSerialUsername
					DisplayString,
				extremeWingCfgDevIfSerialPassword
					DisplayString,
				extremeWingCfgDevIfSerialRemoteIpSubnet
					DisplayString
			 }

		-- 1.3.6.1.4.1.1916.2.131.50.1.3.18.3.15.1.1
		extremeWingCfgDevIfSerialAuthentication OBJECT-TYPE
			SYNTAX DisplayString
			MAX-ACCESS read-write
			STATUS current
			DESCRIPTION
				"Type of authentication
				
				Values:
				none
				pap
				chap
				
				XPath: /extremeWing-config/device[mac=key1]/interface[name=key2]/authentication"
			DEFVAL { "none" }
			::= { extremeWingCfgDevIfSerialEntry 1 }

		
		-- 1.3.6.1.4.1.1916.2.131.50.1.3.18.3.15.1.2
		extremeWingCfgDevIfSerialEncapsulation OBJECT-TYPE
			SYNTAX DisplayString
			MAX-ACCESS read-write
			STATUS current
			DESCRIPTION
				"The type of traffic that this group handles
				
				Values:
				chdlc
				hdlc
				ppp
				
				XPath: /extremeWing-config/device[mac=key1]/interface[name=key2]/encapsulation"
			DEFVAL { "ppp" }
			::= { extremeWingCfgDevIfSerialEntry 2 }

		
		-- 1.3.6.1.4.1.1916.2.131.50.1.3.18.3.15.1.3
		extremeWingCfgDevIfSerialLocalIpAddress OBJECT-TYPE
			SYNTAX DisplayString
			MAX-ACCESS read-write
			STATUS current
			DESCRIPTION
				"IP address assigned to the local system
				
				XPath: /extremeWing-config/device[mac=key1]/interface[name=key2]/local_ip_address"
			DEFVAL { "" }
			::= { extremeWingCfgDevIfSerialEntry 3 }

		
		-- 1.3.6.1.4.1.1916.2.131.50.1.3.18.3.15.1.4
		extremeWingCfgDevIfSerialUsername OBJECT-TYPE
			SYNTAX DisplayString (SIZE (0..32))
			MAX-ACCESS read-write
			STATUS current
			DESCRIPTION
				"Username provided by the service provider
				
				XPath: /extremeWing-config/device[mac=key1]/interface[name=key2]/username"
			DEFVAL { "" }
			::= { extremeWingCfgDevIfSerialEntry 4 }

		
		-- 1.3.6.1.4.1.1916.2.131.50.1.3.18.3.15.1.5
		extremeWingCfgDevIfSerialPassword OBJECT-TYPE
			SYNTAX DisplayString (SIZE (0..32))
			MAX-ACCESS read-write
			STATUS current
			DESCRIPTION
				"Password provided by the service provider
				
				XPath: /extremeWing-config/device[mac=key1]/interface[name=key2]/password"
			DEFVAL { "" }
			::= { extremeWingCfgDevIfSerialEntry 5 }

		
		-- 1.3.6.1.4.1.1916.2.131.50.1.3.18.3.15.1.6
		extremeWingCfgDevIfSerialRemoteIpSubnet OBJECT-TYPE
			SYNTAX DisplayString
			MAX-ACCESS read-write
			STATUS current
			DESCRIPTION
				"IP subnet assigned to the remote system along with subnet
				in CIDR notation - A.B.C.D/M
				
				XPath: /extremeWing-config/device[mac=key1]/interface[name=key2]/remote_ip_subnet"
			DEFVAL { "" }
			::= { extremeWingCfgDevIfSerialEntry 6 }

		
		-- 1.3.6.1.4.1.1916.2.131.50.1.3.18.3.16
		extremeWingCfgDevIfDot1xAuthTable OBJECT-TYPE
			SYNTAX SEQUENCE OF ExtremeWingCfgDevIfDot1xAuthEntry
			MAX-ACCESS not-accessible
			STATUS current
			DESCRIPTION
				"
				
				/extremeWing-config/device/interface"
			::= { extremeWingCfgDevIf 16 }

		
		-- 1.3.6.1.4.1.1916.2.131.50.1.3.18.3.16.1
		extremeWingCfgDevIfDot1xAuthEntry OBJECT-TYPE
			SYNTAX ExtremeWingCfgDevIfDot1xAuthEntry
			MAX-ACCESS not-accessible
			STATUS current
			DESCRIPTION
				"An entry in the table."
			INDEX { extremeWingCfgDevMac, extremeWingCfgDevIfName }
			::= { extremeWingCfgDevIfDot1xAuthTable 1 }

		
		ExtremeWingCfgDevIfDot1xAuthEntry ::=
			SEQUENCE { 
				extremeWingCfgDevIfDot1xAuthHostMode
					DisplayString,
				extremeWingCfgDevIfDot1xAuthGuestVlan
					Unsigned32,
				extremeWingCfgDevIfDot1xAuthPortControl
					DisplayString,
				extremeWingCfgDevIfDot1xAuthReauthenticate
					TruthValue,
				extremeWingCfgDevIfDot1xAuthMaxReauthCount
					Unsigned32,
				extremeWingCfgDevIfDot1xAuthMaxReq
					Unsigned32,
				extremeWingCfgDevIfDot1xAuthQuietPeriod
					Unsigned32,
				extremeWingCfgDevIfDot1xAuthReauthPeriod
					Unsigned32
			 }

		-- 1.3.6.1.4.1.1916.2.131.50.1.3.18.3.16.1.1
		extremeWingCfgDevIfDot1xAuthHostMode OBJECT-TYPE
			SYNTAX DisplayString
			MAX-ACCESS read-write
			STATUS current
			DESCRIPTION
				"Single or multi-host mode.
				
				Values:
				single-host,
				multi-host
				
				XPath: /extremeWing-config/device[mac=key1]/interface[name=key2]/host_mode"
			DEFVAL { "single-host" }
			::= { extremeWingCfgDevIfDot1xAuthEntry 1 }

		
		-- 1.3.6.1.4.1.1916.2.131.50.1.3.18.3.16.1.2
		extremeWingCfgDevIfDot1xAuthGuestVlan OBJECT-TYPE
			SYNTAX Unsigned32 (1..4094)
			MAX-ACCESS read-write
			STATUS current
			DESCRIPTION
				"Vlan onto which traffic is bridged if port is unauthorized and guest vlan is globally enabled
				
				XPath: /extremeWing-config/device[mac=key1]/interface[name=key2]/guest_vlan"
			::= { extremeWingCfgDevIfDot1xAuthEntry 2 }

		
		-- 1.3.6.1.4.1.1916.2.131.50.1.3.18.3.16.1.3
		extremeWingCfgDevIfDot1xAuthPortControl OBJECT-TYPE
			SYNTAX DisplayString
			MAX-ACCESS read-write
			STATUS current
			DESCRIPTION
				"Set 802.1x port state
				
				Values:
				auto,
				force-authorized,
				force-unauthorized
				
				XPath: /extremeWing-config/device[mac=key1]/interface[name=key2]/port_control"
			DEFVAL { "force-authorized" }
			::= { extremeWingCfgDevIfDot1xAuthEntry 3 }

		
		-- 1.3.6.1.4.1.1916.2.131.50.1.3.18.3.16.1.4
		extremeWingCfgDevIfDot1xAuthReauthenticate OBJECT-TYPE
			SYNTAX TruthValue
			MAX-ACCESS read-write
			STATUS current
			DESCRIPTION
				"Enable 802.1x re-authentication
				
				XPath: /extremeWing-config/device[mac=key1]/interface[name=key2]/reauthenticate"
			DEFVAL { false }
			::= { extremeWingCfgDevIfDot1xAuthEntry 4 }

		
		-- 1.3.6.1.4.1.1916.2.131.50.1.3.18.3.16.1.5
		extremeWingCfgDevIfDot1xAuthMaxReauthCount OBJECT-TYPE
			SYNTAX Unsigned32 (1..10)
			MAX-ACCESS read-write
			STATUS current
			DESCRIPTION
				"Number of reauthentication attempts before a port is moved to unauthorized
				
				XPath: /extremeWing-config/device[mac=key1]/interface[name=key2]/max_reauth_count"
			DEFVAL { 2 }
			::= { extremeWingCfgDevIfDot1xAuthEntry 5 }

		
		-- 1.3.6.1.4.1.1916.2.131.50.1.3.18.3.16.1.6
		extremeWingCfgDevIfDot1xAuthMaxReq OBJECT-TYPE
			SYNTAX Unsigned32 (1..10)
			MAX-ACCESS read-write
			STATUS current
			DESCRIPTION
				"Number of times 802.1x will retry authentication with the Radius Server before giving up and returning failed to the supplicant.
				
				XPath: /extremeWing-config/device[mac=key1]/interface[name=key2]/max_req"
			DEFVAL { 2 }
			::= { extremeWingCfgDevIfDot1xAuthEntry 6 }

		
		-- 1.3.6.1.4.1.1916.2.131.50.1.3.18.3.16.1.7
		extremeWingCfgDevIfDot1xAuthQuietPeriod OBJECT-TYPE
			SYNTAX Unsigned32 (1..65535)
			MAX-ACCESS read-write
			STATUS current
			DESCRIPTION
				"Time in seconds 802.1x will wait after authentication fails
				
				XPath: /extremeWing-config/device[mac=key1]/interface[name=key2]/quiet_period"
			DEFVAL { 60 }
			::= { extremeWingCfgDevIfDot1xAuthEntry 7 }

		
		-- 1.3.6.1.4.1.1916.2.131.50.1.3.18.3.16.1.8
		extremeWingCfgDevIfDot1xAuthReauthPeriod OBJECT-TYPE
			SYNTAX Unsigned32 (1..65535)
			MAX-ACCESS read-write
			STATUS current
			DESCRIPTION
				"Time in seconds until port is reauthenicated
				
				XPath: /extremeWing-config/device[mac=key1]/interface[name=key2]/reauth_period"
			DEFVAL { 60 }
			::= { extremeWingCfgDevIfDot1xAuthEntry 8 }

		
		-- 1.3.6.1.4.1.1916.2.131.50.1.3.18.3.17
		extremeWingCfgDevIfMeshpointBssmapTable OBJECT-TYPE
			SYNTAX SEQUENCE OF ExtremeWingCfgDevIfMeshpointBssmapEntry
			MAX-ACCESS not-accessible
			STATUS current
			DESCRIPTION
				"
				
				/extremeWing-config/device/interface/meshpoint"
			::= { extremeWingCfgDevIf 17 }

		
		-- 1.3.6.1.4.1.1916.2.131.50.1.3.18.3.17.1
		extremeWingCfgDevIfMeshpointBssmapEntry OBJECT-TYPE
			SYNTAX ExtremeWingCfgDevIfMeshpointBssmapEntry
			MAX-ACCESS not-accessible
			STATUS current
			DESCRIPTION
				"An entry in the table."
			INDEX { extremeWingCfgDevMac, extremeWingCfgDevIfName, extremeWingCfgDevIfMeshpointBssmapMeshpoint }
			::= { extremeWingCfgDevIfMeshpointBssmapTable 1 }

		
		ExtremeWingCfgDevIfMeshpointBssmapEntry ::=
			SEQUENCE { 
				extremeWingCfgDevIfMeshpointBssmapMeshpoint
					ExtremeWingIdentifier,
				extremeWingCfgDevIfMeshpointBssmapBss
					Unsigned32
			 }

		-- 1.3.6.1.4.1.1916.2.131.50.1.3.18.3.17.1.1
		extremeWingCfgDevIfMeshpointBssmapMeshpoint OBJECT-TYPE
			SYNTAX ExtremeWingIdentifier
			MAX-ACCESS read-write
			STATUS current
			DESCRIPTION
				"
				
				XPath: /extremeWing-config/device[mac=key1]/interface[name=key2]/meshpoint[meshpoint=key3]/meshpoint"
			::= { extremeWingCfgDevIfMeshpointBssmapEntry 1 }

		
		-- 1.3.6.1.4.1.1916.2.131.50.1.3.18.3.17.1.3
		extremeWingCfgDevIfMeshpointBssmapBss OBJECT-TYPE
			SYNTAX Unsigned32 (1..8)
			MAX-ACCESS read-write
			STATUS current
			DESCRIPTION
				"
				
				XPath: /extremeWing-config/device[mac=key1]/interface[name=key2]/meshpoint[meshpoint=key3]/bss"
			::= { extremeWingCfgDevIfMeshpointBssmapEntry 3 }

		
-- /extremeWing-config/device/bridge_vlan
		-- 1.3.6.1.4.1.1916.2.131.50.1.3.18.8
		extremeWingCfgDevBridgeVlan OBJECT IDENTIFIER ::= { extremeWingCfgDev 8 }

		
		-- 1.3.6.1.4.1.1916.2.131.50.1.3.18.8.1
		extremeWingCfgDevBridgeVlanTable OBJECT-TYPE
			SYNTAX SEQUENCE OF ExtremeWingCfgDevBridgeVlanEntry
			MAX-ACCESS not-accessible
			STATUS current
			DESCRIPTION
				"
				
				/extremeWing-config/profile/bridge_vlan"
			::= { extremeWingCfgDevBridgeVlan 1 }

		
		-- 1.3.6.1.4.1.1916.2.131.50.1.3.18.8.1.1
		extremeWingCfgDevBridgeVlanEntry OBJECT-TYPE
			SYNTAX ExtremeWingCfgDevBridgeVlanEntry
			MAX-ACCESS not-accessible
			STATUS current
			DESCRIPTION
				"An entry in the table."
			INDEX { extremeWingCfgDevMac, extremeWingCfgDevBridgeVlanId }
			::= { extremeWingCfgDevBridgeVlanTable 1 }

		
		ExtremeWingCfgDevBridgeVlanEntry ::=
			SEQUENCE { 
				extremeWingCfgDevBridgeVlanId
					Unsigned32,
				extremeWingCfgDevBridgeVlanDescription
					DisplayString,
				extremeWingCfgDevBridgeVlanEdgeVlan
					TruthValue,
				extremeWingCfgDevBridgeVlanBridgingMode
					DisplayString,
				extremeWingCfgDevBridgeVlanIpArpTrust
					TruthValue,
				extremeWingCfgDevBridgeVlanIpDhcpTrust
					TruthValue,
				extremeWingCfgDevBridgeVlanTunnelMacOutAcl
					ExtremeWingIdentifier,
				extremeWingCfgDevBridgeVlanTunnelIpOutAcl
					ExtremeWingIdentifier,
				extremeWingCfgDevBridgeVlanTunnelOverLevel2
					TruthValue
			 }

		-- 1.3.6.1.4.1.1916.2.131.50.1.3.18.8.1.1.1
		extremeWingCfgDevBridgeVlanId OBJECT-TYPE
			SYNTAX Unsigned32 (1..4095)
			MAX-ACCESS read-only
			STATUS current
			DESCRIPTION
				"
				
				XPath: /extremeWing-config/device[mac=key1]/bridge_vlan[vlan=key2]/vlan"
			::= { extremeWingCfgDevBridgeVlanEntry 1 }

		
		-- 1.3.6.1.4.1.1916.2.131.50.1.3.18.8.1.1.3
		extremeWingCfgDevBridgeVlanDescription OBJECT-TYPE
			SYNTAX DisplayString (SIZE (64))
			MAX-ACCESS read-write
			STATUS current
			DESCRIPTION
				"
				
				XPath: /extremeWing-config/device[mac=key1]/bridge_vlan[vlan=key2]/description"
			::= { extremeWingCfgDevBridgeVlanEntry 3 }

		
		-- 1.3.6.1.4.1.1916.2.131.50.1.3.18.8.1.1.4
		extremeWingCfgDevBridgeVlanEdgeVlan OBJECT-TYPE
			SYNTAX TruthValue
			MAX-ACCESS read-write
			STATUS current
			DESCRIPTION
				"
				
				XPath: /extremeWing-config/device[mac=key1]/bridge_vlan[vlan=key2]/edge_vlan"
			DEFVAL { true }
			::= { extremeWingCfgDevBridgeVlanEntry 4 }

		
		-- 1.3.6.1.4.1.1916.2.131.50.1.3.18.8.1.1.5
		extremeWingCfgDevBridgeVlanBridgingMode OBJECT-TYPE
			SYNTAX DisplayString
			MAX-ACCESS read-write
			STATUS current
			DESCRIPTION
				"
				
				Values:
				auto,
				local,
				tunnel,
				isolated-tunnel
				
				XPath: /extremeWing-config/device[mac=key1]/bridge_vlan[vlan=key2]/bridging_mode"
			DEFVAL { "auto" }
			::= { extremeWingCfgDevBridgeVlanEntry 5 }

		
		-- 1.3.6.1.4.1.1916.2.131.50.1.3.18.8.1.1.6
		extremeWingCfgDevBridgeVlanIpArpTrust OBJECT-TYPE
			SYNTAX TruthValue
			MAX-ACCESS read-write
			STATUS current
			DESCRIPTION
				"
				
				XPath: /extremeWing-config/device[mac=key1]/bridge_vlan[vlan=key2]/ip_arp_trust"
			DEFVAL { false }
			::= { extremeWingCfgDevBridgeVlanEntry 6 }

		
		-- 1.3.6.1.4.1.1916.2.131.50.1.3.18.8.1.1.7
		extremeWingCfgDevBridgeVlanIpDhcpTrust OBJECT-TYPE
			SYNTAX TruthValue
			MAX-ACCESS read-write
			STATUS current
			DESCRIPTION
				"
				
				XPath: /extremeWing-config/device[mac=key1]/bridge_vlan[vlan=key2]/ip_dhcp_trust"
			DEFVAL { false }
			::= { extremeWingCfgDevBridgeVlanEntry 7 }

		
		-- 1.3.6.1.4.1.1916.2.131.50.1.3.18.8.1.1.8
		extremeWingCfgDevBridgeVlanTunnelMacOutAcl OBJECT-TYPE
			SYNTAX ExtremeWingIdentifier
			MAX-ACCESS read-write
			STATUS current
			DESCRIPTION
				"
				
				XPath: /extremeWing-config/device[mac=key1]/bridge_vlan[vlan=key2]/tunnel_mac_out_acl"
			::= { extremeWingCfgDevBridgeVlanEntry 8 }

		
		-- 1.3.6.1.4.1.1916.2.131.50.1.3.18.8.1.1.9
		extremeWingCfgDevBridgeVlanTunnelIpOutAcl OBJECT-TYPE
			SYNTAX ExtremeWingIdentifier
			MAX-ACCESS read-write
			STATUS current
			DESCRIPTION
				"
				
				XPath: /extremeWing-config/device[mac=key1]/bridge_vlan[vlan=key2]/tunnel_ip_out_acl"
			::= { extremeWingCfgDevBridgeVlanEntry 9 }


		-- 1.3.6.1.4.1.1916.2.131.50.1.3.18.8.1.1.10
		extremeWingCfgDevBridgeVlanTunnelOverLevel2 OBJECT-TYPE
			SYNTAX TruthValue
			MAX-ACCESS read-write
			STATUS current
			DESCRIPTION
				"Allow extended VLAN traffic to be tunneled over level 2 links
				XPath: /extremeWing-config/device[mac=key1]/bridge_vlan[vlan=key2]/tunnel_over_level2
				"
			DEFVAL { false }
			::= { extremeWingCfgDevBridgeVlanEntry 10 }

		
		-- 1.3.6.1.4.1.1916.2.131.50.1.3.18.8.2
		extremeWingCfgDevBridgeVlanIgsTable OBJECT-TYPE
			SYNTAX SEQUENCE OF ExtremeWingCfgDevBridgeVlanIgsEntry
			MAX-ACCESS not-accessible
			STATUS current
			DESCRIPTION
				"
				
				/extremeWing-config/device/interface"
			::= { extremeWingCfgDevBridgeVlan 2 }

		
		-- 1.3.6.1.4.1.1916.2.131.50.1.3.18.8.2.1
		extremeWingCfgDevBridgeVlanIgsEntry OBJECT-TYPE
			SYNTAX ExtremeWingCfgDevBridgeVlanIgsEntry
			MAX-ACCESS not-accessible
			STATUS current
			DESCRIPTION
				"An entry in the table."
			INDEX { extremeWingCfgDevMac, extremeWingCfgDevBridgeVlanId }
			::= { extremeWingCfgDevBridgeVlanIgsTable 1 }

		
		ExtremeWingCfgDevBridgeVlanIgsEntry ::=
			SEQUENCE { 
				extremeWingCfgDevBridgeVlanIgsIpIgs
					TruthValue,
				extremeWingCfgDevBridgeVlanIgsIpIgsQuerier
					TruthValue,
				extremeWingCfgDevBridgeVlanIgsIpIgsQuerierMaxResponseTime
					Unsigned32,
				extremeWingCfgDevBridgeVlanIgsIpIgsQuerierVersion
					Unsigned32,
				extremeWingCfgDevBridgeVlanIgsIpIgsQuerierAddress
					IpAddress,
				extremeWingCfgDevBridgeVlanIgsIpIgsOtherQuerierTimerExpiry
					Unsigned32,
				extremeWingCfgDevBridgeVlanIgsIpIgsForwardUnknownMcast
					TruthValue,
				extremeWingCfgDevBridgeVlanIgsIpIgsMrouterLearnPimDvmrp
					DisplayString
			 }

		-- 1.3.6.1.4.1.1916.2.131.50.1.3.18.8.2.1.1
		extremeWingCfgDevBridgeVlanIgsIpIgs OBJECT-TYPE
			SYNTAX TruthValue
			MAX-ACCESS read-write
			STATUS current
			DESCRIPTION
				"
				
				XPath: /extremeWing-config/device[mac=key1]/bridge_vlan[vlan=key2]/ip_igs"
			DEFVAL { true }
			::= { extremeWingCfgDevBridgeVlanIgsEntry 1 }

		
		-- 1.3.6.1.4.1.1916.2.131.50.1.3.18.8.2.1.2
		extremeWingCfgDevBridgeVlanIgsIpIgsQuerier OBJECT-TYPE
			SYNTAX TruthValue
			MAX-ACCESS read-write
			STATUS current
			DESCRIPTION
				"
				
				XPath: /extremeWing-config/device[mac=key1]/bridge_vlan[vlan=key2]/ip_igs_querier"
			DEFVAL { false }
			::= { extremeWingCfgDevBridgeVlanIgsEntry 2 }

		
		-- 1.3.6.1.4.1.1916.2.131.50.1.3.18.8.2.1.3
		extremeWingCfgDevBridgeVlanIgsIpIgsQuerierMaxResponseTime OBJECT-TYPE
			SYNTAX Unsigned32 (1..25)
			UNITS "seconds"
			MAX-ACCESS read-write
			STATUS current
			DESCRIPTION
				"
				
				XPath: /extremeWing-config/device[mac=key1]/bridge_vlan[vlan=key2]/ip_igs_querier_max_response_time"
			::= { extremeWingCfgDevBridgeVlanIgsEntry 3 }

		
		-- 1.3.6.1.4.1.1916.2.131.50.1.3.18.8.2.1.4
		extremeWingCfgDevBridgeVlanIgsIpIgsQuerierVersion OBJECT-TYPE
			SYNTAX Unsigned32 (1..3)
			MAX-ACCESS read-write
			STATUS current
			DESCRIPTION
				"
				
				XPath: /extremeWing-config/device[mac=key1]/bridge_vlan[vlan=key2]/ip_igs_querier_version"
			::= { extremeWingCfgDevBridgeVlanIgsEntry 4 }

		
		-- 1.3.6.1.4.1.1916.2.131.50.1.3.18.8.2.1.5
		extremeWingCfgDevBridgeVlanIgsIpIgsQuerierAddress OBJECT-TYPE
			SYNTAX IpAddress 
			MAX-ACCESS read-write
			STATUS current
			DESCRIPTION
				"
				
				XPath: /extremeWing-config/device[mac=key1]/bridge_vlan[vlan=key2]/ip_igs_querier_address"
			::= { extremeWingCfgDevBridgeVlanIgsEntry 5 }

		
		-- 1.3.6.1.4.1.1916.2.131.50.1.3.18.8.2.1.6
		extremeWingCfgDevBridgeVlanIgsIpIgsOtherQuerierTimerExpiry OBJECT-TYPE
			SYNTAX Unsigned32 (60..300)
			UNITS "seconds"
			MAX-ACCESS read-write
			STATUS current
			DESCRIPTION
				"
				
				XPath: /extremeWing-config/device[mac=key1]/bridge_vlan[vlan=key2]/ip_igs_other_querier_timer_expiry"
			::= { extremeWingCfgDevBridgeVlanIgsEntry 6 }

		
		-- 1.3.6.1.4.1.1916.2.131.50.1.3.18.8.2.1.7
		extremeWingCfgDevBridgeVlanIgsIpIgsForwardUnknownMcast OBJECT-TYPE
			SYNTAX TruthValue
			MAX-ACCESS read-write
			STATUS current
			DESCRIPTION
				"
				
				XPath: /extremeWing-config/device[mac=key1]/bridge_vlan[vlan=key2]/ip_igs_forward_unknown_mcast"
			DEFVAL { false }
			::= { extremeWingCfgDevBridgeVlanIgsEntry 7 }

		
		-- 1.3.6.1.4.1.1916.2.131.50.1.3.18.8.2.1.8
		extremeWingCfgDevBridgeVlanIgsIpIgsMrouterLearnPimDvmrp OBJECT-TYPE
			SYNTAX DisplayString
			MAX-ACCESS read-write
			STATUS current
			DESCRIPTION
				"
				
				XPath: /extremeWing-config/device[mac=key1]/bridge_vlan[vlan=key2]/ip_igs_mrouter_learn_pim_dvmrp"
			DEFVAL { "pim-dvmrp" }
			::= { extremeWingCfgDevBridgeVlanIgsEntry 8 }

		
-- /extremeWing-config/device/mint_link_cfg
		-- 1.3.6.1.4.1.1916.2.131.50.1.3.18.10
		extremeWingCfgDevMint OBJECT IDENTIFIER ::= { extremeWingCfgDev 10 }

		
		-- 1.3.6.1.4.1.1916.2.131.50.1.3.18.10.1
		extremeWingCfgDevMintTable OBJECT-TYPE
			SYNTAX SEQUENCE OF ExtremeWingCfgDevMintEntry
			MAX-ACCESS not-accessible
			STATUS current
			DESCRIPTION
				"
				
				/extremeWing-config/device/mint_link_cfg"
			::= { extremeWingCfgDevMint 1 }

		
		-- 1.3.6.1.4.1.1916.2.131.50.1.3.18.10.1.1
		extremeWingCfgDevMintEntry OBJECT-TYPE
			SYNTAX ExtremeWingCfgDevMintEntry
			MAX-ACCESS not-accessible
			STATUS current
			DESCRIPTION
				"An entry in the table."
			INDEX { extremeWingCfgDevMac }
			::= { extremeWingCfgDevMintTable 1 }

		
		ExtremeWingCfgDevMintEntry ::=
			SEQUENCE { 
				extremeWingCfgDevMintLevel1AreaId
					DisplayString,
				extremeWingCfgDevMintSpfLatency
					DisplayString,
				extremeWingCfgDevMintDisPriorityAdjustment
					Integer32,
				extremeWingCfgDevMintMlcpVlan
					TruthValue,
				extremeWingCfgDevMintMlcpIp
					TruthValue,
				extremeWingCfgDevMintTunnelControllerLoadBalancingLevel1
					TruthValue
			 }

		-- 1.3.6.1.4.1.1916.2.131.50.1.3.18.10.1.1.1
		extremeWingCfgDevMintLevel1AreaId OBJECT-TYPE
			SYNTAX DisplayString
			MAX-ACCESS read-write
			STATUS current
			DESCRIPTION
				"
				
				XPath: /extremeWing-config/device[mac=key1]/mint_link_cfg/mint_level1_area_id"
			::= { extremeWingCfgDevMintEntry 1 }

		
		-- 1.3.6.1.4.1.1916.2.131.50.1.3.18.10.1.1.2
		extremeWingCfgDevMintSpfLatency OBJECT-TYPE
			SYNTAX DisplayString
			UNITS "seconds"
			MAX-ACCESS read-write
			STATUS current
			DESCRIPTION
				"
				
				XPath: /extremeWing-config/device[mac=key1]/mint_link_cfg/mint_spf_latency"
			::= { extremeWingCfgDevMintEntry 2 }

		
		-- 1.3.6.1.4.1.1916.2.131.50.1.3.18.10.1.1.3
		extremeWingCfgDevMintDisPriorityAdjustment OBJECT-TYPE
			SYNTAX Integer32 (-255..255)
			MAX-ACCESS read-write
			STATUS current
			DESCRIPTION
				"value added to base level DIS priority to influence the DIS election. +1 increases DISiness.
				
				XPath: /extremeWing-config/device[mac=key1]/mint_link_cfg/mint_dis_priority_adjustment"
			DEFVAL { 0 }
			::= { extremeWingCfgDevMintEntry 3 }

		
		-- 1.3.6.1.4.1.1916.2.131.50.1.3.18.10.1.1.4
		extremeWingCfgDevMintMlcpVlan OBJECT-TYPE
			SYNTAX TruthValue
			MAX-ACCESS read-write
			STATUS current
			DESCRIPTION
				"MLCP for automated MiNT VLAN link creation
				
				XPath: /extremeWing-config/device[mac=key1]/mint_link_cfg/mint_mlcp_vlan"
			DEFVAL { true }
			::= { extremeWingCfgDevMintEntry 4 }

		
		-- 1.3.6.1.4.1.1916.2.131.50.1.3.18.10.1.1.5
		extremeWingCfgDevMintMlcpIp OBJECT-TYPE
			SYNTAX TruthValue
			MAX-ACCESS read-write
			STATUS current
			DESCRIPTION
				"MLCP for automated MiNT UDP/IP link creation
				
				XPath: /extremeWing-config/device[mac=key1]/mint_link_cfg/mint_mlcp_ip"
			DEFVAL { true }
			::= { extremeWingCfgDevMintEntry 5 }

		
		-- 1.3.6.1.4.1.1916.2.131.50.1.3.18.10.1.1.6
		extremeWingCfgDevMintTunnelControllerLoadBalancingLevel1 OBJECT-TYPE
			SYNTAX TruthValue
			MAX-ACCESS read-write
			STATUS current
			DESCRIPTION
				"MLCP for automated MiNT UDP/IP link creation
				
				XPath: /extremeWing-config/device[mac=key1]/mint_link_cfg/mint_tunnel_controller_load_balancing_level1"
			::= { extremeWingCfgDevMintEntry 6 }

		
--  /extremeWing-config/device/dot11_cfg
		-- 1.3.6.1.4.1.1916.2.131.50.1.3.18.11
		extremeWingCfgDevDot11 OBJECT IDENTIFIER ::= { extremeWingCfgDev 11 }

		
		-- 1.3.6.1.4.1.1916.2.131.50.1.3.18.11.1
		extremeWingCfgDevDot11Table OBJECT-TYPE
			SYNTAX SEQUENCE OF ExtremeWingCfgDevDot11Entry
			MAX-ACCESS not-accessible
			STATUS current
			DESCRIPTION
				"802.11 global parameters for this device.
				
				/extremeWing-config/device/dot11_cfg"
			::= { extremeWingCfgDevDot11 1 }

		
		-- 1.3.6.1.4.1.1916.2.131.50.1.3.18.11.1.1
		extremeWingCfgDevDot11Entry OBJECT-TYPE
			SYNTAX ExtremeWingCfgDevDot11Entry
			MAX-ACCESS not-accessible
			STATUS current
			DESCRIPTION
				"An entry in the table."
			INDEX { extremeWingCfgDevMac }
			::= { extremeWingCfgDevDot11Table 1 }

		
		ExtremeWingCfgDevDot11Entry ::=
			SEQUENCE { 
				extremeWingCfgDevDot11WepSharedKeyAuth
					TruthValue,
				extremeWingCfgDevDot11LegacyAutoUpdateAp650
					TruthValue,
				extremeWingCfgDevDot11LegacyAutoUpdateImgAp7131
					DisplayString,
				extremeWingCfgDevDot11LegacyAutoDowngrade
					TruthValue,
				extremeWingCfgDevDot11NasIdentifier
					DisplayString,
				extremeWingCfgDevDot11NasPortId
					DisplayString
			 }

		-- 1.3.6.1.4.1.1916.2.131.50.1.3.18.11.1.1.1
		extremeWingCfgDevDot11WepSharedKeyAuth OBJECT-TYPE
			SYNTAX TruthValue
			MAX-ACCESS read-write
			STATUS current
			DESCRIPTION
				"Whether 802.11 shared key authentication is supported
				with WEP. Note: this method has known security vulnerabilities
				and its use is not recommended unless there are devices
				on the network that are only capable of
				shared-key authentication.
				
				XPath: /extremeWing-config/device[mac=key1]/dot11_cfg/wep_shared_key_auth"
			DEFVAL { false }
			::= { extremeWingCfgDevDot11Entry 1 }

		
		-- 1.3.6.1.4.1.1916.2.131.50.1.3.18.11.1.1.2
		extremeWingCfgDevDot11LegacyAutoUpdateAp650 OBJECT-TYPE
			SYNTAX TruthValue
			MAX-ACCESS read-write
			STATUS current
			DESCRIPTION
				"Whether legacy devices found on the network will automatically
				be updated to supported firmware.
				
				XPath: /extremeWing-config/device[mac=key1]/dot11_cfg/legacy_auto_update_ap650"
			DEFVAL { true }
			::= { extremeWingCfgDevDot11Entry 2 }

		
		-- 1.3.6.1.4.1.1916.2.131.50.1.3.18.11.1.1.3
		extremeWingCfgDevDot11LegacyAutoUpdateImgAp7131 OBJECT-TYPE
			SYNTAX DisplayString (SIZE (0..253))
			MAX-ACCESS read-write
			STATUS current
			DESCRIPTION
				"Path to the AP4700 legacy auto update image.
				
				XPath: /extremeWing-config/device[mac=key1]/dot11_cfg/legacy_auto_update_img_ap7131"
			DEFVAL { "" }
			::= { extremeWingCfgDevDot11Entry 3 }

		
		-- 1.3.6.1.4.1.1916.2.131.50.1.3.18.11.1.1.4
		extremeWingCfgDevDot11LegacyAutoDowngrade OBJECT-TYPE
			SYNTAX TruthValue
			MAX-ACCESS read-write
			STATUS current
			DESCRIPTION
				"Whether the AP4600 will connect to a legacy device and
				downgrade to be compatible with legacy devices.
				
				XPath: /extremeWing-config/device[mac=key1]/dot11_cfg/legacy_auto_downgrade"
			DEFVAL { true }
			::= { extremeWingCfgDevDot11Entry 4 }

		
		-- 1.3.6.1.4.1.1916.2.131.50.1.3.18.11.1.1.5
		extremeWingCfgDevDot11NasIdentifier OBJECT-TYPE
			SYNTAX DisplayString (SIZE (0..253))
			MAX-ACCESS read-write
			STATUS current
			DESCRIPTION
				"The RADIUS NAS-Identifier attribute which typically identifies
				the Access Point or Wireless Controller where the RADIUS
				message originates.
				
				XPath: /extremeWing-config/device[mac=key1]/dot11_cfg/nas_identifier"
			DEFVAL { "" }
			::= { extremeWingCfgDevDot11Entry 5 }

		
		-- 1.3.6.1.4.1.1916.2.131.50.1.3.18.11.1.1.6
		extremeWingCfgDevDot11NasPortId OBJECT-TYPE
			SYNTAX DisplayString (SIZE (0..253))
			MAX-ACCESS read-write
			STATUS current
			DESCRIPTION
				"The RADIUS NAS-Port-Id attribute which typically identifies
				the port of the device where the RADIUS messages originates.
				
				XPath: /extremeWing-config/device[mac=key1]/dot11_cfg/nas_port_id"
			DEFVAL { "" }
			::= { extremeWingCfgDevDot11Entry 6 }

		
-- /extremeWing-config/device
		-- 1.3.6.1.4.1.1916.2.131.50.1.3.18.16
		extremeWingCfgDevNat OBJECT IDENTIFIER ::= { extremeWingCfgDev 16 }

		
		-- 1.3.6.1.4.1.1916.2.131.50.1.3.18.16.1
		extremeWingCfgDevNatPoolTable OBJECT-TYPE
			SYNTAX SEQUENCE OF ExtremeWingCfgDevNatPoolEntry
			MAX-ACCESS not-accessible
			STATUS current
			DESCRIPTION
				"
				
				/extremeWing-config/device/nat_pool"
			::= { extremeWingCfgDevNat 1 }

		
		-- 1.3.6.1.4.1.1916.2.131.50.1.3.18.16.1.1
		extremeWingCfgDevNatPoolEntry OBJECT-TYPE
			SYNTAX ExtremeWingCfgDevNatPoolEntry
			MAX-ACCESS not-accessible
			STATUS current
			DESCRIPTION
				"An entry in the table."
			INDEX { extremeWingCfgDevMac, extremeWingCfgDevNatPoolName }
			::= { extremeWingCfgDevNatPoolTable 1 }

		
		ExtremeWingCfgDevNatPoolEntry ::=
			SEQUENCE { 
				extremeWingCfgDevNatPoolName
					ExtremeWingIdentifier
			 }

		-- 1.3.6.1.4.1.1916.2.131.50.1.3.18.16.1.1.1
		extremeWingCfgDevNatPoolName OBJECT-TYPE
			SYNTAX ExtremeWingIdentifier
			MAX-ACCESS read-only
			STATUS current
			DESCRIPTION
				"Name of the NAT pool.
				
				XPath: /extremeWing-config/device[mac=key1]/nat_pool[name=key2]/name"
			::= { extremeWingCfgDevNatPoolEntry 1 }

		
		-- 1.3.6.1.4.1.1916.2.131.50.1.3.18.16.2
		extremeWingCfgDevNatPoolAddrTable OBJECT-TYPE
			SYNTAX SEQUENCE OF ExtremeWingCfgDevNatPoolAddrEntry
			MAX-ACCESS not-accessible
			STATUS current
			DESCRIPTION
				"
				
				/extremeWing-config/device/nat_pool/address_range"
			::= { extremeWingCfgDevNat 2 }

		
		-- 1.3.6.1.4.1.1916.2.131.50.1.3.18.16.2.1
		extremeWingCfgDevNatPoolAddrEntry OBJECT-TYPE
			SYNTAX ExtremeWingCfgDevNatPoolAddrEntry
			MAX-ACCESS not-accessible
			STATUS current
			DESCRIPTION
				"An entry in the table."
			INDEX { extremeWingCfgDevMac, extremeWingCfgDevNatPoolName, extremeWingCfgDevNatPoolAddrStartIp }
			::= { extremeWingCfgDevNatPoolAddrTable 1 }

		
		ExtremeWingCfgDevNatPoolAddrEntry ::=
			SEQUENCE { 
				extremeWingCfgDevNatPoolAddrStartIp
					ExtremeWingIdentifier,
				extremeWingCfgDevNatPoolAddrEndIp
					IpAddress
			 }

		-- 1.3.6.1.4.1.1916.2.131.50.1.3.18.16.2.1.1
		extremeWingCfgDevNatPoolAddrStartIp OBJECT-TYPE
			SYNTAX ExtremeWingIdentifier
			MAX-ACCESS read-only
			STATUS current
			DESCRIPTION
				"
				
				XPath: /extremeWing-config/device[mac=key1]/nat_pool[name=key2]/address_rage[start_ip=key3]/start_ip"
			::= { extremeWingCfgDevNatPoolAddrEntry 1 }

		
		-- 1.3.6.1.4.1.1916.2.131.50.1.3.18.16.2.1.3
		extremeWingCfgDevNatPoolAddrEndIp OBJECT-TYPE
			SYNTAX IpAddress
			MAX-ACCESS read-write
			STATUS current
			DESCRIPTION
				"
				
				XPath: /extremeWing-config/device[mac=key1]/nat_pool[name=key2]/address_rage[start_ip=key3]/end_ip"
			::= { extremeWingCfgDevNatPoolAddrEntry 3 }

		
		-- 1.3.6.1.4.1.1916.2.131.50.1.3.18.16.7
		extremeWingCfgDevNatBridgeSrcDynamicTable OBJECT-TYPE
			SYNTAX SEQUENCE OF ExtremeWingCfgDevNatBridgeSrcDynamicEntry
			MAX-ACCESS not-accessible
			STATUS current
			DESCRIPTION
				"
				/extremeWing-config/device/bridge_source_dynamic_nat"
			::= { extremeWingCfgDevNat 7 }

		
		-- 1.3.6.1.4.1.1916.2.131.50.1.3.18.16.7.1
		extremeWingCfgDevNatBridgeSrcDynamicEntry OBJECT-TYPE
			SYNTAX ExtremeWingCfgDevNatBridgeSrcDynamicEntry
			MAX-ACCESS not-accessible
			STATUS current
			DESCRIPTION
				"An entry in the table."
			INDEX { extremeWingCfgDevMac, extremeWingCfgDevNatBridgeSrcDynamicAcl }
			::= { extremeWingCfgDevNatBridgeSrcDynamicTable 1 }

		
		ExtremeWingCfgDevNatBridgeSrcDynamicEntry ::=
			SEQUENCE { 
				extremeWingCfgDevNatBridgeSrcDynamicAcl
					ExtremeWingIdentifier
			 }

		-- 1.3.6.1.4.1.1916.2.131.50.1.3.18.16.7.1.1
		extremeWingCfgDevNatBridgeSrcDynamicAcl OBJECT-TYPE
			SYNTAX ExtremeWingIdentifier
			MAX-ACCESS read-only
			STATUS current
			DESCRIPTION
				"ACL 
				
				XPath: /extremeWing-config/device[mac=key1]/bridge_source_dynamic_nat[acl=key2]/acl"
			::= { extremeWingCfgDevNatBridgeSrcDynamicEntry 1 }

		
		-- 1.3.6.1.4.1.1916.2.131.50.1.3.18.16.8
		extremeWingCfgDevNatBridgeSrcDynamicIfTable OBJECT-TYPE
			SYNTAX SEQUENCE OF ExtremeWingCfgDevNatBridgeSrcDynamicIfEntry
			MAX-ACCESS not-accessible
			STATUS current
			DESCRIPTION
				"
				
				/extremeWing-config/device/bridge_source_dynamic_nat/interface_cfg"
			::= { extremeWingCfgDevNat 8 }

		
		-- 1.3.6.1.4.1.1916.2.131.50.1.3.18.16.8.1
		extremeWingCfgDevNatBridgeSrcDynamicIfEntry OBJECT-TYPE
			SYNTAX ExtremeWingCfgDevNatBridgeSrcDynamicIfEntry
			MAX-ACCESS not-accessible
			STATUS current
			DESCRIPTION
				"An entry in the table."
			INDEX { extremeWingCfgDevMac, extremeWingCfgDevNatBridgeSrcDynamicAcl, extremeWingCfgDevNatBridgeSrcDynamicIfName }
			::= { extremeWingCfgDevNatBridgeSrcDynamicIfTable 1 }

		
		ExtremeWingCfgDevNatBridgeSrcDynamicIfEntry ::=
			SEQUENCE { 
				extremeWingCfgDevNatBridgeSrcDynamicIfName
					ExtremeWingIdentifier,
				extremeWingCfgDevNatBridgeSrcDynamicIfOverloadType
					DisplayString,
				extremeWingCfgDevNatBridgeSrcDynamicIfOverloadIp
					DisplayString,
				extremeWingCfgDevNatBridgeSrcDynamicIfNatPool
					DisplayString
			 }

		-- 1.3.6.1.4.1.1916.2.131.50.1.3.18.16.8.1.1
		extremeWingCfgDevNatBridgeSrcDynamicIfName OBJECT-TYPE
			SYNTAX ExtremeWingIdentifier
			MAX-ACCESS read-only
			STATUS current
			DESCRIPTION
				"The outgoing layer 3 interface for NAT.
				
				XPath: /extremeWing-config/device[mac=key1]/bridge_source_dynamic_nat[acl=key2]/interface_cfg[interface=key3]/interface"
			::= { extremeWingCfgDevNatBridgeSrcDynamicIfEntry 1 }

		
		-- 1.3.6.1.4.1.1916.2.131.50.1.3.18.16.8.1.3
		extremeWingCfgDevNatBridgeSrcDynamicIfOverloadType OBJECT-TYPE
			SYNTAX DisplayString
			MAX-ACCESS read-write
			STATUS current
			DESCRIPTION
				"Overload Type.
				
				XPath: /extremeWing-config/device[mac=key1]/bridge_source_dynamic_nat[acl=key2]/interface_cfg[interface=key3]/overload_type"
			::= { extremeWingCfgDevNatBridgeSrcDynamicIfEntry 3 }

		
		-- 1.3.6.1.4.1.1916.2.131.50.1.3.18.16.8.1.4
		extremeWingCfgDevNatBridgeSrcDynamicIfOverloadIp OBJECT-TYPE
			SYNTAX DisplayString
			MAX-ACCESS read-write
			STATUS current
			DESCRIPTION
				"Overload IP.
				
				XPath: /extremeWing-config/device[mac=key1]/bridge_source_dynamic_nat[acl=key2]/interface_cfg[interface=key3]/overload_ip"
			::= { extremeWingCfgDevNatBridgeSrcDynamicIfEntry 4 }

		
		-- 1.3.6.1.4.1.1916.2.131.50.1.3.18.16.8.1.5
		extremeWingCfgDevNatBridgeSrcDynamicIfNatPool OBJECT-TYPE
			SYNTAX DisplayString
			MAX-ACCESS read-write
			STATUS current
			DESCRIPTION
				"Nat Pool.
				
				XPath: /extremeWing-config/device[mac=key1]/bridge_source_dynamic_nat[acl=key2]/interface_cfg[interface=key3]/nat_pool"
			::= { extremeWingCfgDevNatBridgeSrcDynamicIfEntry 5 }

		
-- /extremeWing-config/device
		-- 1.3.6.1.4.1.1916.2.131.50.1.3.18.19
		extremeWingCfgDevVpn OBJECT IDENTIFIER ::= { extremeWingCfgDev 19 }

		
		-- 1.3.6.1.4.1.1916.2.131.50.1.3.18.19.1
		extremeWingCfgDevVpnTable OBJECT-TYPE
			SYNTAX SEQUENCE OF ExtremeWingCfgDevVpnEntry
			MAX-ACCESS not-accessible
			STATUS current
			DESCRIPTION
				"
				
				/extremeWing-config/profile"
			::= { extremeWingCfgDevVpn 1 }

		
		-- 1.3.6.1.4.1.1916.2.131.50.1.3.18.19.1.1
		extremeWingCfgDevVpnEntry OBJECT-TYPE
			SYNTAX ExtremeWingCfgDevVpnEntry
			MAX-ACCESS not-accessible
			STATUS current
			DESCRIPTION
				"An entry in the table."
			INDEX { extremeWingCfgDevMac }
			::= { extremeWingCfgDevVpnTable 1 }

		
		ExtremeWingCfgDevVpnEntry ::=
			SEQUENCE { 
				extremeWingCfgDevVpnLifetimeSeconds
					Unsigned32,
				extremeWingCfgDevVpnLifetimeKb
					Unsigned32,
				extremeWingCfgDevVpnIkev1GlobalDpdKeepalive
					Unsigned32,
				extremeWingCfgDevVpnIkev1GlobalDpdRetries
					Unsigned32,
				extremeWingCfgDevVpnIkev1GlobalNatKeepalive
					Unsigned32,
				extremeWingCfgDevVpnIkev2GlobalDpdKeepalive
					Unsigned32,
				extremeWingCfgDevVpnIkev2GlobalDpdRetries
					Unsigned32,
				extremeWingCfgDevVpnIkev2GlobalNatKeepalive
					Unsigned32,
				extremeWingCfgDevVpnCookieChallengeThreshold
					Unsigned32,
				extremeWingCfgDevVpnMaxInNegotiationSa
					Unsigned32,
				extremeWingCfgDevVpnDfBit
					DisplayString
			 }

		-- 1.3.6.1.4.1.1916.2.131.50.1.3.18.19.1.1.1
		extremeWingCfgDevVpnLifetimeSeconds OBJECT-TYPE
			SYNTAX Unsigned32 (120..2147483646)
			UNITS "seconds"
			MAX-ACCESS read-write
			STATUS current
			DESCRIPTION
				"Time-based IPsec security association lifetime.
				
				XPath: /extremeWing-config/device[mac=key1]/lifetime_seconds"
			DEFVAL { 3600 }
			::= { extremeWingCfgDevVpnEntry 1 }

		
		-- 1.3.6.1.4.1.1916.2.131.50.1.3.18.19.1.1.2
		extremeWingCfgDevVpnLifetimeKb OBJECT-TYPE
			SYNTAX Unsigned32 (500..2147483646)
			UNITS "kilobytes"
			MAX-ACCESS read-write
			STATUS current
			DESCRIPTION
				"Data-based IPsec security association lifetime.
				
				XPath: /extremeWing-config/device[mac=key1]/lifetime_kb"
			DEFVAL { 4608000 }
			::= { extremeWingCfgDevVpnEntry 2 }

		
		-- 1.3.6.1.4.1.1916.2.131.50.1.3.18.19.1.1.3
		extremeWingCfgDevVpnIkev1GlobalDpdKeepalive OBJECT-TYPE
			SYNTAX Unsigned32 (10..3600)
			UNITS "seconds"
			MAX-ACCESS read-write
			STATUS current
			DESCRIPTION
				"Global setting for frequency of IKE keepalive messages for Dead Peer Detection.
				
				XPath: /extremeWing-config/device[mac=key1]/ikev1_dpd_keepalive"
			DEFVAL { 30 }
			::= { extremeWingCfgDevVpnEntry 3 }

		
		-- 1.3.6.1.4.1.1916.2.131.50.1.3.18.19.1.1.4
		extremeWingCfgDevVpnIkev1GlobalDpdRetries OBJECT-TYPE
			SYNTAX Unsigned32 (1..100)
			MAX-ACCESS read-write
			STATUS current
			DESCRIPTION
				"Global setting for number of keepalive messages to send before declaring a peer dead.
				
				XPath: /extremeWing-config/device[mac=key1]/ikev1_dpd_retries"
			DEFVAL { 5 }
			::= { extremeWingCfgDevVpnEntry 4 }

		
		-- 1.3.6.1.4.1.1916.2.131.50.1.3.18.19.1.1.5
		extremeWingCfgDevVpnIkev1GlobalNatKeepalive OBJECT-TYPE
			SYNTAX Unsigned32 (10..3600)
			UNITS "seconds"
			MAX-ACCESS read-write
			STATUS current
			DESCRIPTION
				"Global setting for frequency of NAT keepalive messages.
				
				XPath: /extremeWing-config/device[mac=key1]/ikev1_nat_keepalive"
			DEFVAL { 20 }
			::= { extremeWingCfgDevVpnEntry 5 }

		
		-- 1.3.6.1.4.1.1916.2.131.50.1.3.18.19.1.1.6
		extremeWingCfgDevVpnIkev2GlobalDpdKeepalive OBJECT-TYPE
			SYNTAX Unsigned32 (10..3600)
			UNITS "seconds"
			MAX-ACCESS read-write
			STATUS current
			DESCRIPTION
				"Global setting for frequency of IKE keepalive messages for Dead Peer Detection.
				
				XPath: /extremeWing-config/device[mac=key1]/ikev2_dpd_keepalive"
			DEFVAL { 30 }
			::= { extremeWingCfgDevVpnEntry 6 }

		
		-- 1.3.6.1.4.1.1916.2.131.50.1.3.18.19.1.1.7
		extremeWingCfgDevVpnIkev2GlobalDpdRetries OBJECT-TYPE
			SYNTAX Unsigned32 (1..100)
			MAX-ACCESS read-write
			STATUS current
			DESCRIPTION
				"Global setting for number of keepalive messages to send before declaring a peer dead.
				
				XPath: /extremeWing-config/device[mac=key1]/ikev2_dpd_retries"
			DEFVAL { 5 }
			::= { extremeWingCfgDevVpnEntry 7 }

		
		-- 1.3.6.1.4.1.1916.2.131.50.1.3.18.19.1.1.8
		extremeWingCfgDevVpnIkev2GlobalNatKeepalive OBJECT-TYPE
			SYNTAX Unsigned32 (10..3600)
			UNITS "seconds"
			MAX-ACCESS read-write
			STATUS current
			DESCRIPTION
				"Global setting for frequency of NAT keepalive messages.
				
				XPath: /extremeWing-config/device[mac=key1]/ikev2_nat_keepalive"
			DEFVAL { 20 }
			::= { extremeWingCfgDevVpnEntry 8 }

		
		-- 1.3.6.1.4.1.1916.2.131.50.1.3.18.19.1.1.9
		extremeWingCfgDevVpnCookieChallengeThreshold OBJECT-TYPE
			SYNTAX Unsigned32 (1..100)
			MAX-ACCESS read-write
			STATUS current
			DESCRIPTION
				"Number of Half open IKE SA after which cookie challenge mechanism is enabled (IKEv2 only).
				
				XPath: /extremeWing-config/device[mac=key1]/cookie_challenge_threshold"
			DEFVAL { 5 }
			::= { extremeWingCfgDevVpnEntry 9 }

		
		-- 1.3.6.1.4.1.1916.2.131.50.1.3.18.19.1.1.10
		extremeWingCfgDevVpnMaxInNegotiationSa OBJECT-TYPE
			SYNTAX Unsigned32 (1..100)
			MAX-ACCESS read-write
			STATUS current
			DESCRIPTION
				"Maximum allowed half open IKE SAs (IKEv2 only).
				
				XPath: /extremeWing-config/device[mac=key1]/max_in_negotiation_sa"
			DEFVAL { 10 }
			::= { extremeWingCfgDevVpnEntry 10 }

		
		-- 1.3.6.1.4.1.1916.2.131.50.1.3.18.19.1.1.11
		extremeWingCfgDevVpnDfBit OBJECT-TYPE
			SYNTAX DisplayString
			MAX-ACCESS read-write
			STATUS current
			DESCRIPTION
				"Configure DF bit handling for esp encapsulating header
				
				Values:
				clear,
				set,
				copy
				
				XPath: /extremeWing-config/device[mac=key1]/df_bit"
			DEFVAL { "copy" }
			::= { extremeWingCfgDevVpnEntry 11 }

		
		-- 1.3.6.1.4.1.1916.2.131.50.1.3.18.19.2
		extremeWingCfgDevVpnIkev1Table OBJECT-TYPE
			SYNTAX SEQUENCE OF ExtremeWingCfgDevVpnIkev1Entry
			MAX-ACCESS not-accessible
			STATUS current
			DESCRIPTION
				"
				
				/extremeWing-config/device/ikev1_policy"
			::= { extremeWingCfgDevVpn 2 }

		
		-- 1.3.6.1.4.1.1916.2.131.50.1.3.18.19.2.1
		extremeWingCfgDevVpnIkev1Entry OBJECT-TYPE
			SYNTAX ExtremeWingCfgDevVpnIkev1Entry
			MAX-ACCESS not-accessible
			STATUS current
			DESCRIPTION
				"An entry in the table."
			INDEX { extremeWingCfgDevMac, extremeWingCfgDevVpnIkev1Name }
			::= { extremeWingCfgDevVpnIkev1Table 1 }

		
		ExtremeWingCfgDevVpnIkev1Entry ::=
			SEQUENCE { 
				extremeWingCfgDevVpnIkev1Name
					ExtremeWingIdentifier,
				extremeWingCfgDevVpnIkev1Mode
					DisplayString,
				extremeWingCfgDevVpnIkev1IsakmpLifetime
					Unsigned32,
				extremeWingCfgDevVpnIkev1DpdKeepalive
					Unsigned32,
				extremeWingCfgDevVpnIkev1DpdRetries
					Unsigned32
			 }

		-- 1.3.6.1.4.1.1916.2.131.50.1.3.18.19.2.1.1
		extremeWingCfgDevVpnIkev1Name OBJECT-TYPE
			SYNTAX ExtremeWingIdentifier
			MAX-ACCESS read-only
			STATUS current
			DESCRIPTION
				"
				
				XPath: /extremeWing-config/device[mac=key1]/ikev1_policy[name=key2]/name"
			::= { extremeWingCfgDevVpnIkev1Entry 1 }

		
		-- 1.3.6.1.4.1.1916.2.131.50.1.3.18.19.2.1.3
		extremeWingCfgDevVpnIkev1Mode OBJECT-TYPE
			SYNTAX DisplayString
			MAX-ACCESS read-write
			STATUS current
			DESCRIPTION
				"IKE version 1 mode of operation (main/aggressive).
				
				Values:
				main,
				aggressive
				
				XPath: /extremeWing-config/device[mac=key1]/ikev1_policy[name=key2]/mode"
			DEFVAL { "main" }
			::= { extremeWingCfgDevVpnIkev1Entry 3 }

		
		-- 1.3.6.1.4.1.1916.2.131.50.1.3.18.19.2.1.4
		extremeWingCfgDevVpnIkev1IsakmpLifetime OBJECT-TYPE
			SYNTAX Unsigned32 (600..2147483646)
			UNITS "seconds"
			MAX-ACCESS read-write
			STATUS current
			DESCRIPTION
				"Lifetime in seconds for IKE Security Association (ISAKMP SA).
				
				XPath: /extremeWing-config/device[mac=key1]/ikev1_policy[name=key2]/isakmp_lifetime"
			DEFVAL { 86400 }
			::= { extremeWingCfgDevVpnIkev1Entry 4 }

		
		-- 1.3.6.1.4.1.1916.2.131.50.1.3.18.19.2.1.5
		extremeWingCfgDevVpnIkev1DpdKeepalive OBJECT-TYPE
			SYNTAX Unsigned32 (10..3600)
			UNITS "seconds"
			MAX-ACCESS read-write
			STATUS current
			DESCRIPTION
				"Frequency of IKE keepalive messages for Dead Peer Detection.
				
				XPath: /extremeWing-config/device[mac=key1]/ikev1_policy[name=key2]/dpd_keepalive"
			DEFVAL { 30 }
			::= { extremeWingCfgDevVpnIkev1Entry 5 }

		
		-- 1.3.6.1.4.1.1916.2.131.50.1.3.18.19.2.1.6
		extremeWingCfgDevVpnIkev1DpdRetries OBJECT-TYPE
			SYNTAX Unsigned32 (1..100)
			MAX-ACCESS read-write
			STATUS current
			DESCRIPTION
				"Number of keepalive messages to send before declaring a peer dead.
				
				XPath: /extremeWing-config/device[mac=key1]/ikev1_policy[name=key2]/dpd_retries"
			DEFVAL { 5 }
			::= { extremeWingCfgDevVpnIkev1Entry 6 }

		
		-- 1.3.6.1.4.1.1916.2.131.50.1.3.18.19.3
		extremeWingCfgDevVpnIkev1IsakmpTable OBJECT-TYPE
			SYNTAX SEQUENCE OF ExtremeWingCfgDevVpnIkev1IsakmpEntry
			MAX-ACCESS not-accessible
			STATUS current
			DESCRIPTION
				"
				
				/extremeWing-config/device/ikev1_policy/isakmp_proposal"
			::= { extremeWingCfgDevVpn 3 }

		
		-- 1.3.6.1.4.1.1916.2.131.50.1.3.18.19.3.1
		extremeWingCfgDevVpnIkev1IsakmpEntry OBJECT-TYPE
			SYNTAX ExtremeWingCfgDevVpnIkev1IsakmpEntry
			MAX-ACCESS not-accessible
			STATUS current
			DESCRIPTION
				"An entry in the table."
			INDEX { extremeWingCfgDevMac, extremeWingCfgDevVpnIkev1Name, extremeWingCfgDevVpnIkev1IsakmpName }
			::= { extremeWingCfgDevVpnIkev1IsakmpTable 1 }

		
		ExtremeWingCfgDevVpnIkev1IsakmpEntry ::=
			SEQUENCE { 
				extremeWingCfgDevVpnIkev1IsakmpName
					ExtremeWingIdentifier,
				extremeWingCfgDevVpnIkev1IsakmpEncryption
					DisplayString,
				extremeWingCfgDevVpnIkev1IsakmpGroup
					DisplayString,
				extremeWingCfgDevVpnIkev1IsakmpHash
					DisplayString
			 }

		-- 1.3.6.1.4.1.1916.2.131.50.1.3.18.19.3.1.1
		extremeWingCfgDevVpnIkev1IsakmpName OBJECT-TYPE
			SYNTAX ExtremeWingIdentifier
			MAX-ACCESS read-only
			STATUS current
			DESCRIPTION
				"
				
				XPath: /extremeWing-config/device[mac=key1]/ikev1_policy[name=key2]/isakmp_proposal[name=key3]/name"
			::= { extremeWingCfgDevVpnIkev1IsakmpEntry 1 }

		
		-- 1.3.6.1.4.1.1916.2.131.50.1.3.18.19.3.1.3
		extremeWingCfgDevVpnIkev1IsakmpEncryption OBJECT-TYPE
			SYNTAX DisplayString
			MAX-ACCESS read-write
			STATUS current
			DESCRIPTION
				"Encryption method protecting data transmitted between peers.
				
				Values:
				3des,
				aes,
				aes-192,
				aes-256
				
				XPath: /extremeWing-config/device[mac=key1]/ikev1_policy[name=key2]/isakmp_proposal[name=key3]/encryption"
			DEFVAL { "aes-256" }
			::= { extremeWingCfgDevVpnIkev1IsakmpEntry 3 }

		
		-- 1.3.6.1.4.1.1916.2.131.50.1.3.18.19.3.1.4
		extremeWingCfgDevVpnIkev1IsakmpGroup OBJECT-TYPE
			SYNTAX DisplayString
			MAX-ACCESS read-write
			STATUS current
			DESCRIPTION
				"Diffie-Hellman group identifier. IPsec peers use the defined value to derive a shared secret without transmitting.
				
				Values:
				2,
				5,
				14
				
				XPath: /extremeWing-config/device[mac=key1]/ikev1_policy[name=key2]/isakmp_proposal[name=key3]/group"
			DEFVAL { "2" }
			::= { extremeWingCfgDevVpnIkev1IsakmpEntry 4 }

		
		-- 1.3.6.1.4.1.1916.2.131.50.1.3.18.19.3.1.5
		extremeWingCfgDevVpnIkev1IsakmpHash OBJECT-TYPE
			SYNTAX DisplayString
			MAX-ACCESS read-write
			STATUS current
			DESCRIPTION
				"Hash algorithm used to ensure data integrity.
				
				Values:
				md5,
				sha
				
				XPath: /extremeWing-config/device[mac=key1]/ikev1_policy[name=key2]/isakmp_proposal[name=key3]/hash"
			DEFVAL { "sha" }
			::= { extremeWingCfgDevVpnIkev1IsakmpEntry 5 }

		
		-- 1.3.6.1.4.1.1916.2.131.50.1.3.18.19.4
		extremeWingCfgDevVpnIkev2Table OBJECT-TYPE
			SYNTAX SEQUENCE OF ExtremeWingCfgDevVpnIkev2Entry
			MAX-ACCESS not-accessible
			STATUS current
			DESCRIPTION
				"
				
				/extremeWing-config/device/ikev2_policy"
			::= { extremeWingCfgDevVpn 4 }

		
		-- 1.3.6.1.4.1.1916.2.131.50.1.3.18.19.4.1
		extremeWingCfgDevVpnIkev2Entry OBJECT-TYPE
			SYNTAX ExtremeWingCfgDevVpnIkev2Entry
			MAX-ACCESS not-accessible
			STATUS current
			DESCRIPTION
				"An entry in the table."
			INDEX { extremeWingCfgDevMac, extremeWingCfgDevVpnIkev2Name }
			::= { extremeWingCfgDevVpnIkev2Table 1 }

		
		ExtremeWingCfgDevVpnIkev2Entry ::=
			SEQUENCE { 
				extremeWingCfgDevVpnIkev2Name
					ExtremeWingIdentifier,
				extremeWingCfgDevVpnIkev2IkeLifetime
					Unsigned32,
				extremeWingCfgDevVpnIkev2DpdKeepalive
					Unsigned32
			 }

		-- 1.3.6.1.4.1.1916.2.131.50.1.3.18.19.4.1.1
		extremeWingCfgDevVpnIkev2Name OBJECT-TYPE
			SYNTAX ExtremeWingIdentifier
			MAX-ACCESS read-only
			STATUS current
			DESCRIPTION
				"
				
				XPath: /extremeWing-config/device[mac=key1]/ikev2_policy[name=key2]/name"
			::= { extremeWingCfgDevVpnIkev2Entry 1 }

		
		-- 1.3.6.1.4.1.1916.2.131.50.1.3.18.19.4.1.3
		extremeWingCfgDevVpnIkev2IkeLifetime OBJECT-TYPE
			SYNTAX Unsigned32 (600..2147483646)
			UNITS "seconds"
			MAX-ACCESS read-write
			STATUS current
			DESCRIPTION
				"Lifetime in seconds for IKE Security Association (ISAKMP SA).
				
				XPath: /extremeWing-config/device[mac=key1]/ikev2_policy[name=key2]/isakmp_lifetime"
			DEFVAL { 86400 }
			::= { extremeWingCfgDevVpnIkev2Entry 3 }

		
		-- 1.3.6.1.4.1.1916.2.131.50.1.3.18.19.4.1.4
		extremeWingCfgDevVpnIkev2DpdKeepalive OBJECT-TYPE
			SYNTAX Unsigned32 (10..3600)
			UNITS "seconds"
			MAX-ACCESS read-write
			STATUS current
			DESCRIPTION
				"Frequency of IKE keepalive messages for Dead Peer Detection.
				
				XPath: /extremeWing-config/device[mac=key1]/ikev2_policy[name=key2]/dpd_keepalive"
			DEFVAL { 10 }
			::= { extremeWingCfgDevVpnIkev2Entry 4 }

		
		-- 1.3.6.1.4.1.1916.2.131.50.1.3.18.19.5
		extremeWingCfgDevVpnIkev2IsakmpTable OBJECT-TYPE
			SYNTAX SEQUENCE OF ExtremeWingCfgDevVpnIkev2IsakmpEntry
			MAX-ACCESS not-accessible
			STATUS current
			DESCRIPTION
				"
				
				/extremeWing-config/device/ikev2_policy/isakmp_proposal"
			::= { extremeWingCfgDevVpn 5 }

		
		-- 1.3.6.1.4.1.1916.2.131.50.1.3.18.19.5.1
		extremeWingCfgDevVpnIkev2IsakmpEntry OBJECT-TYPE
			SYNTAX ExtremeWingCfgDevVpnIkev2IsakmpEntry
			MAX-ACCESS not-accessible
			STATUS current
			DESCRIPTION
				"An entry in the table."
			INDEX { extremeWingCfgDevMac, extremeWingCfgDevVpnIkev2Name, extremeWingCfgDevVpnIkev2IsakmpName }
			::= { extremeWingCfgDevVpnIkev2IsakmpTable 1 }

		
		ExtremeWingCfgDevVpnIkev2IsakmpEntry ::=
			SEQUENCE { 
				extremeWingCfgDevVpnIkev2IsakmpName
					ExtremeWingIdentifier,
				extremeWingCfgDevVpnIkev2IsakmpEncryption
					DisplayString,
				extremeWingCfgDevVpnIkev2IsakmpGroup
					DisplayString,
				extremeWingCfgDevVpnIkev2IsakmpHash
					DisplayString
			 }

		-- 1.3.6.1.4.1.1916.2.131.50.1.3.18.19.5.1.1
		extremeWingCfgDevVpnIkev2IsakmpName OBJECT-TYPE
			SYNTAX ExtremeWingIdentifier
			MAX-ACCESS read-only
			STATUS current
			DESCRIPTION
				"
				
				XPath: /extremeWing-config/device[mac=key1]/ikev2_policy[name=key2]/isakmp_proposal[name=key3]/name"
			::= { extremeWingCfgDevVpnIkev2IsakmpEntry 1 }

		
		-- 1.3.6.1.4.1.1916.2.131.50.1.3.18.19.5.1.3
		extremeWingCfgDevVpnIkev2IsakmpEncryption OBJECT-TYPE
			SYNTAX DisplayString
			MAX-ACCESS read-write
			STATUS current
			DESCRIPTION
				"Encryption method protecting data transmitted between peers.
				
				Values:
				3des,
				aes,
				aes-192,
				aes-256
				
				XPath: /extremeWing-config/device[mac=key1]/ikev2_policy[name=key2]/isakmp_proposal[name=key3]/encryption"
			DEFVAL { "aes-256" }
			::= { extremeWingCfgDevVpnIkev2IsakmpEntry 3 }

		
		-- 1.3.6.1.4.1.1916.2.131.50.1.3.18.19.5.1.4
		extremeWingCfgDevVpnIkev2IsakmpGroup OBJECT-TYPE
			SYNTAX DisplayString
			MAX-ACCESS read-write
			STATUS current
			DESCRIPTION
				"Diffie-Hellman group identifier. IPsec peers use the defined value to derive a shared secret without transmitting.
				
				Values:
				2,
				5,
				14
				
				XPath: /extremeWing-config/device[mac=key1]/ikev2_policy[name=key2]/isakmp_proposal[name=key3]/group"
			DEFVAL { "2" }
			::= { extremeWingCfgDevVpnIkev2IsakmpEntry 4 }

		
		-- 1.3.6.1.4.1.1916.2.131.50.1.3.18.19.5.1.5
		extremeWingCfgDevVpnIkev2IsakmpHash OBJECT-TYPE
			SYNTAX DisplayString
			MAX-ACCESS read-write
			STATUS current
			DESCRIPTION
				"Hash algorithm used to ensure data integrity.
				
				Values:
				md5,
				sha
				
				XPath: /extremeWing-config/device[mac=key1]/ikev2_policy[name=key2]/isakmp_proposal[name=key3]/hash"
			DEFVAL { "sha" }
			::= { extremeWingCfgDevVpnIkev2IsakmpEntry 5 }

		
		-- 1.3.6.1.4.1.1916.2.131.50.1.3.18.19.6
		extremeWingCfgDevVpnIkev1PeerTable OBJECT-TYPE
			SYNTAX SEQUENCE OF ExtremeWingCfgDevVpnIkev1PeerEntry
			MAX-ACCESS not-accessible
			STATUS current
			DESCRIPTION
				"
				
				/extremeWing-config/device/ikev1_peer"
			::= { extremeWingCfgDevVpn 6 }

		
		-- 1.3.6.1.4.1.1916.2.131.50.1.3.18.19.6.1
		extremeWingCfgDevVpnIkev1PeerEntry OBJECT-TYPE
			SYNTAX ExtremeWingCfgDevVpnIkev1PeerEntry
			MAX-ACCESS not-accessible
			STATUS current
			DESCRIPTION
				"An entry in the table."
			INDEX { extremeWingCfgDevMac, extremeWingCfgDevVpnIkev1PeerName }
			::= { extremeWingCfgDevVpnIkev1PeerTable 1 }

		
		ExtremeWingCfgDevVpnIkev1PeerEntry ::=
			SEQUENCE { 
				extremeWingCfgDevVpnIkev1PeerName
					ExtremeWingIdentifier,
				extremeWingCfgDevVpnIkev1PeerIpType
					DisplayString,
				extremeWingCfgDevVpnIkev1PeerIpValue
					DisplayString,
				extremeWingCfgDevVpnIkev1PeerAuthType
					DisplayString,
				extremeWingCfgDevVpnIkev1PeerAuthKey
					DisplayString,
				extremeWingCfgDevVpnIkev1PeerLocalidType
					DisplayString,
				extremeWingCfgDevVpnIkev1PeerLocalidValue
					DisplayString,
				extremeWingCfgDevVpnIkev1PeerRemoteidType
					DisplayString,
				extremeWingCfgDevVpnIkev1PeerRemoteidValue
					DisplayString,
				extremeWingCfgDevVpnIkev1PeerIkev1Policy
					ExtremeWingIdentifier
			 }

		-- 1.3.6.1.4.1.1916.2.131.50.1.3.18.19.6.1.1
		extremeWingCfgDevVpnIkev1PeerName OBJECT-TYPE
			SYNTAX ExtremeWingIdentifier
			MAX-ACCESS read-only
			STATUS current
			DESCRIPTION
				"
				
				XPath: /extremeWing-config/device[mac=key1]/ikev1_peer[name=key2]/name"
			::= { extremeWingCfgDevVpnIkev1PeerEntry 1 }

		
		-- 1.3.6.1.4.1.1916.2.131.50.1.3.18.19.6.1.3
		extremeWingCfgDevVpnIkev1PeerIpType OBJECT-TYPE
			SYNTAX DisplayString
			MAX-ACCESS read-write
			STATUS current
			DESCRIPTION
				"IP address/fqdn of the IPSEC VPN peer for tunnel setup
				
				Values:
				address,
				fqdn
				
				XPath: /extremeWing-config/device[mac=key1]/ikev1_peer[name=key2]/ip/type"
			DEFVAL { "address" }
			::= { extremeWingCfgDevVpnIkev1PeerEntry 3 }

		
		-- 1.3.6.1.4.1.1916.2.131.50.1.3.18.19.6.1.4
		extremeWingCfgDevVpnIkev1PeerIpValue OBJECT-TYPE
			SYNTAX DisplayString (SIZE (1..64))
			MAX-ACCESS read-write
			STATUS current
			DESCRIPTION
				"Peer IP can be specified as either IP or FQDN.
				
				XPath: /extremeWing-config/device[mac=key1]/ikev1_peer[name=key2]/ip/value"
			::= { extremeWingCfgDevVpnIkev1PeerEntry 4 }

		
		-- 1.3.6.1.4.1.1916.2.131.50.1.3.18.19.6.1.5
		extremeWingCfgDevVpnIkev1PeerAuthType OBJECT-TYPE
			SYNTAX DisplayString
			MAX-ACCESS read-write
			STATUS current
			DESCRIPTION
				"
				
				Values:
				psk,
				rsa
				
				XPath: /extremeWing-config/device[mac=key1]/ikev1_peer[name=key2]/authentication/type"
			DEFVAL { "rsa" }
			::= { extremeWingCfgDevVpnIkev1PeerEntry 5 }

		
		-- 1.3.6.1.4.1.1916.2.131.50.1.3.18.19.6.1.6
		extremeWingCfgDevVpnIkev1PeerAuthKey OBJECT-TYPE
			SYNTAX DisplayString (SIZE (8..21))
			MAX-ACCESS read-write
			STATUS current
			DESCRIPTION
				"The shared secret used for peer authentication.
				
				XPath: /extremeWing-config/device[mac=key1]/ikev1_peer[name=key2]/authentication/key"
			::= { extremeWingCfgDevVpnIkev1PeerEntry 6 }

		
		-- 1.3.6.1.4.1.1916.2.131.50.1.3.18.19.6.1.7
		extremeWingCfgDevVpnIkev1PeerLocalidType OBJECT-TYPE
			SYNTAX DisplayString
			MAX-ACCESS read-write
			STATUS current
			DESCRIPTION
				"Local identity to use in IKE exchange with this peer.
				
				Values:
				address,
				dn,
				fqdn,
				email,
				string
				
				XPath: /extremeWing-config/device[mac=key1]/ikev1_peer[name=key2]/localid/localid_type"
			DEFVAL { "'string'" }
			::= { extremeWingCfgDevVpnIkev1PeerEntry 7 }

		
		-- 1.3.6.1.4.1.1916.2.131.50.1.3.18.19.6.1.8
		extremeWingCfgDevVpnIkev1PeerLocalidValue OBJECT-TYPE
			SYNTAX DisplayString (SIZE (1..128))
			MAX-ACCESS read-write
			STATUS current
			DESCRIPTION
				"
				
				XPath: /extremeWing-config/device[mac=key1]/ikev1_peer[name=key2]/localid/localid_value"
			::= { extremeWingCfgDevVpnIkev1PeerEntry 8 }

		
		-- 1.3.6.1.4.1.1916.2.131.50.1.3.18.19.6.1.9
		extremeWingCfgDevVpnIkev1PeerRemoteidType OBJECT-TYPE
			SYNTAX DisplayString
			MAX-ACCESS read-write
			STATUS current
			DESCRIPTION
				"Peer identity of this peer.
				
				Values:
				address,
				dn,
				fqdn,
				email,
				string
				
				XPath: /extremeWing-config/device[mac=key1]/ikev1_peer[name=key2]/remoteid/remoteid_type"
			DEFVAL { "'string'" }
			::= { extremeWingCfgDevVpnIkev1PeerEntry 9 }

		
		-- 1.3.6.1.4.1.1916.2.131.50.1.3.18.19.6.1.10
		extremeWingCfgDevVpnIkev1PeerRemoteidValue OBJECT-TYPE
			SYNTAX DisplayString (SIZE (1..128))
			MAX-ACCESS read-write
			STATUS current
			DESCRIPTION
				"
				
				XPath: /extremeWing-config/device[mac=key1]/ikev1_peer[name=key2]/remoteid/remoteid_value"
			::= { extremeWingCfgDevVpnIkev1PeerEntry 10 }

		
		-- 1.3.6.1.4.1.1916.2.131.50.1.3.18.19.6.1.11
		extremeWingCfgDevVpnIkev1PeerIkev1Policy OBJECT-TYPE
			SYNTAX ExtremeWingIdentifier
			MAX-ACCESS read-write
			STATUS current
			DESCRIPTION
				"
				
				XPath: /extremeWing-config/device[mac=key1]/ikev1_peer[name=key2]/ikev1_policy"
			::= { extremeWingCfgDevVpnIkev1PeerEntry 11 }

		
		-- 1.3.6.1.4.1.1916.2.131.50.1.3.18.19.7
		extremeWingCfgDevVpnIkev2PeerTable OBJECT-TYPE
			SYNTAX SEQUENCE OF ExtremeWingCfgDevVpnIkev2PeerEntry
			MAX-ACCESS not-accessible
			STATUS current
			DESCRIPTION
				"
				
				/extremeWing-config/device/ikev2_peer"
			::= { extremeWingCfgDevVpn 7 }

		
		-- 1.3.6.1.4.1.1916.2.131.50.1.3.18.19.7.1
		extremeWingCfgDevVpnIkev2PeerEntry OBJECT-TYPE
			SYNTAX ExtremeWingCfgDevVpnIkev2PeerEntry
			MAX-ACCESS not-accessible
			STATUS current
			DESCRIPTION
				"An entry in the table."
			INDEX { extremeWingCfgDevMac, extremeWingCfgDevVpnIkev2PeerName }
			::= { extremeWingCfgDevVpnIkev2PeerTable 1 }

		
		ExtremeWingCfgDevVpnIkev2PeerEntry ::=
			SEQUENCE { 
				extremeWingCfgDevVpnIkev2PeerName
					ExtremeWingIdentifier,
				extremeWingCfgDevVpnIkev2PeerIpType
					DisplayString,
				extremeWingCfgDevVpnIkev2PeerIpValue
					DisplayString,
				extremeWingCfgDevVpnIkev2PeerLocalAuthType
					DisplayString,
				extremeWingCfgDevVpnIkev2PeerLocalAuthKey
					DisplayString,
				extremeWingCfgDevVpnIkev2PeerRemoteAuthType
					DisplayString,
				extremeWingCfgDevVpnIkev2PeerRemoteAuthKey
					DisplayString,
				extremeWingCfgDevVpnIkev2PeerLocalidType
					DisplayString,
				extremeWingCfgDevVpnIkev2PeerLocalidValue
					DisplayString,
				extremeWingCfgDevVpnIkev2PeerRemoteidType
					DisplayString,
				extremeWingCfgDevVpnIkev2PeerRemoteidValue
					DisplayString,
				extremeWingCfgDevVpnIkev2PeerIkev2Policy
					ExtremeWingIdentifier
			 }

		-- 1.3.6.1.4.1.1916.2.131.50.1.3.18.19.7.1.1
		extremeWingCfgDevVpnIkev2PeerName OBJECT-TYPE
			SYNTAX ExtremeWingIdentifier
			MAX-ACCESS read-only
			STATUS current
			DESCRIPTION
				"
				
				XPath: /extremeWing-config/device[mac=key1]/ikev2_peer[name=key2]/name"
			::= { extremeWingCfgDevVpnIkev2PeerEntry 1 }

		
		-- 1.3.6.1.4.1.1916.2.131.50.1.3.18.19.7.1.3
		extremeWingCfgDevVpnIkev2PeerIpType OBJECT-TYPE
			SYNTAX DisplayString
			MAX-ACCESS read-write
			STATUS current
			DESCRIPTION
				"IP address/hostname of the IPSEC VPN peer for tunnel setup
				
				Values:
				address,
				fqdn
				
				XPath: /extremeWing-config/device[mac=key1]/ikev2_peer[name=key2]/ip/type"
			DEFVAL { "address" }
			::= { extremeWingCfgDevVpnIkev2PeerEntry 3 }

		
		-- 1.3.6.1.4.1.1916.2.131.50.1.3.18.19.7.1.4
		extremeWingCfgDevVpnIkev2PeerIpValue OBJECT-TYPE
			SYNTAX DisplayString (SIZE (1..64))
			MAX-ACCESS read-write
			STATUS current
			DESCRIPTION
				"Peer IP can be specified as either IP or FQDN.
				
				XPath: /extremeWing-config/device[mac=key1]/ikev2_peer[name=key2]/ip/value"
			::= { extremeWingCfgDevVpnIkev2PeerEntry 4 }

		
		-- 1.3.6.1.4.1.1916.2.131.50.1.3.18.19.7.1.5
		extremeWingCfgDevVpnIkev2PeerLocalAuthType OBJECT-TYPE
			SYNTAX DisplayString
			MAX-ACCESS read-write
			STATUS current
			DESCRIPTION
				"
				
				Values:
				psk,
				rsa
				
				XPath: /extremeWing-config/device[mac=key1]/ikev2_peer[name=key2]/local_authentication/type"
			DEFVAL { "rsa" }
			::= { extremeWingCfgDevVpnIkev2PeerEntry 5 }

		
		-- 1.3.6.1.4.1.1916.2.131.50.1.3.18.19.7.1.6
		extremeWingCfgDevVpnIkev2PeerLocalAuthKey OBJECT-TYPE
			SYNTAX DisplayString (SIZE (8..21))
			MAX-ACCESS read-write
			STATUS current
			DESCRIPTION
				"The shared secret used for local peer authentication.
				
				XPath: /extremeWing-config/device[mac=key1]/ikev2_peer[name=key2]/local_authentication/key"
			::= { extremeWingCfgDevVpnIkev2PeerEntry 6 }

		
		-- 1.3.6.1.4.1.1916.2.131.50.1.3.18.19.7.1.7
		extremeWingCfgDevVpnIkev2PeerRemoteAuthType OBJECT-TYPE
			SYNTAX DisplayString
			MAX-ACCESS read-write
			STATUS current
			DESCRIPTION
				"
				
				Values:
				psk,
				rsa
				
				XPath: /extremeWing-config/device[mac=key1]/ikev2_peer[name=key2]/remote_authentication/type"
			DEFVAL { "rsa" }
			::= { extremeWingCfgDevVpnIkev2PeerEntry 7 }

		
		-- 1.3.6.1.4.1.1916.2.131.50.1.3.18.19.7.1.8
		extremeWingCfgDevVpnIkev2PeerRemoteAuthKey OBJECT-TYPE
			SYNTAX DisplayString (SIZE (8..21))
			MAX-ACCESS read-write
			STATUS current
			DESCRIPTION
				"The shared secret used for remote peer authentication.
				
				XPath: /extremeWing-config/device[mac=key1]/ikev2_peer[name=key2]/remote_authentication/key"
			::= { extremeWingCfgDevVpnIkev2PeerEntry 8 }

		
		-- 1.3.6.1.4.1.1916.2.131.50.1.3.18.19.7.1.9
		extremeWingCfgDevVpnIkev2PeerLocalidType OBJECT-TYPE
			SYNTAX DisplayString
			MAX-ACCESS read-write
			STATUS current
			DESCRIPTION
				"Local identity to use in IKE exchange with this peer.
				
				Values:
				address,
				dn,
				fqdn,
				email,
				string
				
				XPath: /extremeWing-config/device[mac=key1]/ikev2_peer[name=key2]/localid/localid_type"
			DEFVAL { "'string'" }
			::= { extremeWingCfgDevVpnIkev2PeerEntry 9 }

		
		-- 1.3.6.1.4.1.1916.2.131.50.1.3.18.19.7.1.10
		extremeWingCfgDevVpnIkev2PeerLocalidValue OBJECT-TYPE
			SYNTAX DisplayString (SIZE (1..128))
			MAX-ACCESS read-write
			STATUS current
			DESCRIPTION
				"
				
				XPath: /extremeWing-config/device[mac=key1]/ikev2_peer[name=key2]/localid/localid_value"
			::= { extremeWingCfgDevVpnIkev2PeerEntry 10 }

		
		-- 1.3.6.1.4.1.1916.2.131.50.1.3.18.19.7.1.11
		extremeWingCfgDevVpnIkev2PeerRemoteidType OBJECT-TYPE
			SYNTAX DisplayString
			MAX-ACCESS read-write
			STATUS current
			DESCRIPTION
				"Peer identity of this peer.
				
				Values:
				address,
				dn,
				fqdn,
				email,
				string
				
				XPath: /extremeWing-config/device[mac=key1]/ikev2_peer[name=key2]/remoteid/remoteid_type"
			DEFVAL { "'string'" }
			::= { extremeWingCfgDevVpnIkev2PeerEntry 11 }

		
		-- 1.3.6.1.4.1.1916.2.131.50.1.3.18.19.7.1.12
		extremeWingCfgDevVpnIkev2PeerRemoteidValue OBJECT-TYPE
			SYNTAX DisplayString (SIZE (1..128))
			MAX-ACCESS read-write
			STATUS current
			DESCRIPTION
				"
				
				XPath: /extremeWing-config/device[mac=key1]/ikev2_peer[name=key2]/remoteid/remoteid_value"
			::= { extremeWingCfgDevVpnIkev2PeerEntry 12 }

		
		-- 1.3.6.1.4.1.1916.2.131.50.1.3.18.19.7.1.13
		extremeWingCfgDevVpnIkev2PeerIkev2Policy OBJECT-TYPE
			SYNTAX ExtremeWingIdentifier
			MAX-ACCESS read-write
			STATUS current
			DESCRIPTION
				"IKEv2 Policy to use with this peer.
				
				XPath: /extremeWing-config/device[mac=key1]/ikev2_peer[name=key2]/ikev2_policy"
			::= { extremeWingCfgDevVpnIkev2PeerEntry 13 }

		
		-- 1.3.6.1.4.1.1916.2.131.50.1.3.18.19.8
		extremeWingCfgDevVpnTransformTable OBJECT-TYPE
			SYNTAX SEQUENCE OF ExtremeWingCfgDevVpnTransformEntry
			MAX-ACCESS not-accessible
			STATUS current
			DESCRIPTION
				"
				
				/extremeWing-config/device/ipsec_transform_set"
			::= { extremeWingCfgDevVpn 8 }

		
		-- 1.3.6.1.4.1.1916.2.131.50.1.3.18.19.8.1
		extremeWingCfgDevVpnTransformEntry OBJECT-TYPE
			SYNTAX ExtremeWingCfgDevVpnTransformEntry
			MAX-ACCESS not-accessible
			STATUS current
			DESCRIPTION
				"An entry in the table."
			INDEX { extremeWingCfgDevMac, extremeWingCfgDevVpnTransformName }
			::= { extremeWingCfgDevVpnTransformTable 1 }

		
		ExtremeWingCfgDevVpnTransformEntry ::=
			SEQUENCE { 
				extremeWingCfgDevVpnTransformName
					ExtremeWingIdentifier,
				extremeWingCfgDevVpnTransformCipherAlgo
					DisplayString,
				extremeWingCfgDevVpnTransformAuthAlgo
					DisplayString,
				extremeWingCfgDevVpnTransformMode
					DisplayString
			 }

		-- 1.3.6.1.4.1.1916.2.131.50.1.3.18.19.8.1.1
		extremeWingCfgDevVpnTransformName OBJECT-TYPE
			SYNTAX ExtremeWingIdentifier
			MAX-ACCESS read-only
			STATUS current
			DESCRIPTION
				"
				
				XPath: /extremeWing-config/device[mac=key1]/ipsec_transform_set[name=key2]/name"
			::= { extremeWingCfgDevVpnTransformEntry 1 }

		
		-- 1.3.6.1.4.1.1916.2.131.50.1.3.18.19.8.1.3
		extremeWingCfgDevVpnTransformCipherAlgo OBJECT-TYPE
			SYNTAX DisplayString
			MAX-ACCESS read-write
			STATUS current
			DESCRIPTION
				"Encryption method protecting data transmission.
				
				Values:
				esp-null,
				des,
				3des,
				aes,
				aes-192,
				aes-256
				
				XPath: /extremeWing-config/device[mac=key1]/ipsec_transform_set[name=key2]/cipher_algo"
			DEFVAL { "aes-256" }
			::= { extremeWingCfgDevVpnTransformEntry 3 }

		
		-- 1.3.6.1.4.1.1916.2.131.50.1.3.18.19.8.1.4
		extremeWingCfgDevVpnTransformAuthAlgo OBJECT-TYPE
			SYNTAX DisplayString
			MAX-ACCESS read-write
			STATUS current
			DESCRIPTION
				"Authentication scheme used to validate identity.
				
				Values:
				md5-hmac,
				sha-hmac
				
				XPath: /extremeWing-config/device[mac=key1]/ipsec_transform_set[name=key2]/auth_algo"
			DEFVAL { "sha-hmac" }
			::= { extremeWingCfgDevVpnTransformEntry 4 }

		
		-- 1.3.6.1.4.1.1916.2.131.50.1.3.18.19.8.1.5
		extremeWingCfgDevVpnTransformMode OBJECT-TYPE
			SYNTAX DisplayString
			MAX-ACCESS read-write
			STATUS current
			DESCRIPTION
				"IPsec tunnel type - tunnel mode is used for site-to-site vpn and transport mode is used to remote-vpn.
				
				Values:
				tunnel,
				transport
				
				XPath: /extremeWing-config/device[mac=key1]/ipsec_transform_set[name=key2]/mode"
			DEFVAL { "tunnel" }
			::= { extremeWingCfgDevVpnTransformEntry 5 }

		
		-- 1.3.6.1.4.1.1916.2.131.50.1.3.18.19.9
		extremeWingCfgDevVpnCryptoTable OBJECT-TYPE
			SYNTAX SEQUENCE OF ExtremeWingCfgDevVpnCryptoEntry
			MAX-ACCESS not-accessible
			STATUS current
			DESCRIPTION
				"
				
				/extremeWing-config/device/crypto_map"
			::= { extremeWingCfgDevVpn 9 }

		
		-- 1.3.6.1.4.1.1916.2.131.50.1.3.18.19.9.1
		extremeWingCfgDevVpnCryptoEntry OBJECT-TYPE
			SYNTAX ExtremeWingCfgDevVpnCryptoEntry
			MAX-ACCESS not-accessible
			STATUS current
			DESCRIPTION
				"An entry in the table."
			INDEX { extremeWingCfgDevMac, extremeWingCfgDevVpnCryptoName }
			::= { extremeWingCfgDevVpnCryptoTable 1 }

		
		ExtremeWingCfgDevVpnCryptoEntry ::=
			SEQUENCE { 
				extremeWingCfgDevVpnCryptoName
					ExtremeWingIdentifier
			 }

		-- 1.3.6.1.4.1.1916.2.131.50.1.3.18.19.9.1.1
		extremeWingCfgDevVpnCryptoName OBJECT-TYPE
			SYNTAX ExtremeWingIdentifier
			MAX-ACCESS read-only
			STATUS current
			DESCRIPTION
				"
				
				XPath: /extremeWing-config/device[mac=key1]/crypto_map[name=key2]/name"
			::= { extremeWingCfgDevVpnCryptoEntry 1 }

		
		-- 1.3.6.1.4.1.1916.2.131.50.1.3.18.19.10
		extremeWingCfgDevVpnCryptoInstTable OBJECT-TYPE
			SYNTAX SEQUENCE OF ExtremeWingCfgDevVpnCryptoInstEntry
			MAX-ACCESS not-accessible
			STATUS current
			DESCRIPTION
				"
				
				/extremeWing-config/device/crypto_map/crypto_map_entry"
			::= { extremeWingCfgDevVpn 10 }

		
		-- 1.3.6.1.4.1.1916.2.131.50.1.3.18.19.10.1
		extremeWingCfgDevVpnCryptoInstEntry OBJECT-TYPE
			SYNTAX ExtremeWingCfgDevVpnCryptoInstEntry
			MAX-ACCESS not-accessible
			STATUS current
			DESCRIPTION
				"An entry in the table."
			INDEX { extremeWingCfgDevMac, extremeWingCfgDevVpnCryptoName, extremeWingCfgDevVpnCryptoInstSequence }
			::= { extremeWingCfgDevVpnCryptoInstTable 1 }

		
		ExtremeWingCfgDevVpnCryptoInstEntry ::=
			SEQUENCE { 
				extremeWingCfgDevVpnCryptoInstSequence
					Unsigned32,
				extremeWingCfgDevVpnCryptoInstType
					DisplayString,
				extremeWingCfgDevVpnCryptoInstIpAcl
					ExtremeWingIdentifier,
				extremeWingCfgDevVpnCryptoInstTransformSet
					ExtremeWingIdentifier,
				extremeWingCfgDevVpnCryptoInstLocalip
					DisplayString,
				extremeWingCfgDevVpnCryptoInstPfs
					DisplayString,
				extremeWingCfgDevVpnCryptoInstLifetimeSeconds
					Unsigned32,
				extremeWingCfgDevVpnCryptoInstLifetimeKb
					Unsigned32,
				extremeWingCfgDevVpnCryptoInstRemoteType
					DisplayString,
				extremeWingCfgDevVpnCryptoInstModeconfig
					DisplayString,
				extremeWingCfgDevVpnCryptoInstPeer
					DisplayString,
				extremeWingCfgDevVpnCryptoInstProtocol
					DisplayString,
				extremeWingCfgDevVpnCryptoInstMode
					DisplayString
			 }

		-- 1.3.6.1.4.1.1916.2.131.50.1.3.18.19.10.1.1
		extremeWingCfgDevVpnCryptoInstSequence OBJECT-TYPE
			SYNTAX Unsigned32 (1..1000)
			MAX-ACCESS read-only
			STATUS current
			DESCRIPTION
				"
				
				XPath: /extremeWing-config/device[mac=key1]/crypto_map[name=key2]/crypto_map_entry[sequence=key3]/sequence"
			::= { extremeWingCfgDevVpnCryptoInstEntry 1 }

		
		-- 1.3.6.1.4.1.1916.2.131.50.1.3.18.19.10.1.3
		extremeWingCfgDevVpnCryptoInstType OBJECT-TYPE
			SYNTAX DisplayString
			MAX-ACCESS read-write
			STATUS current
			DESCRIPTION
				"
				
				Values:
				site-to-site-auto,
				remote-vpn,
				site-to-site-manual
				
				XPath: /extremeWing-config/device[mac=key1]/crypto_map[name=key2]/crypto_map_entry[sequence=key3]/type"
			DEFVAL { "site-to-site-auto" }
			::= { extremeWingCfgDevVpnCryptoInstEntry 3 }

		
		-- 1.3.6.1.4.1.1916.2.131.50.1.3.18.19.10.1.4
		extremeWingCfgDevVpnCryptoInstIpAcl OBJECT-TYPE
			SYNTAX ExtremeWingIdentifier
			MAX-ACCESS read-write
			STATUS current
			DESCRIPTION
				"Access list for traffic that should be protected by IPsec.
				
				XPath: /extremeWing-config/device[mac=key1]/crypto_map[name=key2]/crypto_map_entry[sequence=key3]/ip_acl"
			::= { extremeWingCfgDevVpnCryptoInstEntry 4 }

		
		-- 1.3.6.1.4.1.1916.2.131.50.1.3.18.19.10.1.5
		extremeWingCfgDevVpnCryptoInstTransformSet OBJECT-TYPE
			SYNTAX ExtremeWingIdentifier
			MAX-ACCESS read-write
			STATUS current
			DESCRIPTION
				"NOTE: This column is valid only if extremeWingCfgDevVpnCryptoInstType sets to site-to-site-auto or remote-vpn
				
				IPsec transform (encryption and hash algorithms) to use.
				
				XPath: /extremeWing-config/device[mac=key1]/crypto_map[name=key2]/crypto_map_entry[sequence=key3]/ipsec_transform_set"
			::= { extremeWingCfgDevVpnCryptoInstEntry 5 }

		
		-- 1.3.6.1.4.1.1916.2.131.50.1.3.18.19.10.1.6
		extremeWingCfgDevVpnCryptoInstLocalip OBJECT-TYPE
			SYNTAX DisplayString
			MAX-ACCESS read-write
			STATUS current
			DESCRIPTION
				"Use this IP as local tunnel endpoint address, instead of the interface IP (Advanced Configuration).
				
				XPath: /extremeWing-config/device[mac=key1]/crypto_map[name=key2]/crypto_map_entry[sequence=key3]/localip"
			::= { extremeWingCfgDevVpnCryptoInstEntry 6 }

		
		-- 1.3.6.1.4.1.1916.2.131.50.1.3.18.19.10.1.7
		extremeWingCfgDevVpnCryptoInstPfs OBJECT-TYPE
			SYNTAX DisplayString
			MAX-ACCESS read-write
			STATUS current
			DESCRIPTION
				"NOTE: This column is valid only if extremeWingCfgDevVpnCryptoInstType sets to site-to-site-auto or remote-vpn
				
				Perfect Forward Secrecy.
				
				Values:
				none,
				2,
				5,
				14
				
				XPath: /extremeWing-config/device[mac=key1]/crypto_map[name=key2]/crypto_map_entry[sequence=key3]/pfs"
			DEFVAL { "none" }
			::= { extremeWingCfgDevVpnCryptoInstEntry 7 }

		
		-- 1.3.6.1.4.1.1916.2.131.50.1.3.18.19.10.1.8
		extremeWingCfgDevVpnCryptoInstLifetimeSeconds OBJECT-TYPE
			SYNTAX Unsigned32 (120..2147483646)
			UNITS "seconds"
			MAX-ACCESS read-write
			STATUS current
			DESCRIPTION
				"Time-based IPsec security association lifetime.
				
				XPath: /extremeWing-config/device[mac=key1]/crypto_map[name=key2]/crypto_map_entry[sequence=key3]/lifetime_seconds"
			::= { extremeWingCfgDevVpnCryptoInstEntry 8 }

		
		-- 1.3.6.1.4.1.1916.2.131.50.1.3.18.19.10.1.9
		extremeWingCfgDevVpnCryptoInstLifetimeKb OBJECT-TYPE
			SYNTAX Unsigned32 (500..2147483646)
			UNITS "kilobytes"
			MAX-ACCESS read-write
			STATUS current
			DESCRIPTION
				"Volume-based IPsec security association lifetime.
				
				XPath: /extremeWing-config/device[mac=key1]/crypto_map[name=key2]/crypto_map_entry[sequence=key3]/lifetime_kb"
			::= { extremeWingCfgDevVpnCryptoInstEntry 9 }

		
		-- 1.3.6.1.4.1.1916.2.131.50.1.3.18.19.10.1.10
		extremeWingCfgDevVpnCryptoInstRemoteType OBJECT-TYPE
			SYNTAX DisplayString
			MAX-ACCESS read-write
			STATUS current
			DESCRIPTION
				"NOTE: This column is valid only if extremeWingCfgDevVpnCryptoInstType sets to remote-vpn
				
				Remote VPN client type.
				
				Values:
				none,
				xauth
				
				XPath: /extremeWing-config/device[mac=key1]/crypto_map[name=key2]/crypto_map_entry[sequence=key3]/remote_type"
			DEFVAL { "xauth" }
			::= { extremeWingCfgDevVpnCryptoInstEntry 10 }

		
		-- 1.3.6.1.4.1.1916.2.131.50.1.3.18.19.10.1.11
		extremeWingCfgDevVpnCryptoInstModeconfig OBJECT-TYPE
			SYNTAX DisplayString
			MAX-ACCESS read-write
			STATUS current
			DESCRIPTION
				"NOTE: This column is valid only if extremeWingCfgDevVpnCryptoInstType sets to remote-vpn
				
				Choose the modeconfig method to use.
				
				Values:
				push,
				pull
				
				XPath: /extremeWing-config/device[mac=key1]/crypto_map[name=key2]/crypto_map_entry[sequence=key3]/modeconfig"
			DEFVAL { "push" }
			::= { extremeWingCfgDevVpnCryptoInstEntry 11 }

		
		-- 1.3.6.1.4.1.1916.2.131.50.1.3.18.19.10.1.12
		extremeWingCfgDevVpnCryptoInstPeer OBJECT-TYPE
			SYNTAX DisplayString
			MAX-ACCESS read-write
			STATUS current
			DESCRIPTION
				"NOTE: This column is valid only if extremeWingCfgDevVpnCryptoInstType sets to site-to-site-manual
				
				Allowed Encryption/Decryption peer.
				
				XPath: /extremeWing-config/device[mac=key1]/crypto_map[name=key2]/crypto_map_entry[sequence=key3]/peer"
			::= { extremeWingCfgDevVpnCryptoInstEntry 12 }

		
		-- 1.3.6.1.4.1.1916.2.131.50.1.3.18.19.10.1.13
		extremeWingCfgDevVpnCryptoInstProtocol OBJECT-TYPE
			SYNTAX DisplayString
			MAX-ACCESS read-write
			STATUS current
			DESCRIPTION
				"NOTE: This column is valid only if extremeWingCfgDevVpnCryptoInstType sets to site-to-site-manual
				
				Procotol to be used to the IPsec tunnel. It can be ESP or AH.
				
				Values:
				ESP,
				AH
				
				XPath: /extremeWing-config/device[mac=key1]/crypto_map[name=key2]/crypto_map_entry[sequence=key3]/protocol"
			DEFVAL { "ESP" }
			::= { extremeWingCfgDevVpnCryptoInstEntry 13 }

		
		-- 1.3.6.1.4.1.1916.2.131.50.1.3.18.19.10.1.14
		extremeWingCfgDevVpnCryptoInstMode OBJECT-TYPE
			SYNTAX DisplayString
			MAX-ACCESS read-write
			STATUS current
			DESCRIPTION
				"NOTE: This column is valid only if extremeWingCfgDevVpnCryptoInstType sets to site-to-site-manual
				
				IPsec tunnel type - tunnel or transport mode.
				
				Values:
				tunnel,
				transport
				
				XPath: /extremeWing-config/device[mac=key1]/crypto_map[name=key2]/crypto_map_entry[sequence=key3]/mode"
			DEFVAL { "tunnel" }
			::= { extremeWingCfgDevVpnCryptoInstEntry 14 }

		
		-- 1.3.6.1.4.1.1916.2.131.50.1.3.18.19.11
		extremeWingCfgDevVpnCryptoInstPeerListTable OBJECT-TYPE
			SYNTAX SEQUENCE OF ExtremeWingCfgDevVpnCryptoInstPeerListEntry
			MAX-ACCESS not-accessible
			STATUS current
			DESCRIPTION
				"NOTE: Columns under this table are valid only if extremeWingCfgDevVpnCryptoInstType sets to site-to-site-auto or remote-vpn
				
				/extremeWing-config/device/crypto_map/crypto_map_entry"
			::= { extremeWingCfgDevVpn 11 }

		
		-- 1.3.6.1.4.1.1916.2.131.50.1.3.18.19.11.1
		extremeWingCfgDevVpnCryptoInstPeerListEntry OBJECT-TYPE
			SYNTAX ExtremeWingCfgDevVpnCryptoInstPeerListEntry
			MAX-ACCESS not-accessible
			STATUS current
			DESCRIPTION
				"An entry in the table."
			INDEX { extremeWingCfgDevMac, extremeWingCfgDevVpnCryptoName, extremeWingCfgDevVpnCryptoInstSequence, extremeWingCfgDevVpnCryptoInstPeerListPriority }
			::= { extremeWingCfgDevVpnCryptoInstPeerListTable 1 }

		
		ExtremeWingCfgDevVpnCryptoInstPeerListEntry ::=
			SEQUENCE { 
				extremeWingCfgDevVpnCryptoInstPeerListPriority
					Unsigned32,
				extremeWingCfgDevVpnCryptoInstPeerListType
					DisplayString,
				extremeWingCfgDevVpnCryptoInstPeerListIkev1Peer
					ExtremeWingIdentifier,
				extremeWingCfgDevVpnCryptoInstPeerListIkev2Peer
					ExtremeWingIdentifier
			 }

		-- 1.3.6.1.4.1.1916.2.131.50.1.3.18.19.11.1.1
		extremeWingCfgDevVpnCryptoInstPeerListPriority OBJECT-TYPE
			SYNTAX Unsigned32 (1..3)
			MAX-ACCESS read-only
			STATUS current
			DESCRIPTION
				"List of prioritized redundant peers.
				
				XPath: /extremeWing-config/device[mac=key1]/crypto_map[name=key2]/crypto_map_entry[sequence=key3]/peer_list[priority=key4]/priority"
			::= { extremeWingCfgDevVpnCryptoInstPeerListEntry 1 }

		
		-- 1.3.6.1.4.1.1916.2.131.50.1.3.18.19.11.1.3
		extremeWingCfgDevVpnCryptoInstPeerListType OBJECT-TYPE
			SYNTAX DisplayString
			MAX-ACCESS read-write
			STATUS current
			DESCRIPTION
				"Peer IKE type.
				
				Values:
				ikev1,
				ikev2
				
				XPath: /extremeWing-config/device[mac=key1]/crypto_map[name=key2]/crypto_map_entry[sequence=key3]/peer_list[priority=key4]/type"
			::= { extremeWingCfgDevVpnCryptoInstPeerListEntry 3 }

		
		-- 1.3.6.1.4.1.1916.2.131.50.1.3.18.19.11.1.4
		extremeWingCfgDevVpnCryptoInstPeerListIkev1Peer OBJECT-TYPE
			SYNTAX ExtremeWingIdentifier
			MAX-ACCESS read-write
			STATUS current
			DESCRIPTION
				"Name of the IKEv1 Peer.
				
				XPath: /extremeWing-config/device[mac=key1]/crypto_map[name=key2]/crypto_map_entry[sequence=key3]/peer_list[priority=key4]/ikev1_peer"
			::= { extremeWingCfgDevVpnCryptoInstPeerListEntry 4 }

		
		-- 1.3.6.1.4.1.1916.2.131.50.1.3.18.19.11.1.5
		extremeWingCfgDevVpnCryptoInstPeerListIkev2Peer OBJECT-TYPE
			SYNTAX ExtremeWingIdentifier
			MAX-ACCESS read-write
			STATUS current
			DESCRIPTION
				"Name of the IKEv2 Peer.
				
				XPath: /extremeWing-config/device[mac=key1]/crypto_map[name=key2]/crypto_map_entry[sequence=key3]/peer_list[priority=key4]/ikev2_peer"
			::= { extremeWingCfgDevVpnCryptoInstPeerListEntry 5 }

		
		-- 1.3.6.1.4.1.1916.2.131.50.1.3.18.19.12
		extremeWingCfgDevVpnCryptoInstAhSessionTable OBJECT-TYPE
			SYNTAX SEQUENCE OF ExtremeWingCfgDevVpnCryptoInstAhSessionEntry
			MAX-ACCESS not-accessible
			STATUS current
			DESCRIPTION
				"NOTE: Columns under this table are valid only if extremeWingCfgDevVpnCryptoInstType sets to site-to-site-manual
				
				/extremeWing-config/device/crypto_map/crypto_map_entry/ah_session_keys"
			::= { extremeWingCfgDevVpn 12 }

		
		-- 1.3.6.1.4.1.1916.2.131.50.1.3.18.19.12.1
		extremeWingCfgDevVpnCryptoInstAhSessionEntry OBJECT-TYPE
			SYNTAX ExtremeWingCfgDevVpnCryptoInstAhSessionEntry
			MAX-ACCESS not-accessible
			STATUS current
			DESCRIPTION
				"An entry in the table."
			INDEX { extremeWingCfgDevMac, extremeWingCfgDevVpnCryptoName, extremeWingCfgDevVpnCryptoInstSequence, extremeWingCfgDevVpnCryptoInstAhSessionDirection }
			::= { extremeWingCfgDevVpnCryptoInstAhSessionTable 1 }

		
		ExtremeWingCfgDevVpnCryptoInstAhSessionEntry ::=
			SEQUENCE { 
				extremeWingCfgDevVpnCryptoInstAhSessionDirection
					ExtremeWingIdentifier,
				extremeWingCfgDevVpnCryptoInstAhSessionSpi
					Unsigned32,
				extremeWingCfgDevVpnCryptoInstAhSessionAuthAlgo
					DisplayString,
				extremeWingCfgDevVpnCryptoInstAhSessionKey
					OCTET STRING
			 }

		-- 1.3.6.1.4.1.1916.2.131.50.1.3.18.19.12.1.1
		extremeWingCfgDevVpnCryptoInstAhSessionDirection OBJECT-TYPE
			SYNTAX ExtremeWingIdentifier
			MAX-ACCESS read-only
			STATUS current
			DESCRIPTION
				"Direction of the security association.
				
				Values:
				inbound,
				outbound
				
				XPath: /extremeWing-config/device[mac=key1]/crypto_map[name=key2]/crypto_map_entry[sequence=key3]/ah_session_keys[direction=key4]/direction"
			::= { extremeWingCfgDevVpnCryptoInstAhSessionEntry 1 }

		
		-- 1.3.6.1.4.1.1916.2.131.50.1.3.18.19.12.1.3
		extremeWingCfgDevVpnCryptoInstAhSessionSpi OBJECT-TYPE
			SYNTAX Unsigned32 (256..4294967295)
			MAX-ACCESS read-write
			STATUS current
			DESCRIPTION
				"Security Parameter Index for Security Association. This should be unique for all Security Associations.
				
				XPath: /extremeWing-config/device[mac=key1]/crypto_map[name=key2]/crypto_map_entry[sequence=key3]/ah_session_keys[direction=key4]/spi"
			::= { extremeWingCfgDevVpnCryptoInstAhSessionEntry 3 }

		
		-- 1.3.6.1.4.1.1916.2.131.50.1.3.18.19.12.1.4
		extremeWingCfgDevVpnCryptoInstAhSessionAuthAlgo OBJECT-TYPE
			SYNTAX DisplayString
			MAX-ACCESS read-write
			STATUS current
			DESCRIPTION
				"Authentication scheme used to validate identity.
				
				Values:
				md5,
				sha
				
				XPath: /extremeWing-config/device[mac=key1]/crypto_map[name=key2]/crypto_map_entry[sequence=key3]/ah_session_keys[direction=key4]/auth_algo"
			DEFVAL { "sha" }
			::= { extremeWingCfgDevVpnCryptoInstAhSessionEntry 4 }

		
		-- 1.3.6.1.4.1.1916.2.131.50.1.3.18.19.12.1.5
		extremeWingCfgDevVpnCryptoInstAhSessionKey OBJECT-TYPE
			SYNTAX OCTET STRING (SIZE (8..512))
			MAX-ACCESS read-write
			STATUS current
			DESCRIPTION
				"Security association key value. The following key lengths (in hex characters) are required.ESP-MD5: 32,ESP-SHA: 40.
				
				XPath: /extremeWing-config/device[mac=key1]/crypto_map[name=key2]/crypto_map_entry[sequence=key3]/ah_session_keys[direction=key4]/key"
			::= { extremeWingCfgDevVpnCryptoInstAhSessionEntry 5 }

		
		-- 1.3.6.1.4.1.1916.2.131.50.1.3.18.19.13
		extremeWingCfgDevVpnCryptoInstEspSessionTable OBJECT-TYPE
			SYNTAX SEQUENCE OF ExtremeWingCfgDevVpnCryptoInstEspSessionEntry
			MAX-ACCESS not-accessible
			STATUS current
			DESCRIPTION
				"NOTE: Columns under this table are valid only if extremeWingCfgDevVpnCryptoInstType sets to site-to-site-manual
				
				/extremeWing-config/device/crypto_map/crypto_map_entry/esp_session_keys"
			::= { extremeWingCfgDevVpn 13 }

		
		-- 1.3.6.1.4.1.1916.2.131.50.1.3.18.19.13.1
		extremeWingCfgDevVpnCryptoInstEspSessionEntry OBJECT-TYPE
			SYNTAX ExtremeWingCfgDevVpnCryptoInstEspSessionEntry
			MAX-ACCESS not-accessible
			STATUS current
			DESCRIPTION
				"An entry in the table."
			INDEX { extremeWingCfgDevMac, extremeWingCfgDevVpnCryptoName, extremeWingCfgDevVpnCryptoInstSequence, extremeWingCfgDevVpnCryptoInstEspSessionDirection }
			::= { extremeWingCfgDevVpnCryptoInstEspSessionTable 1 }

		
		ExtremeWingCfgDevVpnCryptoInstEspSessionEntry ::=
			SEQUENCE { 
				extremeWingCfgDevVpnCryptoInstEspSessionDirection
					ExtremeWingIdentifier,
				extremeWingCfgDevVpnCryptoInstEspSessionSpi
					Unsigned32,
				extremeWingCfgDevVpnCryptoInstEspSessionCipherAlgo
					DisplayString,
				extremeWingCfgDevVpnCryptoInstEspSessionCipherKey
					OCTET STRING,
				extremeWingCfgDevVpnCryptoInstEspSessionAuthAlgo
					DisplayString,
				extremeWingCfgDevVpnCryptoInstEspSessionAuthKey
					OCTET STRING
			 }

		-- 1.3.6.1.4.1.1916.2.131.50.1.3.18.19.13.1.1
		extremeWingCfgDevVpnCryptoInstEspSessionDirection OBJECT-TYPE
			SYNTAX ExtremeWingIdentifier
			MAX-ACCESS read-only
			STATUS current
			DESCRIPTION
				"
				
				Values:
				inbound,
				outbound
				
				XPath: /extremeWing-config/device[mac=key1]/crypto_map[name=key2]/crypto_map_entry[sequence=key3]/esp_session_keys[direction=key4]/direction"
			::= { extremeWingCfgDevVpnCryptoInstEspSessionEntry 1 }

		
		-- 1.3.6.1.4.1.1916.2.131.50.1.3.18.19.13.1.3
		extremeWingCfgDevVpnCryptoInstEspSessionSpi OBJECT-TYPE
			SYNTAX Unsigned32 (256..4294967295)
			MAX-ACCESS read-write
			STATUS current
			DESCRIPTION
				"Security Parameter Index for Security Association. This should be unique for all Security Associations.
				
				XPath: /extremeWing-config/device[mac=key1]/crypto_map[name=key2]/crypto_map_entry[sequence=key3]/esp_session_keys[direction=key4]/spi"
			::= { extremeWingCfgDevVpnCryptoInstEspSessionEntry 3 }

		
		-- 1.3.6.1.4.1.1916.2.131.50.1.3.18.19.13.1.4
		extremeWingCfgDevVpnCryptoInstEspSessionCipherAlgo OBJECT-TYPE
			SYNTAX DisplayString
			MAX-ACCESS read-write
			STATUS current
			DESCRIPTION
				"Encryption method protecting data transmission.
				
				Values:
				esp-null,
				des,
				3des,
				aes,
				aes-192,
				aes-256
				
				XPath: /extremeWing-config/device[mac=key1]/crypto_map[name=key2]/crypto_map_entry[sequence=key3]/esp_session_keys[direction=key4]/cipher_algo"
			DEFVAL { "aes-256" }
			::= { extremeWingCfgDevVpnCryptoInstEspSessionEntry 4 }

		
		-- 1.3.6.1.4.1.1916.2.131.50.1.3.18.19.13.1.5
		extremeWingCfgDevVpnCryptoInstEspSessionCipherKey OBJECT-TYPE
			SYNTAX OCTET STRING (SIZE (8..512))
			MAX-ACCESS read-write
			STATUS current
			DESCRIPTION
				"Security association key value. The following key lengths (in hex characters) are required .ESP-NULL: 0, ESP-DES: 16, ESP-3DES: 48, ESP-AES: 32, ESP-AES-192: 48, ESP-AES-256: 64
				
				XPath: /extremeWing-config/device[mac=key1]/crypto_map[name=key2]/crypto_map_entry[sequence=key3]/esp_session_keys[direction=key4]/cipher_key"
			::= { extremeWingCfgDevVpnCryptoInstEspSessionEntry 5 }

		
		-- 1.3.6.1.4.1.1916.2.131.50.1.3.18.19.13.1.6
		extremeWingCfgDevVpnCryptoInstEspSessionAuthAlgo OBJECT-TYPE
			SYNTAX DisplayString
			MAX-ACCESS read-write
			STATUS current
			DESCRIPTION
				"Authentication scheme used to validate identity.
				
				Values:
				md5,
				sha
				
				XPath: /extremeWing-config/device[mac=key1]/crypto_map[name=key2]/crypto_map_entry[sequence=key3]/esp_session_keys[direction=key4]/auth_algo"
			DEFVAL { "sha" }
			::= { extremeWingCfgDevVpnCryptoInstEspSessionEntry 6 }

		
		-- 1.3.6.1.4.1.1916.2.131.50.1.3.18.19.13.1.7
		extremeWingCfgDevVpnCryptoInstEspSessionAuthKey OBJECT-TYPE
			SYNTAX OCTET STRING (SIZE (8..512))
			MAX-ACCESS read-write
			STATUS current
			DESCRIPTION
				"Security association key value. The following key lengths (in hex characters) are required.ESP-MD5: 32,ESP-SHA: 40.
				
				XPath: /extremeWing-config/device[mac=key1]/crypto_map[name=key2]/crypto_map_entry[sequence=key3]/esp_session_keys[direction=key4]/auth_key"
			::= { extremeWingCfgDevVpnCryptoInstEspSessionEntry 7 }

		
		-- 1.3.6.1.4.1.1916.2.131.50.1.3.18.19.14
		extremeWingCfgDevVpnIkev1RemoteTable OBJECT-TYPE
			SYNTAX SEQUENCE OF ExtremeWingCfgDevVpnIkev1RemoteEntry
			MAX-ACCESS not-accessible
			STATUS current
			DESCRIPTION
				"
				
				/extremeWing-config/device/ikev1_remote_vpn"
			::= { extremeWingCfgDevVpn 14 }

		
		-- 1.3.6.1.4.1.1916.2.131.50.1.3.18.19.14.1
		extremeWingCfgDevVpnIkev1RemoteEntry OBJECT-TYPE
			SYNTAX ExtremeWingCfgDevVpnIkev1RemoteEntry
			MAX-ACCESS not-accessible
			STATUS current
			DESCRIPTION
				"An entry in the table."
			INDEX { extremeWingCfgDevMac }
			::= { extremeWingCfgDevVpnIkev1RemoteTable 1 }

		
		ExtremeWingCfgDevVpnIkev1RemoteEntry ::=
			SEQUENCE { 
				extremeWingCfgDevVpnIkev1RemoteAuthMethod
					DisplayString,
				extremeWingCfgDevVpnIkev1RemoteAaaPolicy
					ExtremeWingIdentifier,
				extremeWingCfgDevVpnIkev1RemoteIpLocalPool
					DisplayString
			 }

		-- 1.3.6.1.4.1.1916.2.131.50.1.3.18.19.14.1.1
		extremeWingCfgDevVpnIkev1RemoteAuthMethod OBJECT-TYPE
			SYNTAX DisplayString
			MAX-ACCESS read-write
			STATUS current
			DESCRIPTION
				"The authentication method used for Remove VPN client. It can be one of RADIUS or LOCAL.
				
				Values:
				radius,
				local
				
				XPath: /extremeWing-config/device[mac=key1]/ikev1_remote_vpn/auth_method"
			DEFVAL { "local" }
			::= { extremeWingCfgDevVpnIkev1RemoteEntry 1 }

		
		-- 1.3.6.1.4.1.1916.2.131.50.1.3.18.19.14.1.2
		extremeWingCfgDevVpnIkev1RemoteAaaPolicy OBJECT-TYPE
			SYNTAX ExtremeWingIdentifier
			MAX-ACCESS read-write
			STATUS current
			DESCRIPTION
				"AAA Policy to use for remote VPN clients.
				
				XPath: /extremeWing-config/device[mac=key1]/ikev1_remote_vpn/aaa_policy"
			::= { extremeWingCfgDevVpnIkev1RemoteEntry 2 }

		
		-- 1.3.6.1.4.1.1916.2.131.50.1.3.18.19.14.1.3
		extremeWingCfgDevVpnIkev1RemoteIpLocalPool OBJECT-TYPE
			SYNTAX DisplayString
			MAX-ACCESS read-write
			STATUS current
			DESCRIPTION
				"The virtual IP pool for assigning IP addresses to remote VPN clients.
				
				XPath: /extremeWing-config/device[mac=key1]/ikev1_remote_vpn/ip_local_pool"
			::= { extremeWingCfgDevVpnIkev1RemoteEntry 3 }

		
		-- 1.3.6.1.4.1.1916.2.131.50.1.3.18.19.15
		extremeWingCfgDevVpnIkev1RemoteLocalUsersTable OBJECT-TYPE
			SYNTAX SEQUENCE OF ExtremeWingCfgDevVpnIkev1RemoteLocalUsersEntry
			MAX-ACCESS not-accessible
			STATUS current
			DESCRIPTION
				"
				
				/extremeWing-config/device/ikev1_remote_vpn/local_users"
			::= { extremeWingCfgDevVpn 15 }

		
		-- 1.3.6.1.4.1.1916.2.131.50.1.3.18.19.15.1
		extremeWingCfgDevVpnIkev1RemoteLocalUsersEntry OBJECT-TYPE
			SYNTAX ExtremeWingCfgDevVpnIkev1RemoteLocalUsersEntry
			MAX-ACCESS not-accessible
			STATUS current
			DESCRIPTION
				"An entry in the table."
			INDEX { extremeWingCfgDevMac, extremeWingCfgDevVpnIkev1RemoteLocalUsersName }
			::= { extremeWingCfgDevVpnIkev1RemoteLocalUsersTable 1 }

		
		ExtremeWingCfgDevVpnIkev1RemoteLocalUsersEntry ::=
			SEQUENCE { 
				extremeWingCfgDevVpnIkev1RemoteLocalUsersName
					ExtremeWingIdentifier,
				extremeWingCfgDevVpnIkev1RemoteLocalUsersPassword
					DisplayString
			 }

		-- 1.3.6.1.4.1.1916.2.131.50.1.3.18.19.15.1.1
		extremeWingCfgDevVpnIkev1RemoteLocalUsersName OBJECT-TYPE
			SYNTAX ExtremeWingIdentifier
			MAX-ACCESS read-only
			STATUS current
			DESCRIPTION
				"User name
				
				XPath: /extremeWing-config/device[mac=key1]/ikev1_remote_vpn/local_users[name=key2]/name"
			::= { extremeWingCfgDevVpnIkev1RemoteLocalUsersEntry 1 }
-- TODO: Key length may exceed 128 sub-identifiers
-- add leaf with Integer as key to append as the last digit of OID
		
		-- 1.3.6.1.4.1.1916.2.131.50.1.3.18.19.15.1.3
		extremeWingCfgDevVpnIkev1RemoteLocalUsersPassword OBJECT-TYPE
			SYNTAX DisplayString (SIZE (8..21))
			MAX-ACCESS read-write
			STATUS current
			DESCRIPTION
				"The password to authenticate the user.
				
				XPath: /extremeWing-config/device[mac=key1]/ikev1_remote_vpn/local_users[name=key2]/password"
			::= { extremeWingCfgDevVpnIkev1RemoteLocalUsersEntry 3 }

		
		-- 1.3.6.1.4.1.1916.2.131.50.1.3.18.19.16
		extremeWingCfgDevVpnIkev1RemoteWinsTable OBJECT-TYPE
			SYNTAX SEQUENCE OF ExtremeWingCfgDevVpnIkev1RemoteWinsEntry
			MAX-ACCESS not-accessible
			STATUS current
			DESCRIPTION
				"
				
				/extremeWing-config/device/ikev1_remote_vpn/wins"
			::= { extremeWingCfgDevVpn 16 }

		
		-- 1.3.6.1.4.1.1916.2.131.50.1.3.18.19.16.1
		extremeWingCfgDevVpnIkev1RemoteWinsEntry OBJECT-TYPE
			SYNTAX ExtremeWingCfgDevVpnIkev1RemoteWinsEntry
			MAX-ACCESS not-accessible
			STATUS current
			DESCRIPTION
				"An entry in the table."
			INDEX { extremeWingCfgDevMac, extremeWingCfgDevVpnIkev1RemoteWinsServerType }
			::= { extremeWingCfgDevVpnIkev1RemoteWinsTable 1 }

		
		ExtremeWingCfgDevVpnIkev1RemoteWinsEntry ::=
			SEQUENCE { 
				extremeWingCfgDevVpnIkev1RemoteWinsServerType
					ExtremeWingIdentifier,
				extremeWingCfgDevVpnIkev1RemoteWinsServerIp
					DisplayString
			 }

		-- 1.3.6.1.4.1.1916.2.131.50.1.3.18.19.16.1.1
		extremeWingCfgDevVpnIkev1RemoteWinsServerType OBJECT-TYPE
			SYNTAX ExtremeWingIdentifier
			MAX-ACCESS read-only
			STATUS current
			DESCRIPTION
				"Primary or Secondary WINS server.
				
				Values:
				primary,
				secondary
				
				XPath: /extremeWing-config/device[mac=key1]/ikev1_remote_vpn/wins[server_type=key2]/server_type"
			::= { extremeWingCfgDevVpnIkev1RemoteWinsEntry 1 }

		
		-- 1.3.6.1.4.1.1916.2.131.50.1.3.18.19.16.1.3
		extremeWingCfgDevVpnIkev1RemoteWinsServerIp OBJECT-TYPE
			SYNTAX DisplayString
			MAX-ACCESS read-write
			STATUS current
			DESCRIPTION
				"
				
				XPath: /extremeWing-config/device[mac=key1]/ikev1_remote_vpn/wins[server_type=key2]/server_ip"
			::= { extremeWingCfgDevVpnIkev1RemoteWinsEntry 3 }

		
		-- 1.3.6.1.4.1.1916.2.131.50.1.3.18.19.17
		extremeWingCfgDevVpnIkev1RemoteNameServerTable OBJECT-TYPE
			SYNTAX SEQUENCE OF ExtremeWingCfgDevVpnIkev1RemoteNameServerEntry
			MAX-ACCESS not-accessible
			STATUS current
			DESCRIPTION
				"
				
				/extremeWing-config/device/ikev1_remote_vpn/nameserver"
			::= { extremeWingCfgDevVpn 17 }

		
		-- 1.3.6.1.4.1.1916.2.131.50.1.3.18.19.17.1
		extremeWingCfgDevVpnIkev1RemoteNameServerEntry OBJECT-TYPE
			SYNTAX ExtremeWingCfgDevVpnIkev1RemoteNameServerEntry
			MAX-ACCESS not-accessible
			STATUS current
			DESCRIPTION
				"An entry in the table."
			INDEX { extremeWingCfgDevMac, extremeWingCfgDevVpnIkev1RemoteNameServerType }
			::= { extremeWingCfgDevVpnIkev1RemoteNameServerTable 1 }

		
		ExtremeWingCfgDevVpnIkev1RemoteNameServerEntry ::=
			SEQUENCE { 
				extremeWingCfgDevVpnIkev1RemoteNameServerType
					ExtremeWingIdentifier,
				extremeWingCfgDevVpnIkev1RemoteNameServerIp
					DisplayString
			 }

		-- 1.3.6.1.4.1.1916.2.131.50.1.3.18.19.17.1.1
		extremeWingCfgDevVpnIkev1RemoteNameServerType OBJECT-TYPE
			SYNTAX ExtremeWingIdentifier
			MAX-ACCESS read-only
			STATUS current
			DESCRIPTION
				"Primary or Secondary Name server.
				
				Values:
				primary,
				secondary
				
				XPath: /extremeWing-config/device[mac=key1]/ikev1_remote_vpn/nameserver[server_type=key2]/server_type"
			::= { extremeWingCfgDevVpnIkev1RemoteNameServerEntry 1 }

		
		-- 1.3.6.1.4.1.1916.2.131.50.1.3.18.19.17.1.4
		extremeWingCfgDevVpnIkev1RemoteNameServerIp OBJECT-TYPE
			SYNTAX DisplayString
			MAX-ACCESS read-write
			STATUS current
			DESCRIPTION
				"
				
				XPath: /extremeWing-config/device[mac=key1]/ikev1_remote_vpn/nameserver[server_type=key2]/server_ip"
			::= { extremeWingCfgDevVpnIkev1RemoteNameServerEntry 4 }

		
		-- 1.3.6.1.4.1.1916.2.131.50.1.3.18.19.18
		extremeWingCfgDevVpnIkev2RemoteTable OBJECT-TYPE
			SYNTAX SEQUENCE OF ExtremeWingCfgDevVpnIkev2RemoteEntry
			MAX-ACCESS not-accessible
			STATUS current
			DESCRIPTION
				"
				
				/extremeWing-config/device/ikev2_remote_vpn"
			::= { extremeWingCfgDevVpn 18 }

		
		-- 1.3.6.1.4.1.1916.2.131.50.1.3.18.19.18.1
		extremeWingCfgDevVpnIkev2RemoteEntry OBJECT-TYPE
			SYNTAX ExtremeWingCfgDevVpnIkev2RemoteEntry
			MAX-ACCESS not-accessible
			STATUS current
			DESCRIPTION
				"An entry in the table."
			INDEX { extremeWingCfgDevMac }
			::= { extremeWingCfgDevVpnIkev2RemoteTable 1 }

		
		ExtremeWingCfgDevVpnIkev2RemoteEntry ::=
			SEQUENCE { 
				extremeWingCfgDevVpnIkev2RemoteAuthMethod
					DisplayString,
				extremeWingCfgDevVpnIkev2RemoteAaaPolicy
					ExtremeWingIdentifier,
				extremeWingCfgDevVpnIkev2RemoteIpLocalPool
					DisplayString,
				extremeWingCfgDevVpnIkev2RemoteDhcpServerType
					DisplayString,
				extremeWingCfgDevVpnIkev2RemoteDhcpServer
					DisplayString,
				extremeWingCfgDevVpnIkev2RemoteDhcpServerGiaddr
					DisplayString,
				extremeWingCfgDevVpnIkev2RemoteNetmask
					DisplayString
			 }

		-- 1.3.6.1.4.1.1916.2.131.50.1.3.18.19.18.1.1
		extremeWingCfgDevVpnIkev2RemoteAuthMethod OBJECT-TYPE
			SYNTAX DisplayString
			MAX-ACCESS read-write
			STATUS current
			DESCRIPTION
				"The authentication method used for Remove VPN client. It can be one of RADIUS or LOCAL.
				
				Values:
				radius,
				local
				
				XPath: /extremeWing-config/device[mac=key1]/ikev2_remote_vpn/auth_method"
			DEFVAL { "local" }
			::= { extremeWingCfgDevVpnIkev2RemoteEntry 1 }

		
		-- 1.3.6.1.4.1.1916.2.131.50.1.3.18.19.18.1.2
		extremeWingCfgDevVpnIkev2RemoteAaaPolicy OBJECT-TYPE
			SYNTAX ExtremeWingIdentifier
			MAX-ACCESS read-write
			STATUS current
			DESCRIPTION
				"AAA Policy to use for remote VPN clients.
				
				XPath: /extremeWing-config/device[mac=key1]/ikev2_remote_vpn/aaa_policy"
			::= { extremeWingCfgDevVpnIkev2RemoteEntry 2 }

		
		-- 1.3.6.1.4.1.1916.2.131.50.1.3.18.19.18.1.3
		extremeWingCfgDevVpnIkev2RemoteIpLocalPool OBJECT-TYPE
			SYNTAX DisplayString
			MAX-ACCESS read-write
			STATUS current
			DESCRIPTION
				"The virtual IP pool for assigning IP addresses to remote VPN clients.
				
				XPath: /extremeWing-config/device[mac=key1]/ikev2_remote_vpn/ip_local_pool"
			::= { extremeWingCfgDevVpnIkev2RemoteEntry 3 }

		
		-- 1.3.6.1.4.1.1916.2.131.50.1.3.18.19.18.1.4
		extremeWingCfgDevVpnIkev2RemoteDhcpServerType OBJECT-TYPE
			SYNTAX DisplayString
			MAX-ACCESS read-write
			STATUS current
			DESCRIPTION
				"Select DHCP server type as IP or Hostname.
				
				Values:
				address,
				hostname,
				none
				
				XPath: /extremeWing-config/device[mac=key1]/ikev2_remote_vpn/dhcp_server/dhcp_server_type"
			DEFVAL { "'none'" }
			::= { extremeWingCfgDevVpnIkev2RemoteEntry 4 }

		
		-- 1.3.6.1.4.1.1916.2.131.50.1.3.18.19.18.1.5
		extremeWingCfgDevVpnIkev2RemoteDhcpServer OBJECT-TYPE
			SYNTAX DisplayString (SIZE (1..64))
			MAX-ACCESS read-write
			STATUS current
			DESCRIPTION
				"Specify DHCP server IP or Hostname.
				
				XPath: /extremeWing-config/device[mac=key1]/ikev2_remote_vpn/dhcp_server/dhcp_server"
			::= { extremeWingCfgDevVpnIkev2RemoteEntry 5 }

		
		-- 1.3.6.1.4.1.1916.2.131.50.1.3.18.19.18.1.6
		extremeWingCfgDevVpnIkev2RemoteDhcpServerGiaddr OBJECT-TYPE
			SYNTAX DisplayString
			MAX-ACCESS read-write
			STATUS current
			DESCRIPTION
				"DHCP Relay Agent IP address
				
				XPath: /extremeWing-config/device[mac=key1]/ikev2_remote_vpn/dhcp_server/giaddr"
			::= { extremeWingCfgDevVpnIkev2RemoteEntry 6 }

		
		-- 1.3.6.1.4.1.1916.2.131.50.1.3.18.19.18.1.7
		extremeWingCfgDevVpnIkev2RemoteNetmask OBJECT-TYPE
			SYNTAX DisplayString
			MAX-ACCESS read-write
			STATUS current
			DESCRIPTION
				"Netmask for remote VPN clients (IKEv2 only)
				
				XPath: /extremeWing-config/device[mac=key1]/ikev2_remote_vpn/netmask"
			::= { extremeWingCfgDevVpnIkev2RemoteEntry 7 }

		
		-- 1.3.6.1.4.1.1916.2.131.50.1.3.18.19.19
		extremeWingCfgDevVpnIkev2RemoteLocalUsersTable OBJECT-TYPE
			SYNTAX SEQUENCE OF ExtremeWingCfgDevVpnIkev2RemoteLocalUsersEntry
			MAX-ACCESS not-accessible
			STATUS current
			DESCRIPTION
				"
				
				/extremeWing-config/device/ikev2_remote_vpn/local_users"
			::= { extremeWingCfgDevVpn 19 }

		
		-- 1.3.6.1.4.1.1916.2.131.50.1.3.18.19.19.1
		extremeWingCfgDevVpnIkev2RemoteLocalUsersEntry OBJECT-TYPE
			SYNTAX ExtremeWingCfgDevVpnIkev2RemoteLocalUsersEntry
			MAX-ACCESS not-accessible
			STATUS current
			DESCRIPTION
				"An entry in the table."
			INDEX { extremeWingCfgDevMac, extremeWingCfgDevVpnIkev2RemoteLocalUsersName }
			::= { extremeWingCfgDevVpnIkev2RemoteLocalUsersTable 1 }

		
		ExtremeWingCfgDevVpnIkev2RemoteLocalUsersEntry ::=
			SEQUENCE { 
				extremeWingCfgDevVpnIkev2RemoteLocalUsersName
					ExtremeWingIdentifier,
				extremeWingCfgDevVpnIkev2RemoteLocalUsersPassword
					DisplayString
			 }

		-- 1.3.6.1.4.1.1916.2.131.50.1.3.18.19.19.1.1
		extremeWingCfgDevVpnIkev2RemoteLocalUsersName OBJECT-TYPE
			SYNTAX ExtremeWingIdentifier
			MAX-ACCESS read-only
			STATUS current
			DESCRIPTION
				"User name
				
				XPath: /extremeWing-config/device[mac=key1]/ikev2_remote_vpn/local_users[name=key2]/name"
			::= { extremeWingCfgDevVpnIkev2RemoteLocalUsersEntry 1 }
-- TODO: Key length may exceed 128 sub-identifiers
-- add leaf with Integer as key to append as the last digit of OID
		
		-- 1.3.6.1.4.1.1916.2.131.50.1.3.18.19.19.1.3
		extremeWingCfgDevVpnIkev2RemoteLocalUsersPassword OBJECT-TYPE
			SYNTAX DisplayString (SIZE (8..21))
			MAX-ACCESS read-write
			STATUS current
			DESCRIPTION
				"The password to authenticate the user.
				
				XPath: /extremeWing-config/device[mac=key1]/ikev2_remote_vpn/local_users[name=key2]/password"
			::= { extremeWingCfgDevVpnIkev2RemoteLocalUsersEntry 3 }

		
		-- 1.3.6.1.4.1.1916.2.131.50.1.3.18.19.20
		extremeWingCfgDevVpnIkev2RemoteWinsTable OBJECT-TYPE
			SYNTAX SEQUENCE OF ExtremeWingCfgDevVpnIkev2RemoteWinsEntry
			MAX-ACCESS not-accessible
			STATUS current
			DESCRIPTION
				"
				
				/extremeWing-config/device/ikev2_remote_vpn/wins"
			::= { extremeWingCfgDevVpn 20 }

		
		-- 1.3.6.1.4.1.1916.2.131.50.1.3.18.19.20.1
		extremeWingCfgDevVpnIkev2RemoteWinsEntry OBJECT-TYPE
			SYNTAX ExtremeWingCfgDevVpnIkev2RemoteWinsEntry
			MAX-ACCESS not-accessible
			STATUS current
			DESCRIPTION
				"An entry in the table."
			INDEX { extremeWingCfgDevMac, extremeWingCfgDevVpnIkev2RemoteWinsServerType }
			::= { extremeWingCfgDevVpnIkev2RemoteWinsTable 1 }

		
		ExtremeWingCfgDevVpnIkev2RemoteWinsEntry ::=
			SEQUENCE { 
				extremeWingCfgDevVpnIkev2RemoteWinsServerType
					ExtremeWingIdentifier,
				extremeWingCfgDevVpnIkev2RemoteWinsServerIp
					DisplayString
			 }

		-- 1.3.6.1.4.1.1916.2.131.50.1.3.18.19.20.1.1
		extremeWingCfgDevVpnIkev2RemoteWinsServerType OBJECT-TYPE
			SYNTAX ExtremeWingIdentifier
			MAX-ACCESS read-only
			STATUS current
			DESCRIPTION
				"Primary or Secondary WINS server.
				
				Values:
				primary,
				secondary
				
				XPath: /extremeWing-config/device[mac=key1]/ikev2_remote_vpn/wins[server_type=key2]/server_type"
			::= { extremeWingCfgDevVpnIkev2RemoteWinsEntry 1 }

		
		-- 1.3.6.1.4.1.1916.2.131.50.1.3.18.19.20.1.3
		extremeWingCfgDevVpnIkev2RemoteWinsServerIp OBJECT-TYPE
			SYNTAX DisplayString
			MAX-ACCESS read-write
			STATUS current
			DESCRIPTION
				"
				
				XPath: /extremeWing-config/device[mac=key1]/ikev2_remote_vpn/wins[server_type=key2]/server_ip"
			::= { extremeWingCfgDevVpnIkev2RemoteWinsEntry 3 }

		
		-- 1.3.6.1.4.1.1916.2.131.50.1.3.18.19.21
		extremeWingCfgDevVpnIkev2RemoteNameServerTable OBJECT-TYPE
			SYNTAX SEQUENCE OF ExtremeWingCfgDevVpnIkev2RemoteNameServerEntry
			MAX-ACCESS not-accessible
			STATUS current
			DESCRIPTION
				"
				
				/extremeWing-config/device/ikev2_remote_vpn/nameserver"
			::= { extremeWingCfgDevVpn 21 }

		
		-- 1.3.6.1.4.1.1916.2.131.50.1.3.18.19.21.1
		extremeWingCfgDevVpnIkev2RemoteNameServerEntry OBJECT-TYPE
			SYNTAX ExtremeWingCfgDevVpnIkev2RemoteNameServerEntry
			MAX-ACCESS not-accessible
			STATUS current
			DESCRIPTION
				"An entry in the table."
			INDEX { extremeWingCfgDevMac, extremeWingCfgDevVpnIkev2RemoteNameServerType }
			::= { extremeWingCfgDevVpnIkev2RemoteNameServerTable 1 }

		
		ExtremeWingCfgDevVpnIkev2RemoteNameServerEntry ::=
			SEQUENCE { 
				extremeWingCfgDevVpnIkev2RemoteNameServerType
					ExtremeWingIdentifier,
				extremeWingCfgDevVpnIkev2RemoteNameServerIp
					DisplayString
			 }

		-- 1.3.6.1.4.1.1916.2.131.50.1.3.18.19.21.1.1
		extremeWingCfgDevVpnIkev2RemoteNameServerType OBJECT-TYPE
			SYNTAX ExtremeWingIdentifier
			MAX-ACCESS read-only
			STATUS current
			DESCRIPTION
				"Primary or Secondary Name server.
				
				Values:
				primary,
				secondary
				
				XPath: /extremeWing-config/device[mac=key1]/ikev2_remote_vpn/nameserver[server_type=key2]/server_type"
			::= { extremeWingCfgDevVpnIkev2RemoteNameServerEntry 1 }

		
		-- 1.3.6.1.4.1.1916.2.131.50.1.3.18.19.21.1.3
		extremeWingCfgDevVpnIkev2RemoteNameServerIp OBJECT-TYPE
			SYNTAX DisplayString
			MAX-ACCESS read-write
			STATUS current
			DESCRIPTION
				"
				
				XPath: /extremeWing-config/device[mac=key1]/ikev2_remote_vpn/nameserver[server_type=key2]/server_ip"
			::= { extremeWingCfgDevVpnIkev2RemoteNameServerEntry 3 }

		
		-- 1.3.6.1.4.1.1916.2.131.50.1.3.18.19.22
		extremeWingCfgDevVpnAutoIPSecSecureTable OBJECT-TYPE
			SYNTAX SEQUENCE OF ExtremeWingCfgDevVpnAutoIPSecSecureEntry
			MAX-ACCESS not-accessible
			STATUS current
			DESCRIPTION
				"Description."
			::= { extremeWingCfgDevVpn 22 }

		
		-- 1.3.6.1.4.1.1916.2.131.50.1.3.18.19.22.1
		extremeWingCfgDevVpnAutoIPSecSecureEntry OBJECT-TYPE
			SYNTAX ExtremeWingCfgDevVpnAutoIPSecSecureEntry
			MAX-ACCESS not-accessible
			STATUS current
			DESCRIPTION
				"Description."
			INDEX { extremeWingCfgDevMac }
			::= { extremeWingCfgDevVpnAutoIPSecSecureTable 1 }

		
		ExtremeWingCfgDevVpnAutoIPSecSecureEntry ::=
			SEQUENCE { 
				extremeWingCfgDevVpnAutoIPSecSecureGroupId
					OCTET STRING,
				extremeWingCfgDevVpnAutoIPSecSecureGroupIdAuthType
					DisplayString,
				extremeWingCfgDevVpnAutoIPSecSecureGroupIdAuthKey
					DisplayString,
				extremeWingCfgDevVpnAutoIPSecSecureRemoteGWIkeVersion
					DisplayString
			 }

		-- 1.3.6.1.4.1.1916.2.131.50.1.3.18.19.22.1.1
		extremeWingCfgDevVpnAutoIPSecSecureGroupId OBJECT-TYPE
			SYNTAX OCTET STRING (SIZE (1..128))
			MAX-ACCESS read-write
			STATUS current
			DESCRIPTION
				"Group identity to use in IKE exchange for auto ipsec secure peers.
				
				XPath: /extremeWing-config/device[mac=key1]/auto_ipsec_secure/group_id_auth_type_key/groupid_id"
			::= { extremeWingCfgDevVpnAutoIPSecSecureEntry 1 }

		
		-- 1.3.6.1.4.1.1916.2.131.50.1.3.18.19.22.1.2
		extremeWingCfgDevVpnAutoIPSecSecureGroupIdAuthType OBJECT-TYPE
			SYNTAX DisplayString
			MAX-ACCESS read-write
			STATUS current
			DESCRIPTION
				"The authentication type for auto ipsec secure peer authentication.
				
				XPath: /extremeWing-config/device[mac=key1]/auto_ipsec_secure/group_id_auth_type_key/groupid_auth_type"
			::= { extremeWingCfgDevVpnAutoIPSecSecureEntry 2 }

		
		-- 1.3.6.1.4.1.1916.2.131.50.1.3.18.19.22.1.3
		extremeWingCfgDevVpnAutoIPSecSecureGroupIdAuthKey OBJECT-TYPE
			SYNTAX DisplayString (SIZE (8..21))
			MAX-ACCESS read-write
			STATUS current
			DESCRIPTION
				"The shared secret used for auto ipsec secure peer authentication.
				
				XPath: /extremeWing-config/device[mac=key1]/auto_ipsec_secure/group_id_auth_type_key/groupid_auth_key"
			::= { extremeWingCfgDevVpnAutoIPSecSecureEntry 3 }

		
		-- 1.3.6.1.4.1.1916.2.131.50.1.3.18.19.22.1.4
		extremeWingCfgDevVpnAutoIPSecSecureRemoteGWIkeVersion OBJECT-TYPE
			SYNTAX DisplayString
			MAX-ACCESS read-write
			STATUS current
			DESCRIPTION
				"The ike version for auto ipsec secure authentication with ipsec gateway other than controllers.
				
				XPath: /extremeWing-config/device[mac=key1]/auto_ipsec_secure/remotegw_ike_version"
			::= { extremeWingCfgDevVpnAutoIPSecSecureEntry 4 }

		
-- /extremeWing-config/device/controller_host
                -- 1.3.6.1.4.1.1916.2.131.50.1.3.18.20
                extremeWingCfgDevControllerHost OBJECT IDENTIFIER ::= { extremeWingCfgDev 20 }


                -- 1.3.6.1.4.1.1916.2.131.50.1.3.18.20.1
                extremeWingCfgDevControllerHostTable OBJECT-TYPE
                        SYNTAX SEQUENCE OF ExtremeWingCfgDevControllerHostEntry
                        MAX-ACCESS not-accessible
                        STATUS current
                        DESCRIPTION
                                "WLAN controller configuration

                                /extremeWing-config/device/controller_host"
                        ::= { extremeWingCfgDevControllerHost 1 }


                -- 1.3.6.1.4.1.1916.2.131.50.1.3.18.20.1.1
                extremeWingCfgDevControllerHostEntry OBJECT-TYPE
                        SYNTAX ExtremeWingCfgDevControllerHostEntry
                        MAX-ACCESS not-accessible
                        STATUS current
                        DESCRIPTION
                                "An entry in the table."
                        INDEX { extremeWingCfgDevMac, extremeWingCfgDevControllerHostHost, extremeWingCfgDevControllerHostPool, extremeWingCfgDevControllerHostLevel }
                        ::= { extremeWingCfgDevControllerHostTable 1 }


                ExtremeWingCfgDevControllerHostEntry ::=
                        SEQUENCE {
                                extremeWingCfgDevControllerHostHost
                                        DisplayString,
                                extremeWingCfgDevControllerHostPool
                                        Unsigned32,
                                extremeWingCfgDevControllerHostLevel
                                        Unsigned32,
                                extremeWingCfgDevControllerHostRowStatus
                                        RowStatus,
                                extremeWingCfgDevControllerHostForce
                                        TruthValue,
                                extremeWingCfgDevControllerHostRremoteVpnClient
                                        TruthValue,
                                extremeWingCfgDevControllerHostIPSecSecure
                                        TruthValue,
                                extremeWingCfgDevControllerHostIPSecGw
                                        IpAddress
                         }

                -- 1.3.6.1.4.1.1916.2.131.50.1.3.18.20.1.1.1
                extremeWingCfgDevControllerHostHost OBJECT-TYPE
                        SYNTAX DisplayString
                        MAX-ACCESS read-only
                        STATUS current
                        DESCRIPTION
                                "IP address or hostname of controller.

                                As this object is indirectly part of the key,
                                to change its value the row must be deleted and created with
                                the new key.

                                XPath: /extremeWing-config/device[mac=key1]/controller_host[host=key2,pool=key3,level=key4]/host"
                        ::= { extremeWingCfgDevControllerHostEntry 1 }


                -- 1.3.6.1.4.1.1916.2.131.50.1.3.18.20.1.1.2
                extremeWingCfgDevControllerHostPool OBJECT-TYPE
                        SYNTAX Unsigned32 (1..2)
                        MAX-ACCESS read-only
                        STATUS current
                        DESCRIPTION
                                "Pool this controller belongs to.

                                As this object is indirectly part of the key,
                                to change its value the row must be deleted and created with
                                the new key.

                                XPath: /extremeWing-config/device[mac=key1]/controller_host[host=key2,pool=key3,level=key4]/pool"
                        ::= { extremeWingCfgDevControllerHostEntry 2 }


                -- 1.3.6.1.4.1.1916.2.131.50.1.3.18.20.1.1.3
                extremeWingCfgDevControllerHostLevel OBJECT-TYPE
                        SYNTAX Unsigned32 (1..2)
                        MAX-ACCESS read-only
                        STATUS current
                        DESCRIPTION
                                "Routing level for controller link.

                                As this object is indirectly part of the key,
                                to change its value the row must be deleted and created with
                                the new key.

                                Values:
                                1  Level 1 (local)
                                2  Level 2 (inter-site)

                                XPath: /extremeWing-config/device[mac=key1]/controller_host[host=key2,pool=key3,level=key4]/level"
                        ::= { extremeWingCfgDevControllerHostEntry 3 }


                -- 1.3.6.1.4.1.1916.2.131.50.1.3.18.20.1.1.4
                extremeWingCfgDevControllerHostRowStatus OBJECT-TYPE
                        SYNTAX RowStatus
                                {
                                active(1),
                                createAndGo(4),
                                destroy(6)
                                }
                        MAX-ACCESS read-write
                        STATUS current
                        DESCRIPTION
                                "The status of this conceptual row.

                                XPath: /extremeWing-config/device[mac=key1]/controller_host[host=key2,pool=key3,level=key4]/row_status"
                        ::= { extremeWingCfgDevControllerHostEntry 4 }


                -- 1.3.6.1.4.1.1916.2.131.50.1.3.18.20.1.1.5
                extremeWingCfgDevControllerHostForce OBJECT-TYPE
                        SYNTAX TruthValue
                        MAX-ACCESS read-write
                        STATUS current
                        DESCRIPTION
                                "Force link to be created even when unnecessary.

                                XPath: /extremeWing-config/device[mac=key1]/controller_host[host=key2,pool=key3,level=key4]/force"
                        DEFVAL { false }
                        ::= { extremeWingCfgDevControllerHostEntry 5 }


                -- 1.3.6.1.4.1.1916.2.131.50.1.3.18.20.1.1.6
                extremeWingCfgDevControllerHostRremoteVpnClient OBJECT-TYPE
                        SYNTAX TruthValue
                        MAX-ACCESS read-write
                        STATUS current
                        DESCRIPTION
                                "Secure controller link using remote vpn connection.

                                XPath: /extremeWing-config/device[mac=key1]/controller_host[host=key2,pool=key3,level=key4]/remote_vpn_client"
                        DEFVAL { false }
                        ::= { extremeWingCfgDevControllerHostEntry 6 }


                -- 1.3.6.1.4.1.1916.2.131.50.1.3.18.20.1.1.7
                extremeWingCfgDevControllerHostIPSecSecure OBJECT-TYPE
                        SYNTAX TruthValue
                        MAX-ACCESS read-write
                        STATUS current
                        DESCRIPTION
                                "IPSec secure controller link.

                                XPath: /extremeWing-config/device[mac=key1]/controller_host[host=key2,pool=key3,level=key4]/ipsec_secure"
                        DEFVAL { false }
                        ::= { extremeWingCfgDevControllerHostEntry 7 }


                -- 1.3.6.1.4.1.1916.2.131.50.1.3.18.20.1.1.8
                extremeWingCfgDevControllerHostIPSecGw OBJECT-TYPE
                        SYNTAX IpAddress
                        MAX-ACCESS read-write
                        STATUS current
                        DESCRIPTION
                                "IP address or hostname of controller.

                                XPath: /extremeWing-config/device[mac=key1]/controller_host[host=key2,pool=key3,level=key4]/ipsec_gw"
                        ::= { extremeWingCfgDevControllerHostEntry 8 }

		
		-- 1.3.6.1.4.1.1916.2.131.50.1.3.18.23
		extremeWingCfgDevWlan OBJECT IDENTIFIER ::= { extremeWingCfgDev 23 }

		
		-- 1.3.6.1.4.1.1916.2.131.50.1.3.18.23.1
		extremeWingCfgDevWlanSsidOverrideTable OBJECT-TYPE
			SYNTAX SEQUENCE OF ExtremeWingCfgDevWlanSsidOverrideEntry
			MAX-ACCESS not-accessible
			STATUS current
			DESCRIPTION
				"Override wlan ssid at the rf_domain level
				
				/extremeWing-config/device/wlan_override_ssid"
			::= { extremeWingCfgDevWlan 1 }

		
		-- 1.3.6.1.4.1.1916.2.131.50.1.3.18.23.1.1
		extremeWingCfgDevWlanSsidOverrideEntry OBJECT-TYPE
			SYNTAX ExtremeWingCfgDevWlanSsidOverrideEntry
			MAX-ACCESS not-accessible
			STATUS current
			DESCRIPTION
				"An entry in the table."
			INDEX { extremeWingCfgDevMac, extremeWingCfgDevWlanSsidOverrideWlan }
			::= { extremeWingCfgDevWlanSsidOverrideTable 1 }

		
		ExtremeWingCfgDevWlanSsidOverrideEntry ::=
			SEQUENCE { 
				extremeWingCfgDevWlanSsidOverrideWlan
					ExtremeWingIdentifier,
				extremeWingCfgDevWlanSsidOverrideSsid
					DisplayString
			 }

		-- 1.3.6.1.4.1.1916.2.131.50.1.3.18.23.1.1.1
		extremeWingCfgDevWlanSsidOverrideWlan OBJECT-TYPE
			SYNTAX ExtremeWingIdentifier
			MAX-ACCESS read-only
			STATUS current
			DESCRIPTION
				"
				
				XPath: /extremeWing-config/device[mac=key1]/wlan_override_ssid[wlan=key2]/wlan"
			::= { extremeWingCfgDevWlanSsidOverrideEntry 1 }

		
		-- 1.3.6.1.4.1.1916.2.131.50.1.3.18.23.1.1.3
		extremeWingCfgDevWlanSsidOverrideSsid OBJECT-TYPE
			SYNTAX DisplayString (SIZE (1..32))
			MAX-ACCESS read-write
			STATUS current
			DESCRIPTION
				"The Service Set Identifier for this WLAN.
				
				XPath: /extremeWing-config/device[mac=key1]/wlan_override_ssid[wlan=key2]/ssid"
			::= { extremeWingCfgDevWlanSsidOverrideEntry 3 }

		
		-- 1.3.6.1.4.1.1916.2.131.50.1.3.18.23.2
		extremeWingCfgDevWlanVlanOverrideTable OBJECT-TYPE
			SYNTAX SEQUENCE OF ExtremeWingCfgDevWlanVlanOverrideEntry
			MAX-ACCESS not-accessible
			STATUS current
			DESCRIPTION
				"Override WLAN VLANs at the RF Domain level.
				
				/extremeWing-config/device/wlan_override_vlan"
			::= { extremeWingCfgDevWlan 2 }

		
		-- 1.3.6.1.4.1.1916.2.131.50.1.3.18.23.2.1
		extremeWingCfgDevWlanVlanOverrideEntry OBJECT-TYPE
			SYNTAX ExtremeWingCfgDevWlanVlanOverrideEntry
			MAX-ACCESS not-accessible
			STATUS current
			DESCRIPTION
				"An entry in the table."
			INDEX { extremeWingCfgDevMac, extremeWingCfgDevWlanVlanOverrideWlan }
			::= { extremeWingCfgDevWlanVlanOverrideTable 1 }

		
		ExtremeWingCfgDevWlanVlanOverrideEntry ::=
			SEQUENCE { 
				extremeWingCfgDevWlanVlanOverrideWlan
					ExtremeWingIdentifier
			 }

		-- 1.3.6.1.4.1.1916.2.131.50.1.3.18.23.2.1.1
		extremeWingCfgDevWlanVlanOverrideWlan OBJECT-TYPE
			SYNTAX ExtremeWingIdentifier
			MAX-ACCESS read-only
			STATUS current
			DESCRIPTION
				"
				
				XPath: /extremeWing-config/device[mac=key1]/wlan_override_vlan[wlan=key2]/wlan"
			::= { extremeWingCfgDevWlanVlanOverrideEntry 1 }

		
		-- 1.3.6.1.4.1.1916.2.131.50.1.3.18.23.3
		extremeWingCfgDevWlanVlanOverrideInstTable OBJECT-TYPE
			SYNTAX SEQUENCE OF ExtremeWingCfgDevWlanVlanOverrideInstEntry
			MAX-ACCESS not-accessible
			STATUS current
			DESCRIPTION
				"
				/extremeWing-config/device/wlan_override_vlan/vlans"
			::= { extremeWingCfgDevWlan 3 }

		
		-- 1.3.6.1.4.1.1916.2.131.50.1.3.18.23.3.1
		extremeWingCfgDevWlanVlanOverrideInstEntry OBJECT-TYPE
			SYNTAX ExtremeWingCfgDevWlanVlanOverrideInstEntry
			MAX-ACCESS not-accessible
			STATUS current
			DESCRIPTION
				"An entry in the table."
			INDEX { extremeWingCfgDevMac, extremeWingCfgDevWlanVlanOverrideWlan, extremeWingCfgDevWlanVlanOverrideInstVlan }
			::= { extremeWingCfgDevWlanVlanOverrideInstTable 1 }

		
		ExtremeWingCfgDevWlanVlanOverrideInstEntry ::=
			SEQUENCE { 
				extremeWingCfgDevWlanVlanOverrideInstVlan
					Unsigned32,
				extremeWingCfgDevWlanVlanOverrideInstLimit
					Unsigned32
			 }

		-- 1.3.6.1.4.1.1916.2.131.50.1.3.18.23.3.1.1
		extremeWingCfgDevWlanVlanOverrideInstVlan OBJECT-TYPE
			SYNTAX Unsigned32 (1..4094)
			MAX-ACCESS read-only
			STATUS current
			DESCRIPTION
				"The VLAN identifier.
				
				XPath: /extremeWing-config/device[mac=key1]/wlan_override_vlan[wlan=key2]/vlans[vlan=key3]/vlan"
			::= { extremeWingCfgDevWlanVlanOverrideInstEntry 1 }

		
		-- 1.3.6.1.4.1.1916.2.131.50.1.3.18.23.3.1.3
		extremeWingCfgDevWlanVlanOverrideInstLimit OBJECT-TYPE
			SYNTAX Unsigned32 (0..8192)
			MAX-ACCESS read-write
			STATUS current
			DESCRIPTION
				"The number of users allowed (0 implies unlimited).
				
				XPath: /extremeWing-config/device[mac=key1]/wlan_override_vlan[wlan=key2]/vlans[vlan=key3]/limit"
			DEFVAL { 0 }
			::= { extremeWingCfgDevWlanVlanOverrideInstEntry 3 }

		
		-- 1.3.6.1.4.1.1916.2.131.50.1.3.18.24
		extremeWingCfgDevStatsWindowTable OBJECT-TYPE
			SYNTAX SEQUENCE OF ExtremeWingCfgDevStatsWindowEntry
			MAX-ACCESS not-accessible
			STATUS current
			DESCRIPTION
				"
				
				/extremeWing-config/device/stats_window"
			::= { extremeWingCfgDev 24 }

		
		-- 1.3.6.1.4.1.1916.2.131.50.1.3.18.24.1
		extremeWingCfgDevStatsWindowEntry OBJECT-TYPE
			SYNTAX ExtremeWingCfgDevStatsWindowEntry
			MAX-ACCESS not-accessible
			STATUS current
			DESCRIPTION
				"An entry in the table."
			INDEX { extremeWingCfgDevMac, extremeWingCfgDevStatsWindowIdx }
			::= { extremeWingCfgDevStatsWindowTable 1 }

		
		ExtremeWingCfgDevStatsWindowEntry ::=
			SEQUENCE { 
				extremeWingCfgDevStatsWindowIdx
					Unsigned32,
				extremeWingCfgDevStatsWindowSampleInterval
					Unsigned32,
				extremeWingCfgDevStatsWindowWindowSize
					Unsigned32
			 }

		-- 1.3.6.1.4.1.1916.2.131.50.1.3.18.24.1.1
		extremeWingCfgDevStatsWindowIdx OBJECT-TYPE
			SYNTAX Unsigned32 (1..2)
			MAX-ACCESS read-only
			STATUS current
			DESCRIPTION
				"The index into the list of stats-windows
				
				XPath: /extremeWing-config/device[mac=key1]/stats_window[window_idx=key2]/window_idx"
			::= { extremeWingCfgDevStatsWindowEntry 1 }

		
		-- 1.3.6.1.4.1.1916.2.131.50.1.3.18.24.1.3
		extremeWingCfgDevStatsWindowSampleInterval OBJECT-TYPE
			SYNTAX Unsigned32 (5..86640)
			MAX-ACCESS read-write
			STATUS current
			DESCRIPTION
				"sample interval in seconds for the window
				
				XPath: /extremeWing-config/device[mac=key1]/stats_window[window_idx=key2]/sample_interval"
			DEFVAL { 5 }
			::= { extremeWingCfgDevStatsWindowEntry 3 }

		
		-- 1.3.6.1.4.1.1916.2.131.50.1.3.18.24.1.4
		extremeWingCfgDevStatsWindowWindowSize OBJECT-TYPE
			SYNTAX Unsigned32 (3..100)
			MAX-ACCESS read-write
			STATUS current
			DESCRIPTION
				"number of samples in the window
				
				XPath: /extremeWing-config/device[mac=key1]/stats_window[window_idx=key2]/window_size"
			DEFVAL { 3 }
			::= { extremeWingCfgDevStatsWindowEntry 4 }

		
		-- 1.3.6.1.4.1.1916.2.131.50.1.3.18.26
		extremeWingCfgDevVrrp OBJECT IDENTIFIER ::= { extremeWingCfgDev 26 }

		
		-- 1.3.6.1.4.1.1916.2.131.50.1.3.18.26.1
		extremeWingCfgDevVrrpTable OBJECT-TYPE
			SYNTAX SEQUENCE OF ExtremeWingCfgDevVrrpEntry
			MAX-ACCESS not-accessible
			STATUS current
			DESCRIPTION
				"
				
				/extremeWing-config/device"
			::= { extremeWingCfgDevVrrp 1 }

		
		-- 1.3.6.1.4.1.1916.2.131.50.1.3.18.26.1.1
		extremeWingCfgDevVrrpEntry OBJECT-TYPE
			SYNTAX ExtremeWingCfgDevVrrpEntry
			MAX-ACCESS not-accessible
			STATUS current
			DESCRIPTION
				"An entry in the table."
			INDEX { extremeWingCfgDevMac }
			::= { extremeWingCfgDevVrrpTable 1 }

		
		ExtremeWingCfgDevVrrpEntry ::=
			SEQUENCE { 
				extremeWingCfgDevVrrpVersion
					DisplayString
			 }

		-- 1.3.6.1.4.1.1916.2.131.50.1.3.18.26.1.1.1
		extremeWingCfgDevVrrpVersion OBJECT-TYPE
			SYNTAX DisplayString
			MAX-ACCESS read-write
			STATUS current
			DESCRIPTION
				"VRRP version supported by the device
				
				Values:
				3
				
				XPath: /extremeWing-config/device[mac=key1]/vrrp_version"
			DEFVAL { "2" }
			::= { extremeWingCfgDevVrrpEntry 1 }

		
		-- 1.3.6.1.4.1.1916.2.131.50.1.3.18.26.2
		extremeWingCfgDevVrrpGroupTable OBJECT-TYPE
			SYNTAX SEQUENCE OF ExtremeWingCfgDevVrrpGroupEntry
			MAX-ACCESS not-accessible
			STATUS current
			DESCRIPTION
				"
				
				/extremeWing-config/device/vrrp_groups"
			::= { extremeWingCfgDevVrrp 2 }

		
		-- 1.3.6.1.4.1.1916.2.131.50.1.3.18.26.2.1
		extremeWingCfgDevVrrpGroupEntry OBJECT-TYPE
			SYNTAX ExtremeWingCfgDevVrrpGroupEntry
			MAX-ACCESS not-accessible
			STATUS current
			DESCRIPTION
				"An entry in the table."
			INDEX { extremeWingCfgDevMac, extremeWingCfgDevVrrpGroupVirtualRouterId }
			::= { extremeWingCfgDevVrrpGroupTable 1 }

		
		ExtremeWingCfgDevVrrpGroupEntry ::=
			SEQUENCE { 
				extremeWingCfgDevVrrpGroupVirtualRouterId
					Unsigned32,
				extremeWingCfgDevVrrpGroupDescription
					DisplayString,
				extremeWingCfgDevVrrpGroupPriority
					Unsigned32,
				extremeWingCfgDevVrrpGroupAdvertisementUnit
					DisplayString,
				extremeWingCfgDevVrrpGroupAdvertisementIntervalV2
					Unsigned32,
				extremeWingCfgDevVrrpGroupAdvertisementIntervalV2Msec
					Unsigned32,
				extremeWingCfgDevVrrpGroupAdvertisementIntervalV3
					Unsigned32,
				extremeWingCfgDevVrrpGroupPreempt
					TruthValue,
				extremeWingCfgDevVrrpGroupPreemptDelay
					Unsigned32,
				extremeWingCfgDevVrrpGroupCrmAction
					DisplayString,
				extremeWingCfgDevVrrpGroupDeltaPriority
					Unsigned32,
				extremeWingCfgDevVrrpGroupInterface
					Unsigned32,
				extremeWingCfgDevVrrpGroupSyncGroup
					TruthValue
			 }

		-- 1.3.6.1.4.1.1916.2.131.50.1.3.18.26.2.1.1
		extremeWingCfgDevVrrpGroupVirtualRouterId OBJECT-TYPE
			SYNTAX Unsigned32 (1..255)
			MAX-ACCESS read-only
			STATUS current
			DESCRIPTION
				"Identifies the virtual router and used for associating VRRP packet with this field
				
				XPath: /extremeWing-config/device[mac=key1]/vrrp_groups[virtual_router_id=key2]/virtual_router_id"
			::= { extremeWingCfgDevVrrpGroupEntry 1 }

		
		-- 1.3.6.1.4.1.1916.2.131.50.1.3.18.26.2.1.3
		extremeWingCfgDevVrrpGroupDescription OBJECT-TYPE
			SYNTAX DisplayString (SIZE (1..64))
			MAX-ACCESS read-write
			STATUS current
			DESCRIPTION
				"Assigns a text description to the VRRP group
				
				XPath: /extremeWing-config/device[mac=key1]/vrrp_groups[virtual_router_id=key2]/description"
			::= { extremeWingCfgDevVrrpGroupEntry 3 }

		
		-- 1.3.6.1.4.1.1916.2.131.50.1.3.18.26.2.1.4
		extremeWingCfgDevVrrpGroupPriority OBJECT-TYPE
			SYNTAX Unsigned32 (1..254)
			MAX-ACCESS read-write
			STATUS current
			DESCRIPTION
				"the priority to be used for the virtual router master election process.  Higher values imply higher priority.
				
				XPath: /extremeWing-config/device[mac=key1]/vrrp_groups[virtual_router_id=key2]/priority"
			DEFVAL { 100 }
			::= { extremeWingCfgDevVrrpGroupEntry 4 }

		
		-- 1.3.6.1.4.1.1916.2.131.50.1.3.18.26.2.1.5
		extremeWingCfgDevVrrpGroupAdvertisementUnit OBJECT-TYPE
			SYNTAX DisplayString
			MAX-ACCESS read-write
			STATUS current
			DESCRIPTION
				"unit of the advertisment interval
				
				Values:
				seconds,
				milliseconds,
				centiseconds
				
				XPath: /extremeWing-config/device[mac=key1]/vrrp_groups[virtual_router_id=key2]/advertisement_interval/advertisement_unit"
			DEFVAL { "seconds" }
			::= { extremeWingCfgDevVrrpGroupEntry 5 }

		
		-- 1.3.6.1.4.1.1916.2.131.50.1.3.18.26.2.1.6
		extremeWingCfgDevVrrpGroupAdvertisementIntervalV2 OBJECT-TYPE
			SYNTAX Unsigned32 (1..255)
			UNITS "seconds"
			MAX-ACCESS read-write
			STATUS current
			DESCRIPTION
				"Time interval between VRRP advertisments
				
				XPath: /extremeWing-config/device[mac=key1]/vrrp_groups[virtual_router_id=key2]/advertisement_interval/advertisement_interval_v2"
			DEFVAL { 1 }
			::= { extremeWingCfgDevVrrpGroupEntry 6 }

		
		-- 1.3.6.1.4.1.1916.2.131.50.1.3.18.26.2.1.7
		extremeWingCfgDevVrrpGroupAdvertisementIntervalV2Msec OBJECT-TYPE
			SYNTAX Unsigned32 (50..999)
			UNITS "milliseconds"
			MAX-ACCESS read-write
			STATUS current
			DESCRIPTION
				"Time interval between VRRP advertisments
				
				XPath: /extremeWing-config/device[mac=key1]/vrrp_groups[virtual_router_id=key2]/advertisement_interval/advertisement_interval_v2_msec"
			::= { extremeWingCfgDevVrrpGroupEntry 7 }

		
		-- 1.3.6.1.4.1.1916.2.131.50.1.3.18.26.2.1.8
		extremeWingCfgDevVrrpGroupAdvertisementIntervalV3 OBJECT-TYPE
			SYNTAX Unsigned32 (1..4095)
			UNITS "centiseconds"
			MAX-ACCESS read-write
			STATUS current
			DESCRIPTION
				"Time interval between VRRP advertisments
				
				XPath: /extremeWing-config/device[mac=key1]/vrrp_groups[virtual_router_id=key2]/advertisement_interval/advertisement_interval_v3"
			DEFVAL { 100 }
			::= { extremeWingCfgDevVrrpGroupEntry 8 }

		
		-- 1.3.6.1.4.1.1916.2.131.50.1.3.18.26.2.1.9
		extremeWingCfgDevVrrpGroupPreempt OBJECT-TYPE
			SYNTAX TruthValue
			MAX-ACCESS read-write
			STATUS current
			DESCRIPTION
				"Controls whether a higher priority backup router will preempt a lower priority master.
				
				XPath: /extremeWing-config/device[mac=key1]/vrrp_groups[virtual_router_id=key2]/preemption/preempt"
			DEFVAL { true }
			::= { extremeWingCfgDevVrrpGroupEntry 9 }

		
		-- 1.3.6.1.4.1.1916.2.131.50.1.3.18.26.2.1.10
		extremeWingCfgDevVrrpGroupPreemptDelay OBJECT-TYPE
			SYNTAX Unsigned32 (1..65535)
			UNITS "seconds"
			MAX-ACCESS read-write
			STATUS current
			DESCRIPTION
				"Delay interval for pre-emption
				
				XPath: /extremeWing-config/device[mac=key1]/vrrp_groups[virtual_router_id=key2]/preemption/preempt_delay"
			::= { extremeWingCfgDevVrrpGroupEntry 10 }

		
		-- 1.3.6.1.4.1.1916.2.131.50.1.3.18.26.2.1.11
		extremeWingCfgDevVrrpGroupCrmAction OBJECT-TYPE
			SYNTAX DisplayString
			MAX-ACCESS read-write
			STATUS current
			DESCRIPTION
				"Backup virtual router may raise its priority in case the critical resources connected via the master router fail so that
				
				Values:
				increment-priority,
				decrement-priority,
				none
				
				XPath: /extremeWing-config/device[mac=key1]/vrrp_groups[virtual_router_id=key2]/crm_action"
			DEFVAL { "none" }
			::= { extremeWingCfgDevVrrpGroupEntry 11 }

		
		-- 1.3.6.1.4.1.1916.2.131.50.1.3.18.26.2.1.12
		extremeWingCfgDevVrrpGroupDeltaPriority OBJECT-TYPE
			SYNTAX Unsigned32 (1..253)
			MAX-ACCESS read-write
			STATUS current
			DESCRIPTION
				"The configured priority will be decremented by this value when the monitored interface state is down. In case of critical resource monitoring, the configured priority will be incremented by this value
				
				XPath: /extremeWing-config/device[mac=key1]/vrrp_groups[virtual_router_id=key2]/delta_priority"
			::= { extremeWingCfgDevVrrpGroupEntry 12 }

		
		-- 1.3.6.1.4.1.1916.2.131.50.1.3.18.26.2.1.13
		extremeWingCfgDevVrrpGroupInterface OBJECT-TYPE
			SYNTAX Unsigned32 (1..4094)
			MAX-ACCESS read-write
			STATUS current
			DESCRIPTION
				"The SVI (VLAN only) interface on which VRRP will be running. This also enable/disable VRRP operations
				
				XPath: /extremeWing-config/device[mac=key1]/vrrp_groups[virtual_router_id=key2]/interface"
			::= { extremeWingCfgDevVrrpGroupEntry 13 }

		
		-- 1.3.6.1.4.1.1916.2.131.50.1.3.18.26.2.1.14
		extremeWingCfgDevVrrpGroupSyncGroup OBJECT-TYPE
			SYNTAX TruthValue
			MAX-ACCESS read-write
			STATUS current
			DESCRIPTION
				"Make this group part of vrrp sync group. This triggers VRRP failover only when advertisement is not received from all the masters of the virtual routers that is part of this vrrp sync group
				
				XPath: /extremeWing-config/device[mac=key1]/vrrp_groups[virtual_router_id=key2]/sync_group"
			DEFVAL { false }
			::= { extremeWingCfgDevVrrpGroupEntry 14 }

		
		-- 1.3.6.1.4.1.1916.2.131.50.1.3.18.27
		extremeWingCfgDevIgs OBJECT IDENTIFIER ::= { extremeWingCfgDev 27 }

		
		-- 1.3.6.1.4.1.1916.2.131.50.1.3.18.27.1
		extremeWingCfgDevIgsTable OBJECT-TYPE
			SYNTAX SEQUENCE OF ExtremeWingCfgDevIgsEntry
			MAX-ACCESS not-accessible
			STATUS current
			DESCRIPTION
				"
				
				/extremeWing-config/device"
			::= { extremeWingCfgDevIgs 1 }

		
		-- 1.3.6.1.4.1.1916.2.131.50.1.3.18.27.1.1
		extremeWingCfgDevIgsEntry OBJECT-TYPE
			SYNTAX ExtremeWingCfgDevIgsEntry
			MAX-ACCESS not-accessible
			STATUS current
			DESCRIPTION
				"An entry in the table."
			INDEX { extremeWingCfgDevMac }
			::= { extremeWingCfgDevIgsTable 1 }

		
		ExtremeWingCfgDevIgsEntry ::=
			SEQUENCE { 
				extremeWingCfgDevIgsIpIgmpSnooping
					TruthValue,
				extremeWingCfgDevIgsIpIgmpSnoopingForwardUnknownMulticast
					TruthValue,
				extremeWingCfgDevIgsIpIgmpSnoopingQuerier
					TruthValue,
				extremeWingCfgDevIgsIpIgmpSnoopingQuerierAddress
					IpAddress,
				extremeWingCfgDevIgsIpIgmpSnoopingQuerierMaxResponseTime
					Unsigned32,
				extremeWingCfgDevIgsIpIgmpSnoopingQuerierOtherQuerierTimerExpiry
					Unsigned32,
				extremeWingCfgDevIgsIpIgmpSnoopingQuerierVersion
					Unsigned32,
				extremeWingCfgDevIgsIpIgmpSnoopingQuerierQueryInterval
					Unsigned32,
				extremeWingCfgDevIgsIpIgmpSnoopingQuerierRobustnessVariable
					Unsigned32
			 }

		-- 1.3.6.1.4.1.1916.2.131.50.1.3.18.27.1.1.1
		extremeWingCfgDevIgsIpIgmpSnooping OBJECT-TYPE
			SYNTAX TruthValue
			MAX-ACCESS read-write
			STATUS current
			DESCRIPTION
				"Enable/Disable igmp snooping; if set to disable, then per vlan bridge configuration is ignored
				
				XPath: /extremeWing-config/device[mac=key1]/ip_igmp_snooping"
			DEFVAL { true }
			::= { extremeWingCfgDevIgsEntry 1 }

		
		-- 1.3.6.1.4.1.1916.2.131.50.1.3.18.27.1.1.2
		extremeWingCfgDevIgsIpIgmpSnoopingForwardUnknownMulticast OBJECT-TYPE
			SYNTAX TruthValue
			MAX-ACCESS read-write
			STATUS current
			DESCRIPTION
				"Enable/Disable unknown multicast fowarding
				
				XPath: /extremeWing-config/device[mac=key1]/ip_igmp_snooping_forward_unknown_multicast"
			DEFVAL { false }
			::= { extremeWingCfgDevIgsEntry 2 }

		
		-- 1.3.6.1.4.1.1916.2.131.50.1.3.18.27.1.1.3
		extremeWingCfgDevIgsIpIgmpSnoopingQuerier OBJECT-TYPE
			SYNTAX TruthValue
			MAX-ACCESS read-write
			STATUS current
			DESCRIPTION
				"Enable/Disable on board IGMP querier on the device
				
				XPath: /extremeWing-config/device[mac=key1]/ip_igmp_snooping_querier"
			DEFVAL { false }
			::= { extremeWingCfgDevIgsEntry 3 }

		
		-- 1.3.6.1.4.1.1916.2.131.50.1.3.18.27.1.1.4
		extremeWingCfgDevIgsIpIgmpSnoopingQuerierAddress OBJECT-TYPE
			SYNTAX IpAddress
			MAX-ACCESS read-write
			STATUS current
			DESCRIPTION
				"IP Address used by IGMP querier
				
				XPath: /extremeWing-config/device[mac=key1]/ip_igmp_snooping_querier_address"
			DEFVAL { '00000000'h }
			::= { extremeWingCfgDevIgsEntry 4 }

		
		-- 1.3.6.1.4.1.1916.2.131.50.1.3.18.27.1.1.5
		extremeWingCfgDevIgsIpIgmpSnoopingQuerierMaxResponseTime OBJECT-TYPE
			SYNTAX Unsigned32 (1..25)
			UNITS "seconds"
			MAX-ACCESS read-write
			STATUS current
			DESCRIPTION
				"Maximum query response time
				
				XPath: /extremeWing-config/device[mac=key1]/ip_igmp_snooping_querier_max_response_time"
			DEFVAL { 10 }
			::= { extremeWingCfgDevIgsEntry 5 }

		
		-- 1.3.6.1.4.1.1916.2.131.50.1.3.18.27.1.1.6
		extremeWingCfgDevIgsIpIgmpSnoopingQuerierOtherQuerierTimerExpiry OBJECT-TYPE
			SYNTAX Unsigned32 (60..300)
			UNITS "seconds"
			MAX-ACCESS read-write
			STATUS current
			DESCRIPTION
				"other querier time out value for the IGMP Querier
				
				XPath: /extremeWing-config/device[mac=key1]/ip_igmp_snooping_querier_other_querier_timer_expiry"
			DEFVAL { 60 }
			::= { extremeWingCfgDevIgsEntry 6 }

		
		-- 1.3.6.1.4.1.1916.2.131.50.1.3.18.27.1.1.7
		extremeWingCfgDevIgsIpIgmpSnoopingQuerierVersion OBJECT-TYPE
			SYNTAX Unsigned32 (1..3)
			MAX-ACCESS read-write
			STATUS current
			DESCRIPTION
				"IGMP version for the querier
				
				XPath: /extremeWing-config/device[mac=key1]/ip_igmp_snooping_querier_version"
			DEFVAL { 3 }
			::= { extremeWingCfgDevIgsEntry 7 }

		
		-- 1.3.6.1.4.1.1916.2.131.50.1.3.18.27.1.1.8
		extremeWingCfgDevIgsIpIgmpSnoopingQuerierQueryInterval OBJECT-TYPE
			SYNTAX Unsigned32 (1..18000)
			UNITS "seconds"
			MAX-ACCESS read-write
			STATUS current
			DESCRIPTION
				"
				
				XPath: /extremeWing-config/device[mac=key1]/ip_igmp_snooping_querier_query_interval"
			DEFVAL { 60 }
			::= { extremeWingCfgDevIgsEntry 8 }

		
		-- 1.3.6.1.4.1.1916.2.131.50.1.3.18.27.1.1.9
		extremeWingCfgDevIgsIpIgmpSnoopingQuerierRobustnessVariable OBJECT-TYPE
			SYNTAX Unsigned32 (1..7)
			MAX-ACCESS read-write
			STATUS current
			DESCRIPTION
				"
				
				XPath: /extremeWing-config/device[mac=key1]/ip_igmp_snooping_querier_robustness_variable"
			DEFVAL { 2 }
			::= { extremeWingCfgDevIgsEntry 9 }

		
		-- 1.3.6.1.4.1.1916.2.131.50.1.3.18.28
		extremeWingCfgDevDynRoute OBJECT IDENTIFIER ::= { extremeWingCfgDev 28 }

		
		-- 1.3.6.1.4.1.1916.2.131.50.1.3.18.28.1
		extremeWingCfgDevDynRouteOspfTable OBJECT-TYPE
			SYNTAX SEQUENCE OF ExtremeWingCfgDevDynRouteOspfEntry
			MAX-ACCESS not-accessible
			STATUS current
			DESCRIPTION
				"Route Ospf Table.
				
				/extremeWing-config/device/dynamic_router_ospf"
			::= { extremeWingCfgDevDynRoute 1 }

		
		-- 1.3.6.1.4.1.1916.2.131.50.1.3.18.28.1.1
		extremeWingCfgDevDynRouteOspfEntry OBJECT-TYPE
			SYNTAX ExtremeWingCfgDevDynRouteOspfEntry
			MAX-ACCESS not-accessible
			STATUS current
			DESCRIPTION
				"An entry in the table."
			INDEX { extremeWingCfgDevMac }
			::= { extremeWingCfgDevDynRouteOspfTable 1 }

		
		ExtremeWingCfgDevDynRouteOspfEntry ::=
			SEQUENCE { 
				extremeWingCfgDevDynRouteOspfEnabled
					TruthValue,
				extremeWingCfgDevDynRouteOspfRouterId
					OCTET STRING,
				extremeWingCfgDevDynRouteOspfAutoCost
					Unsigned32,
				extremeWingCfgDevDynRouteOspfPassiveAll
					TruthValue,
				extremeWingCfgDevDynRouteOspfPassive
					DisplayString,
				extremeWingCfgDevDynRouteOspfPassiveRemoved
					DisplayString,
				extremeWingCfgDevDynRouteOspfVrrpStateCheck
					TruthValue,
				extremeWingCfgDevDynRouteOspfDefaultRoutePriority
					Unsigned32,
				extremeWingCfgDevDynRouteOspfNumRoutes
					Unsigned32,
				extremeWingCfgDevDynRouteOspfRetryCount
					Unsigned32,
				extremeWingCfgDevDynRouteOspfRetryTimeout
					Unsigned32,
				extremeWingCfgDevDynRouteOspfResetTime
					Unsigned32
			 }

		-- 1.3.6.1.4.1.1916.2.131.50.1.3.18.28.1.1.1
		extremeWingCfgDevDynRouteOspfEnabled OBJECT-TYPE
			SYNTAX TruthValue
			MAX-ACCESS read-write
			STATUS current
			DESCRIPTION
				"Dynamic routing protocol OSPF
				
				XPath: /extremeWing-config/device[mac=key1]/dynamic_router_ospf/ospf"
			DEFVAL { false }
			::= { extremeWingCfgDevDynRouteOspfEntry 1 }

		
		-- 1.3.6.1.4.1.1916.2.131.50.1.3.18.28.1.1.2
		extremeWingCfgDevDynRouteOspfRouterId OBJECT-TYPE
			SYNTAX OCTET STRING
			MAX-ACCESS read-write
			STATUS current
			DESCRIPTION
				"Router-ID for this device. If Router-ID is not configured, system generates one and it can be viewed in statistics
				
				XPath: /extremeWing-config/device[mac=key1]/dynamic_router_ospf/router_id"
			::= { extremeWingCfgDevDynRouteOspfEntry 2 }

		
		-- 1.3.6.1.4.1.1916.2.131.50.1.3.18.28.1.1.3
		extremeWingCfgDevDynRouteOspfAutoCost OBJECT-TYPE
			SYNTAX Unsigned32 (1..4294967)
			MAX-ACCESS read-write
			STATUS current
			DESCRIPTION
				"Specifies reference bandwidth to be used in Mbps to calculate OSPF interface cost if OSPF area is STUB or NSSA
				
				XPath: /extremeWing-config/device[mac=key1]/dynamic_router_ospf/auto_cost"
			::= { extremeWingCfgDevDynRouteOspfEntry 3 }

		
		-- 1.3.6.1.4.1.1916.2.131.50.1.3.18.28.1.1.4
		extremeWingCfgDevDynRouteOspfPassiveAll OBJECT-TYPE
			SYNTAX TruthValue
			MAX-ACCESS read-write
			STATUS current
			DESCRIPTION
				"Configures all L3 interfaces as OSPF passive interface
				
				XPath: /extremeWing-config/device[mac=key1]/dynamic_router_ospf/passive_all"
			DEFVAL { false }
			::= { extremeWingCfgDevDynRouteOspfEntry 4 }

		
		-- 1.3.6.1.4.1.1916.2.131.50.1.3.18.28.1.1.5
		extremeWingCfgDevDynRouteOspfPassive OBJECT-TYPE
			SYNTAX DisplayString
			MAX-ACCESS read-write
			STATUS current
			DESCRIPTION
				"Configures specified interface(s) as OSPF passive interface(s).
				
				XPath: /extremeWing-config/device[mac=key1]/dynamic_router_ospf/passive"
			::= { extremeWingCfgDevDynRouteOspfEntry 5 }

		
		-- 1.3.6.1.4.1.1916.2.131.50.1.3.18.28.1.1.6
		extremeWingCfgDevDynRouteOspfPassiveRemoved OBJECT-TYPE
			SYNTAX DisplayString
			MAX-ACCESS read-write
			STATUS current
			DESCRIPTION
				"Configures specified interface(s) as OSPF NON-passive interface(s).
				
				XPath: /extremeWing-config/device[mac=key1]/dynamic_router_ospf/passive_removed"
			REFERENCE
				"Configures specified interface(s) as OSPF NON-passive interface(s)."
			::= { extremeWingCfgDevDynRouteOspfEntry 6 }

		
		-- 1.3.6.1.4.1.1916.2.131.50.1.3.18.28.1.1.7
		extremeWingCfgDevDynRouteOspfVrrpStateCheck OBJECT-TYPE
			SYNTAX TruthValue
			MAX-ACCESS read-write
			STATUS current
			DESCRIPTION
				"Publish interface via OSPF only if the interface VRRP state is not BACKUP.
				
				XPath: /extremeWing-config/device[mac=key1]/dynamic_router_ospf/vrrp_state_check"
			::= { extremeWingCfgDevDynRouteOspfEntry 7 }

		
		-- 1.3.6.1.4.1.1916.2.131.50.1.3.18.28.1.1.8
		extremeWingCfgDevDynRouteOspfDefaultRoutePriority OBJECT-TYPE
			SYNTAX Unsigned32 (1..8000)
			MAX-ACCESS read-write
			STATUS current
			DESCRIPTION
				"Priority for the default route learnt via OSPF.
				
				XPath: /extremeWing-config/device[mac=key1]/dynamic_router_ospf/ospf_default_route_priority"
			DEFVAL { 7000 }
			::= { extremeWingCfgDevDynRouteOspfEntry 8 }

		
		-- 1.3.6.1.4.1.1916.2.131.50.1.3.18.28.1.1.9
		extremeWingCfgDevDynRouteOspfNumRoutes OBJECT-TYPE
			SYNTAX Unsigned32 (1..4294967295)
			MAX-ACCESS read-write
			STATUS current
			DESCRIPTION
				"Maximum number of OSPF routes allowed.
				
				XPath: /extremeWing-config/device[mac=key1]/dynamic_router_ospf/route_limit/num_routes"
			::= { extremeWingCfgDevDynRouteOspfEntry 9 }

		
		-- 1.3.6.1.4.1.1916.2.131.50.1.3.18.28.1.1.10
		extremeWingCfgDevDynRouteOspfRetryCount OBJECT-TYPE
			SYNTAX Unsigned32 (1..32)
			MAX-ACCESS read-write
			STATUS current
			DESCRIPTION
				"Maximum number for which OSPF process will be reset before permanently shutting down OSPF.
				
				XPath: /extremeWing-config/device[mac=key1]/dynamic_router_ospf/route_limit/retry_count"
			DEFVAL { 5 }
			::= { extremeWingCfgDevDynRouteOspfEntry 10 }

		
		-- 1.3.6.1.4.1.1916.2.131.50.1.3.18.28.1.1.11
		extremeWingCfgDevDynRouteOspfRetryTimeout OBJECT-TYPE
			SYNTAX Unsigned32 (1..3600)
			MAX-ACCESS read-write
			STATUS current
			DESCRIPTION
				"Time in seconds during which the OSPF process remains shut before attempting next retry.
				
				XPath: /extremeWing-config/device[mac=key1]/dynamic_router_ospf/route_limit/retry_timeout"
			DEFVAL { 60 }
			::= { extremeWingCfgDevDynRouteOspfEntry 11 }

		
		-- 1.3.6.1.4.1.1916.2.131.50.1.3.18.28.1.1.12
		extremeWingCfgDevDynRouteOspfResetTime OBJECT-TYPE
			SYNTAX Unsigned32 (1..86400)
			MAX-ACCESS read-write
			STATUS current
			DESCRIPTION
				"Time in seconds after which retry-count is reset to zero.
				
				XPath: /extremeWing-config/device[mac=key1]/dynamic_router_ospf/route_limit/reset_time"
			DEFVAL { 360 }
			::= { extremeWingCfgDevDynRouteOspfEntry 12 }

		
		-- 1.3.6.1.4.1.1916.2.131.50.1.3.18.28.2
		extremeWingCfgDevDynRouteOspfNetworkTable OBJECT-TYPE
			SYNTAX SEQUENCE OF ExtremeWingCfgDevDynRouteOspfNetworkEntry
			MAX-ACCESS not-accessible
			STATUS current
			DESCRIPTION
				"Route Ospf Network Table
				
				/extremeWing-config/device/dynamic_router_cfg/ospf_network"
			::= { extremeWingCfgDevDynRoute 2 }

		
		-- 1.3.6.1.4.1.1916.2.131.50.1.3.18.28.2.1
		extremeWingCfgDevDynRouteOspfNetworkEntry OBJECT-TYPE
			SYNTAX ExtremeWingCfgDevDynRouteOspfNetworkEntry
			MAX-ACCESS not-accessible
			STATUS current
			DESCRIPTION
				"An entry in the table."
			INDEX { extremeWingCfgDevMac, extremeWingCfgDevDynRouteOspfNetwork }
			::= { extremeWingCfgDevDynRouteOspfNetworkTable 1 }

		
		ExtremeWingCfgDevDynRouteOspfNetworkEntry ::=
			SEQUENCE { 
				extremeWingCfgDevDynRouteOspfNetwork
					ExtremeWingIdentifier,
				extremeWingCfgDevDynRouteOspfNetworkAreaId
					IpAddress
			 }

		-- 1.3.6.1.4.1.1916.2.131.50.1.3.18.28.2.1.1
		extremeWingCfgDevDynRouteOspfNetwork OBJECT-TYPE
			SYNTAX ExtremeWingIdentifier
			MAX-ACCESS read-only
			STATUS current
			DESCRIPTION
				"Networks that need to participate in OSPF
				
				XPath: /extremeWing-config/device[mac=key1]/dynamic_router_ospf/ospf_network[network=key2]/network"
			::= { extremeWingCfgDevDynRouteOspfNetworkEntry 1 }

		
		-- 1.3.6.1.4.1.1916.2.131.50.1.3.18.28.2.1.3
		extremeWingCfgDevDynRouteOspfNetworkAreaId OBJECT-TYPE
			SYNTAX IpAddress
			MAX-ACCESS read-write
			STATUS current
			DESCRIPTION
				"OSPF area to which this network belongs; area is a 32 bit number, which can be represented as IPv4 address
				
				XPath: /extremeWing-config/device[mac=key1]/dynamic_router_ospf/ospf_network[network=key2]/area_id"
			::= { extremeWingCfgDevDynRouteOspfNetworkEntry 3 }

		
		-- 1.3.6.1.4.1.1916.2.131.50.1.3.18.28.3
		extremeWingCfgDevDynRouteOspfAreaTable OBJECT-TYPE
			SYNTAX SEQUENCE OF ExtremeWingCfgDevDynRouteOspfAreaEntry
			MAX-ACCESS not-accessible
			STATUS current
			DESCRIPTION
				"RouteOspfAreaTable
				
				/extremeWing-config/device/dynamic_router_cfg/ospf_area"
			::= { extremeWingCfgDevDynRoute 3 }

		
		-- 1.3.6.1.4.1.1916.2.131.50.1.3.18.28.3.1
		extremeWingCfgDevDynRouteOspfAreaEntry OBJECT-TYPE
			SYNTAX ExtremeWingCfgDevDynRouteOspfAreaEntry
			MAX-ACCESS not-accessible
			STATUS current
			DESCRIPTION
				"An entry in the table."
			INDEX { extremeWingCfgDevMac, extremeWingCfgDevDynRouteOspfAreaId }
			::= { extremeWingCfgDevDynRouteOspfAreaTable 1 }

		
		ExtremeWingCfgDevDynRouteOspfAreaEntry ::=
			SEQUENCE { 
				extremeWingCfgDevDynRouteOspfAreaId
					ExtremeWingIdentifier,
				extremeWingCfgDevDynRouteOspfAreaAuthentication
					DisplayString,
				extremeWingCfgDevDynRouteOspfAreaRange
					DisplayString,
				extremeWingCfgDevDynRouteOspfAreaType
					DisplayString,
				extremeWingCfgDevDynRouteOspfAreaDefaultCost
					Unsigned32,
				extremeWingCfgDevDynRouteOspfAreaTranslateType
					DisplayString
			 }

		-- 1.3.6.1.4.1.1916.2.131.50.1.3.18.28.3.1.1
		extremeWingCfgDevDynRouteOspfAreaId OBJECT-TYPE
			SYNTAX ExtremeWingIdentifier
			MAX-ACCESS read-only
			STATUS current
			DESCRIPTION
				"OSPF area related parameters
				
				XPath: /extremeWing-config/device[mac=key1]/dynamic_router_ospf/ospf_area[ospf_area_id=key2]/ospf_area_id"
			::= { extremeWingCfgDevDynRouteOspfAreaEntry 1 }

		
		-- 1.3.6.1.4.1.1916.2.131.50.1.3.18.28.3.1.3
		extremeWingCfgDevDynRouteOspfAreaAuthentication OBJECT-TYPE
			SYNTAX DisplayString
			MAX-ACCESS read-write
			STATUS current
			DESCRIPTION
				"OSPF authentication type
				
				Values:
				simple-password,
				message-digest,
				none
				
				XPath: /extremeWing-config/device[mac=key1]/dynamic_router_ospf/ospf_area[ospf_area_id=key2]/authentication"
			DEFVAL { "none" }
			::= { extremeWingCfgDevDynRouteOspfAreaEntry 3 }

		
		-- 1.3.6.1.4.1.1916.2.131.50.1.3.18.28.3.1.4
		extremeWingCfgDevDynRouteOspfAreaRange OBJECT-TYPE
			SYNTAX DisplayString
			MAX-ACCESS read-only
			STATUS current
			DESCRIPTION
				"Specifies the routes matching address/mask for summarization
				
				XPath: /extremeWing-config/device[mac=key1]/dynamic_router_ospf/ospf_area[ospf_area_id=key2]/range"
			::= { extremeWingCfgDevDynRouteOspfAreaEntry 4 }

		
		-- 1.3.6.1.4.1.1916.2.131.50.1.3.18.28.3.1.5
		extremeWingCfgDevDynRouteOspfAreaType OBJECT-TYPE
			SYNTAX DisplayString
			MAX-ACCESS read-write
			STATUS current
			DESCRIPTION
				"Type of this OSPF area
				
				Values:
				stub,
				totally-stub,
				nssa,
				totally-nssa,
				non-stub
				
				XPath: /extremeWing-config/device[mac=key1]/dynamic_router_ospf/ospf_area[ospf_area_id=key2]/area_type/type"
			DEFVAL { "non-stub" }
			::= { extremeWingCfgDevDynRouteOspfAreaEntry 5 }

		
		-- 1.3.6.1.4.1.1916.2.131.50.1.3.18.28.3.1.6
		extremeWingCfgDevDynRouteOspfAreaDefaultCost OBJECT-TYPE
			SYNTAX Unsigned32 (1..16777215)
			MAX-ACCESS read-write
			STATUS current
			DESCRIPTION
				"Default summary cost that will be advertised if this are is stub
				
				XPath: /extremeWing-config/device[mac=key1]/dynamic_router_ospf/ospf_area[ospf_area_id=key2]/area_type/default_cost"
			::= { extremeWingCfgDevDynRouteOspfAreaEntry 6 }

		
		-- 1.3.6.1.4.1.1916.2.131.50.1.3.18.28.3.1.7
		extremeWingCfgDevDynRouteOspfAreaTranslateType OBJECT-TYPE
			SYNTAX DisplayString
			MAX-ACCESS read-write
			STATUS current
			DESCRIPTION
				"Configures if/how LSA Type 7 message shall be translated
				
				Values:
				translate-always,
				translate-candidate,
				translate-never
				
				XPath: /extremeWing-config/device[mac=key1]/dynamic_router_ospf/ospf_area[ospf_area_id=key2]/area_type/translate_type"
			::= { extremeWingCfgDevDynRouteOspfAreaEntry 7 }

		
		-- 1.3.6.1.4.1.1916.2.131.50.1.3.18.28.4
		extremeWingCfgDevDynRouteDefaultInfoTable OBJECT-TYPE
			SYNTAX SEQUENCE OF ExtremeWingCfgDevDynRouteDefaultInfoEntry
			MAX-ACCESS not-accessible
			STATUS current
			DESCRIPTION
				"Description."
			::= { extremeWingCfgDevDynRoute 4 }
-- Dyn Route Default Info.
-- 
-- XPath: /extremeWing-config/device[mac=key1]/dynamic_router_ospf/default_information
		
		-- 1.3.6.1.4.1.1916.2.131.50.1.3.18.28.4.1
		extremeWingCfgDevDynRouteDefaultInfoEntry OBJECT-TYPE
			SYNTAX ExtremeWingCfgDevDynRouteDefaultInfoEntry
			MAX-ACCESS not-accessible
			STATUS current
			DESCRIPTION
				"An entry in the table."
			INDEX { extremeWingCfgDevMac }
			::= { extremeWingCfgDevDynRouteDefaultInfoTable 1 }

		
		ExtremeWingCfgDevDynRouteDefaultInfoEntry ::=
			SEQUENCE { 
				extremeWingCfgDevDynRouteDefaultInfoOriginate
					TruthValue,
				extremeWingCfgDevDynRouteDefaultInfoAlways
					TruthValue,
				extremeWingCfgDevDynRouteDefaultInfoRtMetric
					Unsigned32,
				extremeWingCfgDevDynRouteDefaultInfoRtMetricType
					DisplayString
			 }

		-- 1.3.6.1.4.1.1916.2.131.50.1.3.18.28.4.1.1
		extremeWingCfgDevDynRouteDefaultInfoOriginate OBJECT-TYPE
			SYNTAX TruthValue
			MAX-ACCESS read-write
			STATUS current
			DESCRIPTION
				"Specifies whether default route should be distributed or not.
				
				XPath: /extremeWing-config/device[mac=key1]/dynamic_router_ospf/default_information/originate"
			::= { extremeWingCfgDevDynRouteDefaultInfoEntry 1 }

		
		-- 1.3.6.1.4.1.1916.2.131.50.1.3.18.28.4.1.2
		extremeWingCfgDevDynRouteDefaultInfoAlways OBJECT-TYPE
			SYNTAX TruthValue
			MAX-ACCESS read-write
			STATUS current
			DESCRIPTION
				"Originate a default route even if one is not present in routing table.
				
				XPath: /extremeWing-config/device[mac=key1]/dynamic_router_ospf/default_information/always"
			::= { extremeWingCfgDevDynRouteDefaultInfoEntry 2 }

		
		-- 1.3.6.1.4.1.1916.2.131.50.1.3.18.28.4.1.3
		extremeWingCfgDevDynRouteDefaultInfoRtMetric OBJECT-TYPE
			SYNTAX Unsigned32 (1..16777214)
			MAX-ACCESS read-write
			STATUS current
			DESCRIPTION
				"Metric for default route.
				
				XPath: /extremeWing-config/device[mac=key1]/dynamic_router_ospf/default_information/default_rt_metric"
			::= { extremeWingCfgDevDynRouteDefaultInfoEntry 3 }

		
		-- 1.3.6.1.4.1.1916.2.131.50.1.3.18.28.4.1.4
		extremeWingCfgDevDynRouteDefaultInfoRtMetricType OBJECT-TYPE
			SYNTAX DisplayString
			MAX-ACCESS read-write
			STATUS current
			DESCRIPTION
				"OSPF exterior metric type for default route.
				Values:
				1
				2
				
				XPath: /extremeWing-config/device[mac=key1]/dynamic_router_ospf/default_information/default_rt_metric_type"
			::= { extremeWingCfgDevDynRouteDefaultInfoEntry 4 }

		
		-- 1.3.6.1.4.1.1916.2.131.50.1.3.18.28.5
		extremeWingCfgDevDynRouteRedistributeTable OBJECT-TYPE
			SYNTAX SEQUENCE OF ExtremeWingCfgDevDynRouteRedistributeEntry
			MAX-ACCESS not-accessible
			STATUS current
			DESCRIPTION
				"
				
				/extremeWing-config/device/dynamic_router_cfg/redistribute"
			::= { extremeWingCfgDevDynRoute 5 }

		
		-- 1.3.6.1.4.1.1916.2.131.50.1.3.18.28.5.1
		extremeWingCfgDevDynRouteRedistributeEntry OBJECT-TYPE
			SYNTAX ExtremeWingCfgDevDynRouteRedistributeEntry
			MAX-ACCESS not-accessible
			STATUS current
			DESCRIPTION
				"An entry in the table."
			INDEX { extremeWingCfgDevMac, extremeWingCfgDevDynRouteRedistributeRouteType }
			::= { extremeWingCfgDevDynRouteRedistributeTable 1 }

		
		ExtremeWingCfgDevDynRouteRedistributeEntry ::=
			SEQUENCE { 
				extremeWingCfgDevDynRouteRedistributeRouteType
					ExtremeWingIdentifier,
				extremeWingCfgDevDynRouteRedistributeMetric
					Unsigned32,
				extremeWingCfgDevDynRouteRedistributeMetricType
					DisplayString
			 }

		-- 1.3.6.1.4.1.1916.2.131.50.1.3.18.28.5.1.1
		extremeWingCfgDevDynRouteRedistributeRouteType OBJECT-TYPE
			SYNTAX ExtremeWingIdentifier
			MAX-ACCESS read-only
			STATUS current
			DESCRIPTION
				"Type of redistributed type
				
				Values:
				connected,
				kernel,
				static
				
				XPath: /extremeWing-config/device[mac=key1]/dynamic_router_ospf/redistribute[route_type=key2]/route_type"
			::= { extremeWingCfgDevDynRouteRedistributeEntry 1 }

		
		-- 1.3.6.1.4.1.1916.2.131.50.1.3.18.28.5.1.3
		extremeWingCfgDevDynRouteRedistributeMetric OBJECT-TYPE
			SYNTAX Unsigned32 (1..16777214)
			MAX-ACCESS read-write
			STATUS current
			DESCRIPTION
				"Metric for redistributed routes
				
				XPath: /extremeWing-config/device[mac=key1]/dynamic_router_ospf/redistribute[route_type=key2]/metric"
			::= { extremeWingCfgDevDynRouteRedistributeEntry 3 }

		
		-- 1.3.6.1.4.1.1916.2.131.50.1.3.18.28.5.1.4
		extremeWingCfgDevDynRouteRedistributeMetricType OBJECT-TYPE
			SYNTAX DisplayString
			MAX-ACCESS read-write
			STATUS current
			DESCRIPTION
				"OSPF exterior metric type for redistributed routes
				
				Values:
				1,
				2
				
				XPath: /extremeWing-config/device[mac=key1]/dynamic_router_ospf/redistribute[route_type=key2]/metric_type"
			::= { extremeWingCfgDevDynRouteRedistributeEntry 4 }

		
		-- 1.3.6.1.4.1.1916.2.131.50.1.3.18.29
		extremeWingCfgDevCriticalRes OBJECT IDENTIFIER ::= { extremeWingCfgDev 29 }

		
		-- 1.3.6.1.4.1.1916.2.131.50.1.3.18.29.1
		extremeWingCfgDevCriticalResMonitorTable OBJECT-TYPE
			SYNTAX SEQUENCE OF ExtremeWingCfgDevCriticalResMonitorEntry
			MAX-ACCESS not-accessible
			STATUS current
			DESCRIPTION
				"
				
				/extremeWing-config/profile"
			::= { extremeWingCfgDevCriticalRes 1 }

		
		-- 1.3.6.1.4.1.1916.2.131.50.1.3.18.29.1.1
		extremeWingCfgDevCriticalResMonitorEntry OBJECT-TYPE
			SYNTAX ExtremeWingCfgDevCriticalResMonitorEntry
			MAX-ACCESS not-accessible
			STATUS current
			DESCRIPTION
				"An entry in the table."
			INDEX { extremeWingCfgDevMac }
			::= { extremeWingCfgDevCriticalResMonitorTable 1 }

		
		ExtremeWingCfgDevCriticalResMonitorEntry ::=
			SEQUENCE { 
				extremeWingCfgDevCriticalResMonitorInt
					Unsigned32
			 }

		-- 1.3.6.1.4.1.1916.2.131.50.1.3.18.29.1.1.1
		extremeWingCfgDevCriticalResMonitorInt OBJECT-TYPE
			SYNTAX Unsigned32 (5..86400)
			UNITS "seconds"
			MAX-ACCESS read-write
			STATUS current
			DESCRIPTION
				"Monitoring frequency
				
				XPath: /extremeWing-config/device[mac=key1]/crm_monitor_interval"
			DEFVAL { 30 }
			::= { extremeWingCfgDevCriticalResMonitorEntry 1 }

		
		-- 1.3.6.1.4.1.1916.2.131.50.1.3.18.29.2
		extremeWingCfgDevCriticalResPolicyTable OBJECT-TYPE
			SYNTAX SEQUENCE OF ExtremeWingCfgDevCriticalResPolicyEntry
			MAX-ACCESS not-accessible
			STATUS current
			DESCRIPTION
				"
				
				/extremeWing-config/device/critical_resources"
			::= { extremeWingCfgDevCriticalRes 2 }

		
		-- 1.3.6.1.4.1.1916.2.131.50.1.3.18.29.2.1
		extremeWingCfgDevCriticalResPolicyEntry OBJECT-TYPE
			SYNTAX ExtremeWingCfgDevCriticalResPolicyEntry
			MAX-ACCESS not-accessible
			STATUS current
			DESCRIPTION
				"An entry in the table."
			INDEX { extremeWingCfgDevMac, extremeWingCfgDevCriticalResPolicyVia }
			::= { extremeWingCfgDevCriticalResPolicyTable 1 }

		
		ExtremeWingCfgDevCriticalResPolicyEntry ::=
			SEQUENCE { 
				extremeWingCfgDevCriticalResPolicyVia
					ExtremeWingIdentifier,
				extremeWingCfgDevCriticalResPolicyAnyAll
					DisplayString
			 }

		-- 1.3.6.1.4.1.1916.2.131.50.1.3.18.29.2.1.1
		extremeWingCfgDevCriticalResPolicyVia OBJECT-TYPE
			SYNTAX ExtremeWingIdentifier
			MAX-ACCESS read-only
			STATUS current
			DESCRIPTION
				"
				
				XPath: /extremeWing-config/device[mac=key1]/critical_resources[via=key2]/via"
			::= { extremeWingCfgDevCriticalResPolicyEntry 1 }

		
		-- 1.3.6.1.4.1.1916.2.131.50.1.3.18.29.2.1.3
		extremeWingCfgDevCriticalResPolicyAnyAll OBJECT-TYPE
			SYNTAX DisplayString
			MAX-ACCESS read-write
			STATUS current
			DESCRIPTION
				"
				
				Values:
				any,
				all
				
				XPath: /extremeWing-config/device[mac=key1]/critical_resources[via=key2]/any_all"
			DEFVAL { "any" }
			::= { extremeWingCfgDevCriticalResPolicyEntry 3 }

		
		-- 1.3.6.1.4.1.1916.2.131.50.1.3.18.29.3
		extremeWingCfgDevCriticalResourcesTable OBJECT-TYPE
			SYNTAX SEQUENCE OF ExtremeWingCfgDevCriticalResourcesEntry
			MAX-ACCESS not-accessible
			STATUS current
			DESCRIPTION
				"
				
				/extremeWing-config/device/critical_resources/resources"
			::= { extremeWingCfgDevCriticalRes 3 }

		
		-- 1.3.6.1.4.1.1916.2.131.50.1.3.18.29.3.1
		extremeWingCfgDevCriticalResourcesEntry OBJECT-TYPE
			SYNTAX ExtremeWingCfgDevCriticalResourcesEntry
			MAX-ACCESS not-accessible
			STATUS current
			DESCRIPTION
				"An entry in the table."
			INDEX { extremeWingCfgDevMac, extremeWingCfgDevCriticalResPolicyVia, extremeWingCfgDevCriticalResourcesAddr }
			::= { extremeWingCfgDevCriticalResourcesTable 1 }

		
		ExtremeWingCfgDevCriticalResourcesEntry ::=
			SEQUENCE { 
				extremeWingCfgDevCriticalResourcesAddr
					ExtremeWingIdentifier,
				extremeWingCfgDevCriticalResourcesMonitorType
					DisplayString,
				extremeWingCfgDevCriticalResourcesVlan
					Unsigned32,
				extremeWingCfgDevCriticalResourcesPort
					DisplayString
			 }

		-- 1.3.6.1.4.1.1916.2.131.50.1.3.18.29.3.1.1
		extremeWingCfgDevCriticalResourcesAddr OBJECT-TYPE
			SYNTAX ExtremeWingIdentifier
			MAX-ACCESS read-only
			STATUS current
			DESCRIPTION
				"
				
				XPath: /extremeWing-config/device[mac=key1]/critical_resources[via=key2]/resources[address=key3]/address"
			::= { extremeWingCfgDevCriticalResourcesEntry 1 }

		
		-- 1.3.6.1.4.1.1916.2.131.50.1.3.18.29.3.1.3
		extremeWingCfgDevCriticalResourcesMonitorType OBJECT-TYPE
			SYNTAX DisplayString
			MAX-ACCESS read-write
			STATUS current
			DESCRIPTION
				"
				
				Values:
				arp-only,
				arp-and-ping
				
				XPath: /extremeWing-config/device[mac=key1]/critical_resources[via=key2]/resources[address=key3]/monitor_type"
			DEFVAL { "arp-and-ping" }
			::= { extremeWingCfgDevCriticalResourcesEntry 3 }

		
		-- 1.3.6.1.4.1.1916.2.131.50.1.3.18.29.3.1.4
		extremeWingCfgDevCriticalResourcesVlan OBJECT-TYPE
			SYNTAX Unsigned32 (1..4094)
			MAX-ACCESS read-write
			STATUS current
			DESCRIPTION
				"
				
				XPath: /extremeWing-config/device[mac=key1]/critical_resources[via=key2]/resources[address=key3]/vlan"
			::= { extremeWingCfgDevCriticalResourcesEntry 4 }

		
		-- 1.3.6.1.4.1.1916.2.131.50.1.3.18.29.3.1.5
		extremeWingCfgDevCriticalResourcesPort OBJECT-TYPE
			SYNTAX DisplayString
			MAX-ACCESS read-write
			STATUS current
			DESCRIPTION
				"
				
				Values:
				ge1, ge2, ge3, ge4, ge5, ge6, ge7, ge8, xge1, xge2, fe1, fe2, fe3, fe4, me1, up1
				
				XPath: /extremeWing-config/device[mac=key1]/critical_resources[via=key2]/resources[address=key3]/port"
			::= { extremeWingCfgDevCriticalResourcesEntry 5 }

		
-- /extremeWing-config/profile/l2tpv3
		-- 1.3.6.1.4.1.1916.2.131.50.1.3.18.30
		extremeWingCfgDevl2tpv3 OBJECT IDENTIFIER ::= { extremeWingCfgDev 30 }

		
-- /extremeWing-config/device/l2tpv3
		-- 1.3.6.1.4.1.1916.2.131.50.1.3.18.30.1
		extremeWingCfgDevl2tpv3Table OBJECT-TYPE
			SYNTAX SEQUENCE OF ExtremeWingCfgDevl2tpv3Entry
			MAX-ACCESS not-accessible
			STATUS current
			DESCRIPTION
				"/extremeWing-config/device/l2tpv3"
			::= { extremeWingCfgDevl2tpv3 1 }

		
		-- 1.3.6.1.4.1.1916.2.131.50.1.3.18.30.1.1
		extremeWingCfgDevl2tpv3Entry OBJECT-TYPE
			SYNTAX ExtremeWingCfgDevl2tpv3Entry
			MAX-ACCESS not-accessible
			STATUS current
			DESCRIPTION
				"An entry in the table."
			INDEX { extremeWingCfgDevMac }
			::= { extremeWingCfgDevl2tpv3Table 1 }

		
		ExtremeWingCfgDevl2tpv3Entry ::=
			SEQUENCE { 
				extremeWingCfgDevl2tpv3lUdpListenPort
					Unsigned32,
				extremeWingCfgDevl2tpv3RouterId
					DisplayString,
				extremeWingCfgDevl2tpv3HostName
					DisplayString,
				extremeWingCfgDevl2tpv3InterTunnelBridging
					TruthValue
			 }

		-- 1.3.6.1.4.1.1916.2.131.50.1.3.18.30.1.1.1
		extremeWingCfgDevl2tpv3lUdpListenPort OBJECT-TYPE
			SYNTAX Unsigned32
			MAX-ACCESS read-write
			STATUS current
			DESCRIPTION
				"The UDP port on which incoming requests are listened.
				
				XPath: /extremeWing-config/device[mac=key1]/l2tpv3_udp_listen_port"
			::= { extremeWingCfgDevl2tpv3Entry 1 }

		
		-- 1.3.6.1.4.1.1916.2.131.50.1.3.18.30.1.1.2
		extremeWingCfgDevl2tpv3RouterId OBJECT-TYPE
			SYNTAX DisplayString
			MAX-ACCESS read-write
			STATUS current
			DESCRIPTION
				"Router Id used in AVP message for the tunnel.
				
				XPath: /extremeWing-config/device[mac=key1]/l2tpv3_router_id"
			::= { extremeWingCfgDevl2tpv3Entry 2 }

		
		-- 1.3.6.1.4.1.1916.2.131.50.1.3.18.30.1.1.3
		extremeWingCfgDevl2tpv3HostName OBJECT-TYPE
			SYNTAX DisplayString
			MAX-ACCESS read-write
			STATUS current
			DESCRIPTION
				"Host name sent in AVP message for the tunnel.
				
				XPath: /extremeWing-config/device[mac=key1]/l2tpv3_host_name"
			::= { extremeWingCfgDevl2tpv3Entry 3 }

		
		-- 1.3.6.1.4.1.1916.2.131.50.1.3.18.30.1.1.4
		extremeWingCfgDevl2tpv3InterTunnelBridging OBJECT-TYPE
			SYNTAX TruthValue
			MAX-ACCESS read-write
			STATUS current
			DESCRIPTION
				"Enable/Disable Bridge packets between tunnels.
				
				XPath: /extremeWing-config/device[mac=key1]/l2tpv3_inter_tunnel_bridging"
			::= { extremeWingCfgDevl2tpv3Entry 4 }

		
-- /extremeWing-config/device/l2tpv3_tunnel
		-- 1.3.6.1.4.1.1916.2.131.50.1.3.18.30.2
		extremeWingCfgDevl2tpv3TunnelTable OBJECT-TYPE
			SYNTAX SEQUENCE OF ExtremeWingCfgDevl2tpv3TunnelEntry
			MAX-ACCESS not-accessible
			STATUS current
			DESCRIPTION
				"/extremeWing-config/device/l2tpv3_tunnel"
			::= { extremeWingCfgDevl2tpv3 2 }

		
		-- 1.3.6.1.4.1.1916.2.131.50.1.3.18.30.2.1
		extremeWingCfgDevl2tpv3TunnelEntry OBJECT-TYPE
			SYNTAX ExtremeWingCfgDevl2tpv3TunnelEntry
			MAX-ACCESS not-accessible
			STATUS current
			DESCRIPTION
				"An entry in the table."
			INDEX { extremeWingCfgDevMac, extremeWingCfgDevl2tpv3TunnelName }
			::= { extremeWingCfgDevl2tpv3TunnelTable 1 }

		
		ExtremeWingCfgDevl2tpv3TunnelEntry ::=
			SEQUENCE { 
				extremeWingCfgDevl2tpv3TunnelName
					ExtremeWingIdentifier,
				extremeWingCfgDevl2tpv3TunnelLocalIpAddrss
					IpAddress,
				extremeWingCfgDevl2tpv3TunnelMtu
					Unsigned32,
				extremeWingCfgDevl2tpv3TunnelUseTunnelPolicy
					DisplayString,
				extremeWingCfgDevl2tpv3TunnelHostname
					DisplayString,
				extremeWingCfgDevl2tpv3TunnelRouterId
					DisplayString
			 }

		-- 1.3.6.1.4.1.1916.2.131.50.1.3.18.30.2.1.1
		extremeWingCfgDevl2tpv3TunnelName OBJECT-TYPE
			SYNTAX ExtremeWingIdentifier
			MAX-ACCESS read-only
			STATUS current
			DESCRIPTION
				"tunnel name.
				
				XPath: /extremeWing-config/device[mac=key1]/l2tpv3_tunnel[name=key2]/name"
			::= { extremeWingCfgDevl2tpv3TunnelEntry 1 }

		
		-- 1.3.6.1.4.1.1916.2.131.50.1.3.18.30.2.1.3
		extremeWingCfgDevl2tpv3TunnelLocalIpAddrss OBJECT-TYPE
			SYNTAX IpAddress
			MAX-ACCESS read-write
			STATUS current
			DESCRIPTION
				"Use this IP as local tunnel endpoint address, instead of the interface IP.
				
				XPath: /extremeWing-config/device[mac=key1]/l2tpv3_tunnel[name=key2]/local_ip_address"
			::= { extremeWingCfgDevl2tpv3TunnelEntry 3 }

		
		-- 1.3.6.1.4.1.1916.2.131.50.1.3.18.30.2.1.4
		extremeWingCfgDevl2tpv3TunnelMtu OBJECT-TYPE
			SYNTAX Unsigned32
			MAX-ACCESS read-write
			STATUS current
			DESCRIPTION
				"MTU for the tunnel.
				
				XPath: /extremeWing-config/device[mac=key1]/l2tpv3_tunnel[name=key2]/mtu"
			::= { extremeWingCfgDevl2tpv3TunnelEntry 4 }

		
		-- 1.3.6.1.4.1.1916.2.131.50.1.3.18.30.2.1.5
		extremeWingCfgDevl2tpv3TunnelUseTunnelPolicy OBJECT-TYPE
			SYNTAX DisplayString
			MAX-ACCESS read-write
			STATUS current
			DESCRIPTION
				"Policy used for the tunnel.
				
				XPath: /extremeWing-config/device[mac=key1]/l2tpv3_tunnel[name=key2]/use_tunnel_policy"
			::= { extremeWingCfgDevl2tpv3TunnelEntry 5 }

		
		-- 1.3.6.1.4.1.1916.2.131.50.1.3.18.30.2.1.6
		extremeWingCfgDevl2tpv3TunnelHostname OBJECT-TYPE
			SYNTAX DisplayString
			MAX-ACCESS read-write
			STATUS current
			DESCRIPTION
				"Tunnel specific hostname.
				
				XPath: /extremeWing-config/device[mac=key1]/l2tpv3_tunnel[name=key2]/tunnel_hostname"
			::= { extremeWingCfgDevl2tpv3TunnelEntry 6 }

		
		-- 1.3.6.1.4.1.1916.2.131.50.1.3.18.30.2.1.7
		extremeWingCfgDevl2tpv3TunnelRouterId OBJECT-TYPE
			SYNTAX DisplayString
			MAX-ACCESS read-write
			STATUS current
			DESCRIPTION
				"Local router-id
				
				XPath: /extremeWing-config/device[mac=key1]/l2tpv3_tunnel[name=key2]/tunnel_router_id"
			::= { extremeWingCfgDevl2tpv3TunnelEntry 7 }

		
-- /extremeWing-config/device/l2tpv3_tunnel/peer
		-- 1.3.6.1.4.1.1916.2.131.50.1.3.18.30.3
		extremeWingCfgDevl2tpv3TunnelPeerTable OBJECT-TYPE
			SYNTAX SEQUENCE OF ExtremeWingCfgDevl2tpv3TunnelPeerEntry
			MAX-ACCESS not-accessible
			STATUS current
			DESCRIPTION
				"/extremeWing-config/device/l2tpv3_tunnel/peer"
			::= { extremeWingCfgDevl2tpv3 3 }

		
		-- 1.3.6.1.4.1.1916.2.131.50.1.3.18.30.3.1
		extremeWingCfgDevl2tpv3TunnelPeerEntry OBJECT-TYPE
			SYNTAX ExtremeWingCfgDevl2tpv3TunnelPeerEntry
			MAX-ACCESS not-accessible
			STATUS current
			DESCRIPTION
				"An entry in the table."
			INDEX { extremeWingCfgDevMac, extremeWingCfgDevl2tpv3TunnelName, extremeWingCfgDevl2tpv3TunnelPeerId }
			::= { extremeWingCfgDevl2tpv3TunnelPeerTable 1 }

		
		ExtremeWingCfgDevl2tpv3TunnelPeerEntry ::=
			SEQUENCE { 
				extremeWingCfgDevl2tpv3TunnelPeerId
					Unsigned32,
				extremeWingCfgDevl2tpv3TunnelPeerIp
					IpAddress,
				extremeWingCfgDev2tpv3TunnelPeerHostName
					DisplayString,
				extremeWingCfgDevl2tpv3TunnelPeerRouterId
					DisplayString,
				extremeWingCfgDevl2tpv3TunnelPeerEncapsulation
					DisplayString,
				extremeWingCfgDevl2tpv3TunnelPeerUDPPort
					Unsigned32
			 }

		-- 1.3.6.1.4.1.1916.2.131.50.1.3.18.30.3.1.1
		extremeWingCfgDevl2tpv3TunnelPeerId OBJECT-TYPE
			SYNTAX Unsigned32 (1..2)
			MAX-ACCESS read-only
			STATUS current
			DESCRIPTION
				"Primary peer to establish the tunnel and secondary peer for failover.
				
				XPath: /extremeWing-config/device[mac=key1]/l2tpv3_tunnel[name=key2]/peer[peer_id=key3]/peer_id"
			::= { extremeWingCfgDevl2tpv3TunnelPeerEntry 1 }

		
		-- 1.3.6.1.4.1.1916.2.131.50.1.3.18.30.3.1.3
		extremeWingCfgDevl2tpv3TunnelPeerIp OBJECT-TYPE
			SYNTAX IpAddress
			MAX-ACCESS read-write
			STATUS current
			DESCRIPTION
				"Peer IP value.
				
				XPath: /extremeWing-config/device[mac=key1]/l2tpv3_tunnel[name=key2]/peer[peer_id=key3]/ip"
			::= { extremeWingCfgDevl2tpv3TunnelPeerEntry 3 }

		
		-- 1.3.6.1.4.1.1916.2.131.50.1.3.18.30.3.1.4
		extremeWingCfgDev2tpv3TunnelPeerHostName OBJECT-TYPE
			SYNTAX DisplayString
			MAX-ACCESS read-write
			STATUS current
			DESCRIPTION
				"Peer hostname.
				
				XPath: /extremeWing-config/device[mac=key1]/l2tpv3_tunnel[name=key2]/peer[peer_id=key3]/hostname"
			::= { extremeWingCfgDevl2tpv3TunnelPeerEntry 4 }

		
		-- 1.3.6.1.4.1.1916.2.131.50.1.3.18.30.3.1.5
		extremeWingCfgDevl2tpv3TunnelPeerRouterId OBJECT-TYPE
			SYNTAX DisplayString
			MAX-ACCESS read-write
			STATUS current
			DESCRIPTION
				"Peer router-id.
				
				XPath: /extremeWing-config/device[mac=key1]/l2tpv3_tunnel[name=key2]/peer[peer_id=key3]/router_id"
			::= { extremeWingCfgDevl2tpv3TunnelPeerEntry 5 }

		
		-- 1.3.6.1.4.1.1916.2.131.50.1.3.18.30.3.1.6
		extremeWingCfgDevl2tpv3TunnelPeerEncapsulation OBJECT-TYPE
			SYNTAX DisplayString
			MAX-ACCESS read-write
			STATUS current
			DESCRIPTION
				"Peer encapsulation protocol.
				
				XPath: /extremeWing-config/device[mac=key1]/l2tpv3_tunnel[name=key2]/peer[peer_id=key3]/encapsulation"
			::= { extremeWingCfgDevl2tpv3TunnelPeerEntry 6 }

		
		-- 1.3.6.1.4.1.1916.2.131.50.1.3.18.30.3.1.7
		extremeWingCfgDevl2tpv3TunnelPeerUDPPort OBJECT-TYPE
			SYNTAX Unsigned32
			MAX-ACCESS read-write
			STATUS current
			DESCRIPTION
				"Peer UDP encapsualtion port.
				
				XPath: /extremeWing-config/device[mac=key1]/l2tpv3_tunnel[name=key2]/peer[peer_id=key3]/udpport"
			::= { extremeWingCfgDevl2tpv3TunnelPeerEntry 7 }

		
-- /extremeWing-config/device/l2tpv3_tunnel/session
		-- 1.3.6.1.4.1.1916.2.131.50.1.3.18.30.4
		extremeWingCfgDevl2tpv3TunnelSessionTable OBJECT-TYPE
			SYNTAX SEQUENCE OF ExtremeWingCfgDevl2tpv3TunnelSessionEntry
			MAX-ACCESS not-accessible
			STATUS current
			DESCRIPTION
				"/extremeWing-config/device/l2tpv3_tunnel/session"
			::= { extremeWingCfgDevl2tpv3 4 }

		
		-- 1.3.6.1.4.1.1916.2.131.50.1.3.18.30.4.1
		extremeWingCfgDevl2tpv3TunnelSessionEntry OBJECT-TYPE
			SYNTAX ExtremeWingCfgDevl2tpv3TunnelSessionEntry
			MAX-ACCESS not-accessible
			STATUS current
			DESCRIPTION
				"An entry in the table."
			INDEX { extremeWingCfgDevMac, extremeWingCfgDevl2tpv3TunnelName, extremeWingCfgDevl2tpv3TunnelSessionName }
			::= { extremeWingCfgDevl2tpv3TunnelSessionTable 1 }

		
		ExtremeWingCfgDevl2tpv3TunnelSessionEntry ::=
			SEQUENCE { 
				extremeWingCfgDevl2tpv3TunnelSessionName
					ExtremeWingIdentifier,
				extremeWingCfgDevl2tpv3TunnelSessionPseudoWireId
					Unsigned32,
				extremeWingCfgDevl2tpv3TunnelSessionTrafficSourceType
					DisplayString,
				extremeWingCfgDevl2tpv3TunnelSessionTrafficSourceValue
					Unsigned32,
				extremeWingCfgDevl2tpv3TunnelSessionNativeVlan
					DisplayString
			 }

		-- 1.3.6.1.4.1.1916.2.131.50.1.3.18.30.4.1.1
		extremeWingCfgDevl2tpv3TunnelSessionName OBJECT-TYPE
			SYNTAX ExtremeWingIdentifier
			MAX-ACCESS read-only
			STATUS current
			DESCRIPTION
				"Name of the Session.
				
				XPath: /extremeWing-config/device[mac=key1]/l2tpv3_tunnel[name=key2]/session[name=key3]/name"
			::= { extremeWingCfgDevl2tpv3TunnelSessionEntry 1 }

		
		-- 1.3.6.1.4.1.1916.2.131.50.1.3.18.30.4.1.3
		extremeWingCfgDevl2tpv3TunnelSessionPseudoWireId OBJECT-TYPE
			SYNTAX Unsigned32
			MAX-ACCESS read-write
			STATUS current
			DESCRIPTION
				"Pseudowire Id for the Session.
				
				XPath: /extremeWing-config/device[mac=key1]/l2tpv3_tunnel[name=key2]/session[name=key3]/pseudowire_id"
			::= { extremeWingCfgDevl2tpv3TunnelSessionEntry 3 }

		
		-- 1.3.6.1.4.1.1916.2.131.50.1.3.18.30.4.1.4
		extremeWingCfgDevl2tpv3TunnelSessionTrafficSourceType OBJECT-TYPE
			SYNTAX DisplayString
			MAX-ACCESS read-write
			STATUS current
			DESCRIPTION
				"Tunneled traffic type.
				
				XPath: /extremeWing-config/device[mac=key1]/l2tpv3_tunnel[name=key2]/session[name=key3]/traffic_source_type"
			::= { extremeWingCfgDevl2tpv3TunnelSessionEntry 4 }

		
		-- 1.3.6.1.4.1.1916.2.131.50.1.3.18.30.4.1.5
		extremeWingCfgDevl2tpv3TunnelSessionTrafficSourceValue OBJECT-TYPE
			SYNTAX Unsigned32
			MAX-ACCESS read-only
			STATUS current
			DESCRIPTION
				"The range of VLAN that is tunneled.
				
				XPath: /extremeWing-config/device[mac=key1]/l2tpv3_tunnel[name=key2]/session[name=key3]/traffic_source_value"
			::= { extremeWingCfgDevl2tpv3TunnelSessionEntry 5 }

		
		-- 1.3.6.1.4.1.1916.2.131.50.1.3.18.30.4.1.6
		extremeWingCfgDevl2tpv3TunnelSessionNativeVlan OBJECT-TYPE
			SYNTAX DisplayString
			MAX-ACCESS read-write
			STATUS current
			DESCRIPTION
				"Vlan id which will not be tagged.
				
				XPath: /extremeWing-config/device[mac=key1]/l2tpv3_tunnel[name=key2]/session[name=key3]/native_vlan"
			::= { extremeWingCfgDevl2tpv3TunnelSessionEntry 6 }

		
-- /extremeWing-config/device/l2tpv3_manual_session
		-- 1.3.6.1.4.1.1916.2.131.50.1.3.18.30.5
		extremeWingCfgDevl2tpv3ManualSessionTable OBJECT-TYPE
			SYNTAX SEQUENCE OF ExtremeWingCfgDevl2tpv3ManualSessionEntry
			MAX-ACCESS not-accessible
			STATUS current
			DESCRIPTION
				"/extremeWing-config/device/l2tpv3_manual_session"
			::= { extremeWingCfgDevl2tpv3 5 }

		
		-- 1.3.6.1.4.1.1916.2.131.50.1.3.18.30.5.1
		extremeWingCfgDevl2tpv3ManualSessionEntry OBJECT-TYPE
			SYNTAX ExtremeWingCfgDevl2tpv3ManualSessionEntry
			MAX-ACCESS not-accessible
			STATUS current
			DESCRIPTION
				"An entry in the table."
			INDEX { extremeWingCfgDevMac, extremeWingCfgDevl2tpv3ManualSessionName }
			::= { extremeWingCfgDevl2tpv3ManualSessionTable 1 }

		
		ExtremeWingCfgDevl2tpv3ManualSessionEntry ::=
			SEQUENCE { 
				extremeWingCfgDevl2tpv3ManualSessionName
					ExtremeWingIdentifier,
				extremeWingCfgDevl2tpv3ManualSessionLocalIpAddr
					IpAddress,
				extremeWingCfgDevl2tpv3ManualSessionPeerIp
					IpAddress,
				extremeWingCfgDevl2tpv3ManualSessionPeerEncapsulation
					DisplayString,
				extremeWingCfgDevl2tpv3ManualSessionPeerUDPPort
					Unsigned32,
				extremeWingCfgDevl2tpv3ManualSessionMtu
					Unsigned32,
				extremeWingCfgDevl2tpv3ManualSessionTrafficSource
					DisplayString,
				extremeWingCfgDevl2tpv3ManualSessionTrafficSourceValue
					Unsigned32,
				extremeWingCfgDevl2tpv3ManualSessionNativeVlan
					DisplayString,
				extremeWingCfgDevl2tpv3ManualSessionLocalSessionId
					Unsigned32,
				extremeWingCfgDevl2tpv3ManualSessionRemoteSessionId
					Unsigned32
			 }

		-- 1.3.6.1.4.1.1916.2.131.50.1.3.18.30.5.1.1
		extremeWingCfgDevl2tpv3ManualSessionName OBJECT-TYPE
			SYNTAX ExtremeWingIdentifier
			MAX-ACCESS read-only
			STATUS current
			DESCRIPTION
				"Name of the session.
				
				XPath: /extremeWing-config/device[mac=key1]/l2tpv3_manual_session[name=key2]/name"
			::= { extremeWingCfgDevl2tpv3ManualSessionEntry 1 }

		
		-- 1.3.6.1.4.1.1916.2.131.50.1.3.18.30.5.1.3
		extremeWingCfgDevl2tpv3ManualSessionLocalIpAddr OBJECT-TYPE
			SYNTAX IpAddress 
			MAX-ACCESS read-write
			STATUS current
			DESCRIPTION
				"Use this IP as local tunnel endpoint address, instead of the interface IP.
				
				XPath: /extremeWing-config/device[mac=key1]/l2tpv3_manual_session[name=key2]/local_ip_address"
			::= { extremeWingCfgDevl2tpv3ManualSessionEntry 3 }

		
		-- 1.3.6.1.4.1.1916.2.131.50.1.3.18.30.5.1.4
		extremeWingCfgDevl2tpv3ManualSessionPeerIp OBJECT-TYPE
			SYNTAX IpAddress
			MAX-ACCESS read-write
			STATUS current
			DESCRIPTION
				"Peer IP value.
				
				XPath: /extremeWing-config/device[mac=key1]/l2tpv3_manual_session[name=key2]/peer/ip"
			::= { extremeWingCfgDevl2tpv3ManualSessionEntry 4 }

		
		-- 1.3.6.1.4.1.1916.2.131.50.1.3.18.30.5.1.5
		extremeWingCfgDevl2tpv3ManualSessionPeerEncapsulation OBJECT-TYPE
			SYNTAX DisplayString
			MAX-ACCESS read-write
			STATUS current
			DESCRIPTION
				"Peer encapsulation protocol.
				
				XPath: /extremeWing-config/device[mac=key1]/l2tpv3_manual_session[name=key2]/peer/encapsulation"
			::= { extremeWingCfgDevl2tpv3ManualSessionEntry 5 }

		
		-- 1.3.6.1.4.1.1916.2.131.50.1.3.18.30.5.1.6
		extremeWingCfgDevl2tpv3ManualSessionPeerUDPPort OBJECT-TYPE
			SYNTAX Unsigned32
			MAX-ACCESS read-write
			STATUS current
			DESCRIPTION
				"Peer UDP encapsualtion port.
				
				XPath: /extremeWing-config/device[mac=key1]/l2tpv3_manual_session[name=key2]/peer/udpport"
			::= { extremeWingCfgDevl2tpv3ManualSessionEntry 6 }

		
		-- 1.3.6.1.4.1.1916.2.131.50.1.3.18.30.5.1.7
		extremeWingCfgDevl2tpv3ManualSessionMtu OBJECT-TYPE
			SYNTAX Unsigned32
			MAX-ACCESS read-write
			STATUS current
			DESCRIPTION
				"MTU for the tunnel.
				
				XPath: /extremeWing-config/device[mac=key1]/l2tpv3_manual_session[name=key2]/mtu"
			::= { extremeWingCfgDevl2tpv3ManualSessionEntry 7 }

		
		-- 1.3.6.1.4.1.1916.2.131.50.1.3.18.30.5.1.8
		extremeWingCfgDevl2tpv3ManualSessionTrafficSource OBJECT-TYPE
			SYNTAX DisplayString
			MAX-ACCESS read-write
			STATUS current
			DESCRIPTION
				"Tunneled traffic type.
				
				XPath: /extremeWing-config/device[mac=key1]/l2tpv3_manual_session[name=key2]/traffic_source/traffic_source_type"
			::= { extremeWingCfgDevl2tpv3ManualSessionEntry 8 }

		
		-- 1.3.6.1.4.1.1916.2.131.50.1.3.18.30.5.1.9
		extremeWingCfgDevl2tpv3ManualSessionTrafficSourceValue OBJECT-TYPE
			SYNTAX Unsigned32
			MAX-ACCESS read-only
			STATUS current
			DESCRIPTION
				"The range of VLAN that is tunneled.
				
				XPath: /extremeWing-config/device[mac=key1]/l2tpv3_manual_session[name=key2]/traffic_source/traffic_source_value"
			::= { extremeWingCfgDevl2tpv3ManualSessionEntry 9 }

		
		-- 1.3.6.1.4.1.1916.2.131.50.1.3.18.30.5.1.10
		extremeWingCfgDevl2tpv3ManualSessionNativeVlan OBJECT-TYPE
			SYNTAX DisplayString
			MAX-ACCESS read-write
			STATUS current
			DESCRIPTION
				"Vlan id which will not be tagged.
				
				XPath: /extremeWing-config/device[mac=key1]/l2tpv3_manual_session[name=key2]/traffic_source/native_vlan"
			::= { extremeWingCfgDevl2tpv3ManualSessionEntry 10 }

		
		-- 1.3.6.1.4.1.1916.2.131.50.1.3.18.30.5.1.11
		extremeWingCfgDevl2tpv3ManualSessionLocalSessionId OBJECT-TYPE
			SYNTAX Unsigned32
			MAX-ACCESS read-write
			STATUS current
			DESCRIPTION
				"Local Session Id. Max limit is platform specific.
				
				XPath: /extremeWing-config/device[mac=key1]/l2tpv3_manual_session[name=key2]/local_session_id"
			::= { extremeWingCfgDevl2tpv3ManualSessionEntry 11 }

		
		-- 1.3.6.1.4.1.1916.2.131.50.1.3.18.30.5.1.12
		extremeWingCfgDevl2tpv3ManualSessionRemoteSessionId OBJECT-TYPE
			SYNTAX Unsigned32
			MAX-ACCESS read-write
			STATUS current
			DESCRIPTION
				"Remote Session Id.
				
				XPath: /extremeWing-config/device[mac=key1]/l2tpv3_manual_session[name=key2]/remote_session_id"
			::= { extremeWingCfgDevl2tpv3ManualSessionEntry 12 }

		
-- /extremeWing-config/device/l2tpv3_manual_session/cookie
		-- 1.3.6.1.4.1.1916.2.131.50.1.3.18.30.6
		extremeWingCfgDevl2tpv3ManualSessionCookieTable OBJECT-TYPE
			SYNTAX SEQUENCE OF ExtremeWingCfgDevl2tpv3ManualSessionCookieEntry
			MAX-ACCESS not-accessible
			STATUS current
			DESCRIPTION
				"/extremeWing-config/device/l2tpv3_manual_session/cookie"
			::= { extremeWingCfgDevl2tpv3 6 }

		
		-- 1.3.6.1.4.1.1916.2.131.50.1.3.18.30.6.1
		extremeWingCfgDevl2tpv3ManualSessionCookieEntry OBJECT-TYPE
			SYNTAX ExtremeWingCfgDevl2tpv3ManualSessionCookieEntry
			MAX-ACCESS not-accessible
			STATUS current
			DESCRIPTION
				"An entry in the table."
			INDEX { extremeWingCfgDevMac, extremeWingCfgDevl2tpv3ManualSessionName, extremeWingCfgDevl2tpv3ManualSessionCookieEndpoint }
			::= { extremeWingCfgDevl2tpv3ManualSessionCookieTable 1 }

		
		ExtremeWingCfgDevl2tpv3ManualSessionCookieEntry ::=
			SEQUENCE { 
				extremeWingCfgDevl2tpv3ManualSessionCookieEndpoint
					ExtremeWingIdentifier,
				extremeWingCfgDevl2tpv3ManualSessionCookieSize
					DisplayString,
				extremeWingCfgDevl2tpv3ManualSessionCookieVal1
					DisplayString,
				extremeWingCfgDevl2tpv3ManualSessionCookieVal2
					DisplayString
			 }

		-- 1.3.6.1.4.1.1916.2.131.50.1.3.18.30.6.1.1
		extremeWingCfgDevl2tpv3ManualSessionCookieEndpoint OBJECT-TYPE
			SYNTAX ExtremeWingIdentifier
			MAX-ACCESS read-only
			STATUS current
			DESCRIPTION
				"Local or Remote endpoint.
				
				XPath: /extremeWing-config/device[mac=key1]/l2tpv3_manual_session[name=key2]/cookie[endpoint=key3]/endpoint"
			::= { extremeWingCfgDevl2tpv3ManualSessionCookieEntry 1 }

		
		-- 1.3.6.1.4.1.1916.2.131.50.1.3.18.30.6.1.3
		extremeWingCfgDevl2tpv3ManualSessionCookieSize OBJECT-TYPE
			SYNTAX DisplayString
			MAX-ACCESS read-write
			STATUS current
			DESCRIPTION
				"Cookie Size  0 or 4 or 8.
				
				XPath: /extremeWing-config/device[mac=key1]/l2tpv3_manual_session[name=key2]/cookie[endpoint=key3]/cookie_size"
			::= { extremeWingCfgDevl2tpv3ManualSessionCookieEntry 3 }

		
		-- 1.3.6.1.4.1.1916.2.131.50.1.3.18.30.6.1.4
		extremeWingCfgDevl2tpv3ManualSessionCookieVal1 OBJECT-TYPE
			SYNTAX DisplayString
			MAX-ACCESS read-write
			STATUS current
			DESCRIPTION
				"cookie value firstword.
				
				XPath: /extremeWing-config/device[mac=key1]/l2tpv3_manual_session[name=key2]/cookie[endpoint=key3]/cookie_val_1"
			::= { extremeWingCfgDevl2tpv3ManualSessionCookieEntry 4 }

		
		-- 1.3.6.1.4.1.1916.2.131.50.1.3.18.30.6.1.5
		extremeWingCfgDevl2tpv3ManualSessionCookieVal2 OBJECT-TYPE
			SYNTAX DisplayString
			MAX-ACCESS read-write
			STATUS current
			DESCRIPTION
				"cookie value secondword.
				
				XPath: /extremeWing-config/device[mac=key1]/l2tpv3_manual_session[name=key2]/cookie[endpoint=key3]/cookie_val_2"
			::= { extremeWingCfgDevl2tpv3ManualSessionCookieEntry 5 }

		
		-- 1.3.6.1.4.1.1916.2.131.50.1.3.18.31
		extremeWingCfgDevMcx OBJECT IDENTIFIER ::= { extremeWingCfgDev 31 }

		
		-- 1.3.6.1.4.1.1916.2.131.50.1.3.18.31.1
		extremeWingCfgDevMeshpointDevTable OBJECT-TYPE
			SYNTAX SEQUENCE OF ExtremeWingCfgDevMeshpointDevEntry
			MAX-ACCESS not-accessible
			STATUS current
			DESCRIPTION
				"
				
				/extremeWing-config/device/meshpoint_device"
			::= { extremeWingCfgDevMcx 1 }

		
		-- 1.3.6.1.4.1.1916.2.131.50.1.3.18.31.1.1
		extremeWingCfgDevMeshpointDevEntry OBJECT-TYPE
			SYNTAX ExtremeWingCfgDevMeshpointDevEntry
			MAX-ACCESS not-accessible
			STATUS current
			DESCRIPTION
				"An entry in the table."
			INDEX { extremeWingCfgDevMac, extremeWingCfgDevMeshpointDevName }
			::= { extremeWingCfgDevMeshpointDevTable 1 }

		
		ExtremeWingCfgDevMeshpointDevEntry ::=
			SEQUENCE { 
				extremeWingCfgDevMeshpointDevName
					ExtremeWingIdentifier,
				extremeWingCfgDevMeshpointDevIsRootDev
					DisplayString,
				extremeWingCfgDevMeshpointDevPreferredRoot
					DisplayString,
				extremeWingCfgDevMeshpointDevPreferredNeighbor
					MacAddress,
				extremeWingCfgDevMeshpointDevPreferredIf
					DisplayString,
				extremeWingCfgDevMeshpointDevMonitorCriticalResources
					TruthValue,
				extremeWingCfgDevMeshpointDevMonitorPriPortLink
					TruthValue,
				extremeWingCfgDevMeshpointDevPathMethod
					DisplayString,
				extremeWingCfgDevMeshpointDevHysteresisPeriod
					Unsigned32,
				extremeWingCfgDevMeshpointDevHysteresisSnrDelta
					Unsigned32,
				extremeWingCfgDevMeshpointDevHysteresisSnrMin
					Integer32,
				extremeWingCfgDevMeshpointDevExcludeWiredPeer
 					TruthValue,
				extremeWingCfgDevMeshpointDevHysteresisRootSelSnrDelta
					Unsigned32,
				extremeWingCfgDevMeshpointDevRootSelectMethod
					DisplayString,
				extremeWingCfgDevMeshpointDevRootSelectCostRoot
					TruthValue
			 }

		-- 1.3.6.1.4.1.1916.2.131.50.1.3.18.31.1.1.1
		extremeWingCfgDevMeshpointDevName OBJECT-TYPE
			SYNTAX ExtremeWingIdentifier
			MAX-ACCESS read-only
			STATUS current
			DESCRIPTION
				"
				
				XPath: /extremeWing-config/device[mac=key1]/meshpoint_device[name=key2]/name"
			::= { extremeWingCfgDevMeshpointDevEntry 1 }

		
		-- 1.3.6.1.4.1.1916.2.131.50.1.3.18.31.1.1.3
		extremeWingCfgDevMeshpointDevIsRootDev OBJECT-TYPE
			SYNTAX DisplayString
			MAX-ACCESS read-write
			STATUS current
			DESCRIPTION
				"Overrides whether the meshpoint is a root or not
				
				Values:
				none,
				true,
				false
				
				XPath: /extremeWing-config/device[mac=key1]/meshpoint_device[name=key2]/is_root_dev"
			DEFVAL { "none" }
			::= { extremeWingCfgDevMeshpointDevEntry 3 }

		
		-- 1.3.6.1.4.1.1916.2.131.50.1.3.18.31.1.1.4
		extremeWingCfgDevMeshpointDevPreferredRoot OBJECT-TYPE
			SYNTAX DisplayString
			MAX-ACCESS read-write
			STATUS current
			DESCRIPTION
				"Preferred root MAC address
				
				XPath: /extremeWing-config/device[mac=key1]/meshpoint_device[name=key2]/preferred_root"
			::= { extremeWingCfgDevMeshpointDevEntry 4 }

		
		-- 1.3.6.1.4.1.1916.2.131.50.1.3.18.31.1.1.5
		extremeWingCfgDevMeshpointDevPreferredNeighbor OBJECT-TYPE
			SYNTAX MacAddress
			MAX-ACCESS read-write
			STATUS current
			DESCRIPTION
				"Preferred neighbor MAC address
				
				XPath: /extremeWing-config/device[mac=key1]/meshpoint_device[name=key2]/preferred_neighbor"
			::= { extremeWingCfgDevMeshpointDevEntry 5 }

		
		-- 1.3.6.1.4.1.1916.2.131.50.1.3.18.31.1.1.6
		extremeWingCfgDevMeshpointDevPreferredIf OBJECT-TYPE
			SYNTAX DisplayString
			MAX-ACCESS read-write
			STATUS current
			DESCRIPTION
				"Preferred interface
				
				Values:
				none,
				2.4GHz,
				5GHz
				
				XPath: /extremeWing-config/device[mac=key1]/meshpoint_device[name=key2]/preferred_interface"
			DEFVAL { "none" }
			::= { extremeWingCfgDevMeshpointDevEntry 6 }

		-- 1.3.6.1.4.1.1916.2.131.50.1.3.18.31.1.1.7
		extremeWingCfgDevMeshpointDevMonitorCriticalResources OBJECT-TYPE
			SYNTAX TruthValue
			MAX-ACCESS read-write
			STATUS current
			DESCRIPTION
				"
				
				XPath: /extremeWing-config/device[mac=key1]/meshpoint_device[name=key2]/monitor_critical_resources"
			DEFVAL { false }
			::= { extremeWingCfgDevMeshpointDevEntry 7 }

		-- 1.3.6.1.4.1.1916.2.131.50.1.3.18.31.1.1.8
		extremeWingCfgDevMeshpointDevMonitorPriPortLink OBJECT-TYPE
			SYNTAX TruthValue
			MAX-ACCESS read-write
			STATUS current
			DESCRIPTION
				"
				
				XPath: /extremeWing-config/device[mac=key1]/meshpoint_device[name=key2]/monitor_pri_port_link"
			DEFVAL { false }
			::= { extremeWingCfgDevMeshpointDevEntry 8 }


		-- 1.3.6.1.4.1.1916.2.131.50.1.3.18.31.1.1.9
		extremeWingCfgDevMeshpointDevPathMethod OBJECT-TYPE
			SYNTAX DisplayString
			MAX-ACCESS read-write
			STATUS current
			DESCRIPTION
				"Path selection method for determining the root path
				none,
				uniform,
				mobile-snr-leaf,
				pcr-weighted,
				snr-leaf.
				XPath: /extremeWing-config/device[mac=key1]/meshpoint_device[name=key2]/path_method
				"
			DEFVAL { "none" }
			::= { extremeWingCfgDevMeshpointDevEntry 9 }

		
		-- 1.3.6.1.4.1.1916.2.131.50.1.3.18.31.1.1.10
		extremeWingCfgDevMeshpointDevHysteresisPeriod OBJECT-TYPE
			SYNTAX Unsigned32 (0..600)
			MAX-ACCESS read-write
			STATUS current
			DESCRIPTION
				"Path method hysteresis of candidate must be sustained for period of time
				XPath: /extremeWing-config/device[mac=key1]/meshpoint_device[name=key2]/hysteresis_period"
			DEFVAL { 1 }
			::= { extremeWingCfgDevMeshpointDevEntry 10 }


		-- 1.3.6.1.4.1.1916.2.131.50.1.3.18.31.1.1.11
		extremeWingCfgDevMeshpointDevHysteresisSnrDelta OBJECT-TYPE
			SYNTAX Unsigned32 (0..100)
			UNITS "db"
			MAX-ACCESS read-write
			STATUS current
			DESCRIPTION
				"Path method hysteresis SNR of candidate must have dB level better than current
				XPath: /extremeWing-config/device[mac=key1]/meshpoint_device[name=key2]/hysteresis_snr_delta
				"
			DEFVAL { 1 }
			::= { extremeWingCfgDevMeshpointDevEntry 11 }

		
		-- 1.3.6.1.4.1.1916.2.131.50.1.3.18.31.1.1.12
		extremeWingCfgDevMeshpointDevHysteresisSnrMin OBJECT-TYPE
			SYNTAX Integer32 (-100..0)
			UNITS "db"
			MAX-ACCESS read-write
			STATUS current
			DESCRIPTION
				"Path method hysteresis SNR of candidate must be above minimum threshold
				XPath: /extremeWing-config/device[mac=key1]/meshpoint_device[name=key2]/hysteresis_snr_min
				"
			DEFVAL { 0 }
			::= { extremeWingCfgDevMeshpointDevEntry 12 }

		
		-- 1.3.6.1.4.1.1916.2.131.50.1.3.18.31.1.1.13
		extremeWingCfgDevMeshpointDevExcludeWiredPeer OBJECT-TYPE
			SYNTAX TruthValue
			MAX-ACCESS read-write
			STATUS current
			DESCRIPTION
				"Excluded a mesh link from forming with a mesh device that is a wired peer
				XPath: /extremeWing-config/device[mac=key1]/meshpoint_device[name=key2]/exclude_wired_peer
				"
			DEFVAL { false }
			::= { extremeWingCfgDevMeshpointDevEntry 13 }


		-- 1.3.6.1.4.1.1916.2.131.50.1.3.18.31.1.1.14
		extremeWingCfgDevMeshpointDevHysteresisRootSelSnrDelta OBJECT-TYPE
			SYNTAX Unsigned32 (1..100)
			UNITS "dB"
			MAX-ACCESS read-write
			STATUS current
			DESCRIPTION
				"Root selection method hysteresis SNR delta range that a candidate must sustain
				
				XPATH: /extremeWing-config/device[mac=key1]/meshpoint_device[name=key2]/hysteresis_root_sel_snr_delta"
			DEFVAL { 1 }
			::= { extremeWingCfgDevMeshpointDevEntry 14 }


		-- 1.3.6.1.4.1.1916.2.131.50.1.3.18.31.1.1.15
		extremeWingCfgDevMeshpointDevRootSelectMethod OBJECT-TYPE
			SYNTAX DisplayString
			MAX-ACCESS read-write
			STATUS current
			DESCRIPTION
				"Root selection method for determining whether the meshpoint is a root or non-root
				
				none
				auto-mint
				
				XPATH: /extremeWing-config/device[mac=key1]/meshpoint_device[name=key2]/root_select_method"
			DEFVAL { "none" }
			::= { extremeWingCfgDevMeshpointDevEntry 15 }


		-- 1.3.6.1.4.1.1916.2.131.50.1.3.18.31.1.1.16
		extremeWingCfgDevMeshpointDevRootSelectCostRoot OBJECT-TYPE
			SYNTAX TruthValue
			MAX-ACCESS read-write
			STATUS current
			DESCRIPTION
				"Set as cost root for meshpoint root selection
				
				XPATH: /extremeWing-config/device[mac=key1]/meshpoint_device[name=key2]/root_select_cost_root"
			DEFVAL { false }
			::= { extremeWingCfgDevMeshpointDevEntry 16 }



-- /extremeWing-config/device/gre
                -- 1.3.6.1.4.1.1916.2.131.50.1.3.18.32
                extremeWingCfgDevGre OBJECT IDENTIFIER ::= { extremeWingCfgDev 32 }


-- /extremeWing-config/device/gre_tunnel
                -- 1.3.6.1.4.1.1916.2.131.50.1.3.18.32.1
                extremeWingCfgDevGreTunnelTable OBJECT-TYPE
                        SYNTAX SEQUENCE OF ExtremeWingCfgDevGreTunnelEntry
                        MAX-ACCESS not-accessible
                        STATUS current
                        DESCRIPTION
                                "/extremeWing-config/device/l2tpv3_tunnel"
                        ::= { extremeWingCfgDevGre 1 }


                -- 1.3.6.1.4.1.1916.2.131.50.1.3.18.32.1.1
                extremeWingCfgDevGreTunnelEntry OBJECT-TYPE
                        SYNTAX ExtremeWingCfgDevGreTunnelEntry
                        MAX-ACCESS not-accessible
                        STATUS current
                        DESCRIPTION
                                "An entry in the table."
                        INDEX { extremeWingCfgDevMac, extremeWingCfgDevGreTunnelName }
                        ::= { extremeWingCfgDevGreTunnelTable 1 }


                ExtremeWingCfgDevGreTunnelEntry ::=
                        SEQUENCE {
                                extremeWingCfgDevGreTunnelName
                                        ExtremeWingIdentifier,
                                extremeWingCfgGreTunnelVlan
                                        DisplayString,
                                extremeWingCfgDevGreNativeTag
                                        Integer32,
                                extremeWingCfgDevGreNativeVlan
                                        Integer32,
                                extremeWingCfgDevGreDscpOutPkt
                                        Integer32,
                                extremeWingCfgDevGreDscpInPkt
                                        Integer32,
                                extremeWingCfgDevGreFailoverPingIntv
                                        Integer32,
                                extremeWingCfgDevGreFailoverRetries
                                        Integer32
                         }

                -- 1.3.6.1.4.1.1916.2.131.50.1.3.18.32.1.1.1
                extremeWingCfgDevGreTunnelName OBJECT-TYPE
                        SYNTAX ExtremeWingIdentifier (SIZE (1..32))
                        MAX-ACCESS read-only
                        STATUS current
                        DESCRIPTION
                                "tunnel name.

                                XPath: /extremeWing-config/device[mac=key1]/gre_tunnel[name=key2]/name"
                        ::= { extremeWingCfgDevGreTunnelEntry 1 }


                -- 1.3.6.1.4.1.1916.2.131.50.1.3.18.32.1.1.4
                extremeWingCfgGreTunnelVlan OBJECT-TYPE
                        SYNTAX DisplayString
                        MAX-ACCESS read-write
                        STATUS current
                        DESCRIPTION
                                "VLAN extended over GRE tunnel.

                                XPath: /extremeWing-config/device[mac=key1]/gre_tunnel[name=key2]/tunneled_vlan"
                        ::= { extremeWingCfgDevGreTunnelEntry 4 }


                -- 1.3.6.1.4.1.1916.2.131.50.1.3.18.32.1.1.5
                extremeWingCfgDevGreNativeTag OBJECT-TYPE
                        SYNTAX Integer32
                        MAX-ACCESS read-write
                        STATUS current
                        DESCRIPTION
                                "Tag the native vlan.

                                XPath: /extremeWing-config/device[mac=key1]/gre_tunnel[name=key2]/native_tagged"
                        ::= { extremeWingCfgDevGreTunnelEntry 5 }


                -- 1.3.6.1.4.1.1916.2.131.50.1.3.18.32.1.1.6
                extremeWingCfgDevGreNativeVlan OBJECT-TYPE
                        SYNTAX Integer32 (1..4095)
                        MAX-ACCESS read-write
                        STATUS current
                        DESCRIPTION
                                "Native VLAN for classifying untagged traffic.

                                XPath: /extremeWing-config/device[mac=key1]/gre_tunnel[name=key2]/native_vlan"
                        ::= { extremeWingCfgDevGreTunnelEntry 6 }


                -- 1.3.6.1.4.1.1916.2.131.50.1.3.18.32.1.1.7
                extremeWingCfgDevGreDscpOutPkt OBJECT-TYPE
                        SYNTAX Integer32 (0..63)
                        MAX-ACCESS read-write
                        STATUS current
                        DESCRIPTION
                                "DSCP to set for outer packet
                                XPath: /extremeWing-config/device[mac=key1]/gre_tunnel[name=key2]/dscp/code_point"
                        ::= { extremeWingCfgDevGreTunnelEntry 7 }


                -- 1.3.6.1.4.1.1916.2.131.50.1.3.18.32.1.1.8
                extremeWingCfgDevGreDscpInPkt OBJECT-TYPE
                        SYNTAX Integer32
                        MAX-ACCESS read-write
                        STATUS current
                        DESCRIPTION
                                "Copy DSCP value from inner packet
                                XPath: /extremeWing-config/device[mac=key1]/gre_tunnel[name=key2]/dscp/reflect"
                        ::= { extremeWingCfgDevGreTunnelEntry 8 }


                -- 1.3.6.1.4.1.1916.2.131.50.1.3.18.32.1.1.9
                extremeWingCfgDevGreFailoverPingIntv OBJECT-TYPE
                        SYNTAX Integer32 (0..86400)
                        MAX-ACCESS read-write
                        STATUS current
                        DESCRIPTION
                                "ping interval in seconds

                                XPath: /extremeWing-config/device[mac=key1]/gre_tunnel[name=key2]/failover/interval"
                        ::= { extremeWingCfgDevGreTunnelEntry 9 }


                -- 1.3.6.1.4.1.1916.2.131.50.1.3.18.32.1.1.10
                extremeWingCfgDevGreFailoverRetries OBJECT-TYPE
                        SYNTAX Integer32 (0..63)
                        MAX-ACCESS read-write
                        STATUS current
                        DESCRIPTION
                                "Number of retrys in case no ping response received

                                XPath: /extremeWing-config/device[mac=key1]/gre_tunnel[name=key2]/failover/retry"
                        ::= { extremeWingCfgDevGreTunnelEntry 10 }


-- /extremeWing-config/device/l2tpv3_tunnel/peer
                -- 1.3.6.1.4.1.1916.2.131.50.1.3.18.32.2
                extremeWingCfgDevGreTunnelPeerTable OBJECT-TYPE
                        SYNTAX SEQUENCE OF ExtremeWingCfgDevGreTunnelPeerEntry
                        MAX-ACCESS not-accessible
                        STATUS current
                        DESCRIPTION
                                "/extremeWing-config/device/gre_tunnel/peer_ip"
                        ::= { extremeWingCfgDevGre 2 }


                -- 1.3.6.1.4.1.1916.2.131.50.1.3.18.32.2.1
                extremeWingCfgDevGreTunnelPeerEntry OBJECT-TYPE
                        SYNTAX ExtremeWingCfgDevGreTunnelPeerEntry
                        MAX-ACCESS not-accessible
                        STATUS current
                        DESCRIPTION
                                "An entry in the table."
                        INDEX { extremeWingCfgDevMac, extremeWingCfgDevGreTunnelName, extremeWingCfgDevGreTunnelPeerId }
                        ::= { extremeWingCfgDevGreTunnelPeerTable 1 }


                ExtremeWingCfgDevGreTunnelPeerEntry ::=
                        SEQUENCE {
                                extremeWingCfgDevGreTunnelPeerId
                                        INTEGER,
                                extremeWingCfgDevGreTunnelPeerIp
                                        DisplayString
                         }

                -- 1.3.6.1.4.1.1916.2.131.50.1.3.18.32.2.1.1
                extremeWingCfgDevGreTunnelPeerId OBJECT-TYPE
                        SYNTAX INTEGER
                                {
                                primary(1),
                                secondary(2)
                                }
                        MAX-ACCESS read-only
                        STATUS current
                        DESCRIPTION
                                "Primary peer to establish the tunnel and secondary peer for failover.

                                XPath: /extremeWing-config/device[mac=key1]/gre_tunnel[name=key2]/peer_ip[peer_idx=key3]/peer_idx"
                        ::= { extremeWingCfgDevGreTunnelPeerEntry 1 }


                -- 1.3.6.1.4.1.1916.2.131.50.1.3.18.32.2.1.3
                extremeWingCfgDevGreTunnelPeerIp OBJECT-TYPE
                        SYNTAX DisplayString
                        MAX-ACCESS read-write
                        STATUS current
                        DESCRIPTION
                                "IP address of peer.

                                XPath: /extremeWing-config/device[mac=key1]/gre_tunnel[name=key2]/peer_ip[peer_idx=key3]/ip"
                        ::= { extremeWingCfgDevGreTunnelPeerEntry 3 }


-- extremeWing-config/device/environmental_sensor
                -- 1.3.6.1.4.1.1916.2.131.50.1.3.18.33
                extremeWingCfgDevSensor OBJECT IDENTIFIER ::= { extremeWingCfgDev 33 }


-- /extremeWing-config/device/envirvironmental_sensor
                -- 1.3.6.1.4.1.1916.2.131.50.1.3.18.33.1
                extremeWingCfgDevEnvSensorTable OBJECT-TYPE
                        SYNTAX SEQUENCE OF ExtremeWingCfgDevEnvSensorEntry
                        MAX-ACCESS not-accessible
                        STATUS current
                        DESCRIPTION
                                "Description."
                        ::= { extremeWingCfgDevSensor 1 }


                -- 1.3.6.1.4.1.1916.2.131.50.1.3.18.33.1.1
                extremeWingCfgDevEnvSensorEntry OBJECT-TYPE
                        SYNTAX ExtremeWingCfgDevEnvSensorEntry
                        MAX-ACCESS not-accessible
                        STATUS current
                        DESCRIPTION
                                "An entry in the table."
                        INDEX { extremeWingCfgDevMac }
                        ::= { extremeWingCfgDevEnvSensorTable 1 }


                ExtremeWingCfgDevEnvSensorEntry ::=
                        SEQUENCE {
                                extremeWingCfgDevEnvSensorHumidity
                                        TruthValue,
                                extremeWingCfgDevEnvSensorMotion
                                        TruthValue,
                                extremeWingCfgDevEnvSensorTemperature
                                        TruthValue
                         }

                -- 1.3.6.1.4.1.1916.2.131.50.1.3.18.33.1.1.1
                extremeWingCfgDevEnvSensorHumidity OBJECT-TYPE
                        SYNTAX TruthValue
                        MAX-ACCESS read-write
                        STATUS current
                        DESCRIPTION
                                "Enable (turn on) the humidity sensor.

                                XPath: /extremeWing-config/device[mac=key1]/environmental_sensor/humidity"
                        DEFVAL { true }
                        ::= { extremeWingCfgDevEnvSensorEntry 1 }


                -- 1.3.6.1.4.1.1916.2.131.50.1.3.18.33.1.1.2
                extremeWingCfgDevEnvSensorMotion OBJECT-TYPE
                        SYNTAX TruthValue
                        MAX-ACCESS read-write
                        STATUS current
                        DESCRIPTION
                                "Enable (turn on) the motion sensor.

                                XPath: /extremeWing-config/device[mac=key1]/environmental_sensor/motion"
                        DEFVAL { true }
                        ::= { extremeWingCfgDevEnvSensorEntry 2 }


                -- 1.3.6.1.4.1.1916.2.131.50.1.3.18.33.1.1.3
                extremeWingCfgDevEnvSensorTemperature OBJECT-TYPE
                        SYNTAX TruthValue
                        MAX-ACCESS read-write
                        STATUS current
                        DESCRIPTION
                                "Enable (turn on) the temperature sensor.

                                XPath: /extremeWing-config/device[mac=key1]/environmental_sensor/temperature"
                        DEFVAL { true }
                        ::= { extremeWingCfgDevEnvSensorEntry 3 }


-- /extremeWing-config/profile/environmental_sensor
                -- 1.3.6.1.4.1.1916.2.131.50.1.3.18.33.2
                extremeWingCfgDevLightSensorTable OBJECT-TYPE
                        SYNTAX SEQUENCE OF ExtremeWingCfgDevLightSensorEntry
                        MAX-ACCESS not-accessible
                        STATUS current
                        DESCRIPTION
                                "Description."
                        ::= { extremeWingCfgDevSensor 2 }


                -- 1.3.6.1.4.1.1916.2.131.50.1.3.18.33.2.1
                extremeWingCfgDevLightSensorEntry OBJECT-TYPE
                        SYNTAX ExtremeWingCfgDevLightSensorEntry
                        MAX-ACCESS not-accessible
                        STATUS current
                        DESCRIPTION
                                "An entry in the table."
                        INDEX { extremeWingCfgDevMac }
                        ::= { extremeWingCfgDevLightSensorTable 1 }


                ExtremeWingCfgDevLightSensorEntry ::=
                        SEQUENCE {
                                extremeWingCfgDevLightSensor
                                        TruthValue,
                                extremeWingCfgDevLightSensorHoldTime
                                        Integer32,
                                extremeWingCfgDevLightSensorThresholdRadioShutdown
                                        DisplayString,
                                extremeWingCfgDevLightSensorLowLimitThreshold
                                        Integer32,
                                extremeWingCfgDevLightSensorHighLimitThreshold
                                        Integer32
                         }

                -- 1.3.6.1.4.1.1916.2.131.50.1.3.18.33.2.1.1
                extremeWingCfgDevLightSensor OBJECT-TYPE
                        SYNTAX TruthValue
                        UNITS "true"
                        MAX-ACCESS read-write
                        STATUS current
                        DESCRIPTION
                                "Enable (turn on) the light sensor..

                                XPath: /extremeWing-config/device[mac=key1]/environmental_sensor/light"
                        ::= { extremeWingCfgDevLightSensorEntry 1 }


                -- 1.3.6.1.4.1.1916.2.131.50.1.3.18.33.2.1.2
                extremeWingCfgDevLightSensorHoldTime OBJECT-TYPE
                        SYNTAX Integer32 (2..201)
                        UNITS "seconds"
                        MAX-ACCESS read-write
                        STATUS current
                        DESCRIPTION
                                "The interval of time (in seconds) during which the light sensor polls the environment for light intensity to determine whehter the light is on or off.

                                XPath: /extremeWing-config/device[mac=key1]/environmental_sensor/light_holdtime"
                        ::= { extremeWingCfgDevLightSensorEntry 2 }


                -- 1.3.6.1.4.1.1916.2.131.50.1.3.18.33.2.1.3
                extremeWingCfgDevLightSensorThresholdRadioShutdown OBJECT-TYPE
                        SYNTAX DisplayString
                        MAX-ACCESS read-write
                        STATUS current
                        DESCRIPTION
                                "Shutdown the AP radio(s) when the light intensity drops below the lower limit -- signifying that the light is off and the facility is unoccupied..

                                enum all,
                                enum radio-1,
                                enum radio-2


                                XPath: /extremeWing-config/device[mac=key1]/environmental_sensor/light_radio_shutdown"
                        DEFVAL { "none" }
                        ::= { extremeWingCfgDevLightSensorEntry 3 }


                -- 1.3.6.1.4.1.1916.2.131.50.1.3.18.33.2.1.4
                extremeWingCfgDevLightSensorLowLimitThreshold OBJECT-TYPE
                        SYNTAX Integer32 (0..1000)
                        UNITS "lux"
                        MAX-ACCESS read-write
                        STATUS current
                        DESCRIPTION
                                "The lower limit (in lux) at which the light sensor determines the lighting is off.


                                XPath: /extremeWing-config/device[mac=key1]/environmental_sensor/light_threshold_low"
                        ::= { extremeWingCfgDevLightSensorEntry 4 }


                -- 1.3.6.1.4.1.1916.2.131.50.1.3.18.33.2.1.5
                extremeWingCfgDevLightSensorHighLimitThreshold OBJECT-TYPE
                        SYNTAX Integer32 (100..10000)
                        UNITS "lux"
                        MAX-ACCESS read-write
                        STATUS current
                        DESCRIPTION
                                "The upper limit (in lux) at which the light sensor determines the lighting is on.

                                XPath: /extremeWing-config/device[mac=key1]/environmental_sensor/light_threshold_high"
                        ::= { extremeWingCfgDevLightSensorEntry 5 }


-- /extremeWing-config/profile/environmental_sensor
                -- 1.3.6.1.4.1.1916.2.131.50.1.3.18.33.3
                extremeWingCfgDevSharedSensorConfTable OBJECT-TYPE
                        SYNTAX SEQUENCE OF ExtremeWingCfgDevSharedSensorConfEntry
                        MAX-ACCESS not-accessible
                        STATUS current
                        DESCRIPTION
                                "Description."
                        ::= { extremeWingCfgDevSensor 3 }


                -- 1.3.6.1.4.1.1916.2.131.50.1.3.18.33.3.1
                extremeWingCfgDevSharedSensorConfEntry OBJECT-TYPE
                        SYNTAX ExtremeWingCfgDevSharedSensorConfEntry
                        MAX-ACCESS not-accessible
                        STATUS current
                        DESCRIPTION
                                "An entry in the table."
                        INDEX { extremeWingCfgDevMac }
                        ::= { extremeWingCfgDevSharedSensorConfTable 1 }


                ExtremeWingCfgDevSharedSensorConfEntry ::=
                        SEQUENCE {
                                extremeWingCfgDevSharedSensorPollingInterval
                                        Integer32
                         }

                -- 1.3.6.1.4.1.1916.2.131.50.1.3.18.33.3.1.1
                extremeWingCfgDevSharedSensorPollingInterval OBJECT-TYPE
                        SYNTAX Integer32 (1..100)
                        UNITS "seconds"
                        MAX-ACCESS read-write
                        STATUS current
                        DESCRIPTION
                                "The upper limit (in lux) at which the light sensor determines the lighting is on.

                                XPath: /extremeWing-config/device[mac=key1]/environmental_sensor/polling_interval"
                        ::= { extremeWingCfgDevSharedSensorConfEntry 1 }


-- /extremeWing-config/management_policy
		-- 1.3.6.1.4.1.1916.2.131.50.1.3.19
		extremeWingCfgMgmt OBJECT IDENTIFIER ::= { extremeWingConfig 19 }

		
		-- 1.3.6.1.4.1.1916.2.131.50.1.3.19.1
		extremeWingCfgMgmtTable OBJECT-TYPE
			SYNTAX SEQUENCE OF ExtremeWingCfgMgmtEntry
			MAX-ACCESS not-accessible
			STATUS current
			DESCRIPTION
				"
				
				/extremeWing-config/management_policy"
			::= { extremeWingCfgMgmt 1 }

		
		-- 1.3.6.1.4.1.1916.2.131.50.1.3.19.1.1
		extremeWingCfgMgmtEntry OBJECT-TYPE
			SYNTAX ExtremeWingCfgMgmtEntry
			MAX-ACCESS not-accessible
			STATUS current
			DESCRIPTION
				"An entry in the table."
			INDEX { extremeWingCfgMgmtName }
			::= { extremeWingCfgMgmtTable 1 }

		
		ExtremeWingCfgMgmtEntry ::=
			SEQUENCE { 
				extremeWingCfgMgmtName
					ExtremeWingIdentifier,
				extremeWingCfgMgmtTelnetEnable
					TruthValue,
				extremeWingCfgMgmtTelnetPort
					Unsigned32,
				extremeWingCfgMgmtHttpEnable
					TruthValue,
				extremeWingCfgMgmtHttpsEnable
					TruthValue,
				extremeWingCfgMgmtSshEnable
					TruthValue,
				extremeWingCfgMgmtSshPort
					Unsigned32,
				extremeWingCfgMgmtBannerMotd
					DisplayString
			 }

		-- 1.3.6.1.4.1.1916.2.131.50.1.3.19.1.1.1
		extremeWingCfgMgmtName OBJECT-TYPE
			SYNTAX ExtremeWingIdentifier
			MAX-ACCESS read-only
			STATUS current
			DESCRIPTION
				"
				
				XPath: /extremeWing-config/management_policy[name=key1]/name"
			::= { extremeWingCfgMgmtEntry 1 }

		
		-- 1.3.6.1.4.1.1916.2.131.50.1.3.19.1.1.3
		extremeWingCfgMgmtTelnetEnable OBJECT-TYPE
			SYNTAX TruthValue
			MAX-ACCESS read-write
			STATUS current
			DESCRIPTION
				"
				
				XPath: /extremeWing-config/management_policy[name=key1]/telnet/enable"
			DEFVAL { false }
			::= { extremeWingCfgMgmtEntry 3 }

		
		-- 1.3.6.1.4.1.1916.2.131.50.1.3.19.1.1.4
		extremeWingCfgMgmtTelnetPort OBJECT-TYPE
			SYNTAX Unsigned32 (1..65535)
			MAX-ACCESS read-write
			STATUS current
			DESCRIPTION
				"
				
				XPath: /extremeWing-config/management_policy[name=key1]/telnet/port"
			DEFVAL { 23 }
			::= { extremeWingCfgMgmtEntry 4 }

		
		-- 1.3.6.1.4.1.1916.2.131.50.1.3.19.1.1.5
		extremeWingCfgMgmtHttpEnable OBJECT-TYPE
			SYNTAX TruthValue
			MAX-ACCESS read-write
			STATUS current
			DESCRIPTION
				"
				
				XPath: /extremeWing-config/management_policy[name=key1]/http/enable"
			DEFVAL { true }
			::= { extremeWingCfgMgmtEntry 5 }

		
		-- 1.3.6.1.4.1.1916.2.131.50.1.3.19.1.1.6
		extremeWingCfgMgmtHttpsEnable OBJECT-TYPE
			SYNTAX TruthValue
			MAX-ACCESS read-write
			STATUS current
			DESCRIPTION
				"
				
				XPath: /extremeWing-config/management_policy[name=key1]/https"
			DEFVAL { false }
			::= { extremeWingCfgMgmtEntry 6 }

		
		-- 1.3.6.1.4.1.1916.2.131.50.1.3.19.1.1.7
		extremeWingCfgMgmtSshEnable OBJECT-TYPE
			SYNTAX TruthValue
			MAX-ACCESS read-write
			STATUS current
			DESCRIPTION
				"
				
				XPath: /extremeWing-config/management_policy[name=key1]/ssh/enable"
			DEFVAL { false }
			::= { extremeWingCfgMgmtEntry 7 }

		
		-- 1.3.6.1.4.1.1916.2.131.50.1.3.19.1.1.8
		extremeWingCfgMgmtSshPort OBJECT-TYPE
			SYNTAX Unsigned32 (1..65535)
			MAX-ACCESS read-write
			STATUS current
			DESCRIPTION
				"
				
				XPath: /extremeWing-config/management_policy[name=key1]/ssh/port"
			DEFVAL { 22 }
			::= { extremeWingCfgMgmtEntry 8 }

		
		-- 1.3.6.1.4.1.1916.2.131.50.1.3.19.1.1.9
		extremeWingCfgMgmtBannerMotd OBJECT-TYPE
			SYNTAX DisplayString (SIZE (0..128))
			MAX-ACCESS read-write
			STATUS current
			DESCRIPTION
				"A message-of-the-day banner displayed to the user on logging into the system over the CLI
				
				XPath: /extremeWing-config/management_policy[name=key1]/banner_motd"
			DEFVAL { "" }
			::= { extremeWingCfgMgmtEntry 9 }

		
-- /extremeWing-config/management_policy/snmp
		-- 1.3.6.1.4.1.1916.2.131.50.1.3.19.2
		extremeWingCfgMgmtSnmp OBJECT IDENTIFIER ::= { extremeWingCfgMgmt 2 }

		
		-- 1.3.6.1.4.1.1916.2.131.50.1.3.19.2.1
		extremeWingCfgMgmtSnmpTable OBJECT-TYPE
			SYNTAX SEQUENCE OF ExtremeWingCfgMgmtSnmpEntry
			MAX-ACCESS not-accessible
			STATUS current
			DESCRIPTION
				"
				
				/extremeWing-config/management_policy/snmp"
			::= { extremeWingCfgMgmtSnmp 1 }

		
		-- 1.3.6.1.4.1.1916.2.131.50.1.3.19.2.1.1
		extremeWingCfgMgmtSnmpEntry OBJECT-TYPE
			SYNTAX ExtremeWingCfgMgmtSnmpEntry
			MAX-ACCESS not-accessible
			STATUS current
			DESCRIPTION
				"An entry in the table."
			INDEX { extremeWingCfgMgmtName }
			::= { extremeWingCfgMgmtSnmpTable 1 }

		
		ExtremeWingCfgMgmtSnmpEntry ::=
			SEQUENCE { 
				extremeWingCfgMgmtSnmpV1Enable
					TruthValue,
				extremeWingCfgMgmtSnmpV2Enable
					TruthValue,
				extremeWingCfgMgmtSnmpV3Enable
					TruthValue,
				extremeWingCfgMgmtSnmpTrapEnable
					TruthValue
			 }

		-- 1.3.6.1.4.1.1916.2.131.50.1.3.19.2.1.1.1
		extremeWingCfgMgmtSnmpV1Enable OBJECT-TYPE
			SYNTAX TruthValue
			MAX-ACCESS read-only
			STATUS current
			DESCRIPTION
				"Enable SNMP version v1
				
				XPath: /extremeWing-config/management_policy[name=key1]/snmp/snmpv1"
			DEFVAL { true }
			::= { extremeWingCfgMgmtSnmpEntry 1 }

		-- 1.3.6.1.4.1.1916.2.131.50.1.3.19.2.1.1.2
		extremeWingCfgMgmtSnmpV2Enable OBJECT-TYPE
			SYNTAX TruthValue
			MAX-ACCESS read-only
			STATUS current
			DESCRIPTION
				"Enable SNMP version v2
				
				XPath: /extremeWing-config/management_policy[name=key1]/snmp/snmpv2"
			DEFVAL { true }
			::= { extremeWingCfgMgmtSnmpEntry 2 }

		
		-- 1.3.6.1.4.1.1916.2.131.50.1.3.19.2.1.1.3
		extremeWingCfgMgmtSnmpV3Enable OBJECT-TYPE
			SYNTAX TruthValue
			MAX-ACCESS read-only
			STATUS current
			DESCRIPTION
				"Enable SNMP version v3
				
				XPath: /extremeWing-config/management_policy[name=key1]/snmp/snmpv3"
			DEFVAL { true }
			::= { extremeWingCfgMgmtSnmpEntry 3 }

		
		-- 1.3.6.1.4.1.1916.2.131.50.1.3.19.2.1.1.4
		extremeWingCfgMgmtSnmpTrapEnable OBJECT-TYPE
			SYNTAX TruthValue
			MAX-ACCESS read-only
			STATUS current
			DESCRIPTION
				"Enable trap generation
				
				XPath: /extremeWing-config/management_policy[name=key1]/snmp/trap/enable_traps"
			DEFVAL { false }
			::= { extremeWingCfgMgmtSnmpEntry 4 }

		
		-- 1.3.6.1.4.1.1916.2.131.50.1.3.19.2.2
		extremeWingCfgMgmtSnmpCommunityTable OBJECT-TYPE
			SYNTAX SEQUENCE OF ExtremeWingCfgMgmtSnmpCommunityEntry
			MAX-ACCESS not-accessible
			STATUS current
			DESCRIPTION
				"
				
				/extremeWing-config/management_policy/snmp/community_string"
			::= { extremeWingCfgMgmtSnmp 2 }

		
		-- 1.3.6.1.4.1.1916.2.131.50.1.3.19.2.2.1
		extremeWingCfgMgmtSnmpCommunityEntry OBJECT-TYPE
			SYNTAX ExtremeWingCfgMgmtSnmpCommunityEntry
			MAX-ACCESS not-accessible
			STATUS current
			DESCRIPTION
				"An entry in the table."
			INDEX { extremeWingCfgMgmtName, extremeWingCfgMgmtSnmpCommunityName }
			::= { extremeWingCfgMgmtSnmpCommunityTable 1 }

		
		ExtremeWingCfgMgmtSnmpCommunityEntry ::=
			SEQUENCE { 
				extremeWingCfgMgmtSnmpCommunityName
					ExtremeWingIdentifier,
				extremeWingCfgMgmtSnmpCommunityAccess
					DisplayString
			 }

		-- 1.3.6.1.4.1.1916.2.131.50.1.3.19.2.2.1.1
		extremeWingCfgMgmtSnmpCommunityName OBJECT-TYPE
			SYNTAX ExtremeWingIdentifier
			MAX-ACCESS read-only
			STATUS current
			DESCRIPTION
				"SNMP community string
				
				XPath: /extremeWing-config/management_policy[name=key1]/snmp/community_string[name=key2]/name"
			::= { extremeWingCfgMgmtSnmpCommunityEntry 1 }

		
		-- 1.3.6.1.4.1.1916.2.131.50.1.3.19.2.2.1.3
		extremeWingCfgMgmtSnmpCommunityAccess OBJECT-TYPE
			SYNTAX DisplayString
			MAX-ACCESS read-write
			STATUS current
			DESCRIPTION
				"Access privilege with this community string
				
				Values:
				ro
				rw
				
				XPath: /extremeWing-config/management_policy[name=key1]/snmp/community_string[name=key2]/access"
			DEFVAL { "ro" }
			::= { extremeWingCfgMgmtSnmpCommunityEntry 3 }

		
		-- 1.3.6.1.4.1.1916.2.131.50.1.3.19.2.3
		extremeWingCfgMgmtSnmpUsmUserTable OBJECT-TYPE
			SYNTAX SEQUENCE OF ExtremeWingCfgMgmtSnmpUsmUserEntry
			MAX-ACCESS not-accessible
			STATUS current
			DESCRIPTION
				"
				
				/extremeWing-config/management_policy/snmp/usm"
			::= { extremeWingCfgMgmtSnmp 3 }

		
		-- 1.3.6.1.4.1.1916.2.131.50.1.3.19.2.3.1
		extremeWingCfgMgmtSnmpUsmUserEntry OBJECT-TYPE
			SYNTAX ExtremeWingCfgMgmtSnmpUsmUserEntry
			MAX-ACCESS not-accessible
			STATUS current
			DESCRIPTION
				"An entry in the table."
			INDEX { extremeWingCfgMgmtName, extremeWingCfgMgmtSnmpUsmUserName }
			::= { extremeWingCfgMgmtSnmpUsmUserTable 1 }

		
		ExtremeWingCfgMgmtSnmpUsmUserEntry ::=
			SEQUENCE { 
				extremeWingCfgMgmtSnmpUsmUserName
					ExtremeWingIdentifier,
				extremeWingCfgMgmtSnmpUsmUserAuthentication
					DisplayString,
				extremeWingCfgMgmtSnmpUsmUserEncryption
					DisplayString,
				extremeWingCfgMgmtSnmpUsmUserPassword
					DisplayString
			 }

		-- 1.3.6.1.4.1.1916.2.131.50.1.3.19.2.3.1.1
		extremeWingCfgMgmtSnmpUsmUserName OBJECT-TYPE
			SYNTAX ExtremeWingIdentifier
			MAX-ACCESS read-only
			STATUS current
			DESCRIPTION
				"SNMPv3 security user name
				
				Values:
				snmpmanager
				snmpoperator
				snmptrap
				
				XPath: /extremeWing-config/management_policy[name=key1]/snmp/usm[user_name=key2]/user_name"
			::= { extremeWingCfgMgmtSnmpUsmUserEntry 1 }

		
		-- 1.3.6.1.4.1.1916.2.131.50.1.3.19.2.3.1.3
		extremeWingCfgMgmtSnmpUsmUserAuthentication OBJECT-TYPE
			SYNTAX DisplayString
			MAX-ACCESS read-write
			STATUS current
			DESCRIPTION
				"Authentication protocol. The default is HMAC-MD5.
				
				Values:
				md5
				
				XPath: /extremeWing-config/management_policy[name=key1]/snmp/usm[user_name=key2]/authentication"
			DEFVAL { "md5" }
			::= { extremeWingCfgMgmtSnmpUsmUserEntry 3 }

		
		-- 1.3.6.1.4.1.1916.2.131.50.1.3.19.2.3.1.4
		extremeWingCfgMgmtSnmpUsmUserEncryption OBJECT-TYPE
			SYNTAX DisplayString
			MAX-ACCESS read-write
			STATUS current
			DESCRIPTION
				"Privacy protocol. The default is CBC-DES.
				
				Values:
				des
				
				XPath: /extremeWing-config/management_policy[name=key1]/snmp/usm[user_name=key2]/encryption"
			DEFVAL { "des" }
			::= { extremeWingCfgMgmtSnmpUsmUserEntry 4 }

		
		-- 1.3.6.1.4.1.1916.2.131.50.1.3.19.2.3.1.5
		extremeWingCfgMgmtSnmpUsmUserPassword OBJECT-TYPE
			SYNTAX DisplayString (SIZE (8..64))
			MAX-ACCESS read-write
			STATUS current
			DESCRIPTION
				"Password for authentication and privacy protocols
				
				XPath: /extremeWing-config/management_policy[name=key1]/snmp/usm[user_name=key2]/password"
			::= { extremeWingCfgMgmtSnmpUsmUserEntry 5 }

		
		-- 1.3.6.1.4.1.1916.2.131.50.1.3.19.5
		extremeWingCfgMgmtAdminTable OBJECT-TYPE
			SYNTAX SEQUENCE OF ExtremeWingCfgMgmtAdminEntry
			MAX-ACCESS not-accessible
			STATUS current
			DESCRIPTION
				"
				
				/extremeWing-config/management_policy/admin"
			::= { extremeWingCfgMgmt 5 }

		
		-- 1.3.6.1.4.1.1916.2.131.50.1.3.19.5.1
		extremeWingCfgMgmtAdminEntry OBJECT-TYPE
			SYNTAX ExtremeWingCfgMgmtAdminEntry
			MAX-ACCESS not-accessible
			STATUS current
			DESCRIPTION
				"An entry in the table."
			INDEX { extremeWingCfgMgmtName, extremeWingCfgMgmtAdminUsername }
			::= { extremeWingCfgMgmtAdminTable 1 }

		
		ExtremeWingCfgMgmtAdminEntry ::=
			SEQUENCE { 
				extremeWingCfgMgmtAdminUsername
					ExtremeWingIdentifier,
				extremeWingCfgMgmtAdminPassword
					DisplayString,
				extremeWingCfgMgmtAdminRole
					DisplayString
			 }

		-- 1.3.6.1.4.1.1916.2.131.50.1.3.19.5.1.1
		extremeWingCfgMgmtAdminUsername OBJECT-TYPE
			SYNTAX ExtremeWingIdentifier
			MAX-ACCESS read-only
			STATUS current
			DESCRIPTION
				"
				
				XPath: /extremeWing-config/management_policy[name=key1]/admin[username=key2]/username"
			::= { extremeWingCfgMgmtAdminEntry 1 }

		
		-- 1.3.6.1.4.1.1916.2.131.50.1.3.19.5.1.3
		extremeWingCfgMgmtAdminPassword OBJECT-TYPE
			SYNTAX DisplayString (SIZE (1..63))
			MAX-ACCESS read-write
			STATUS current
			DESCRIPTION
				"
				
				XPath: /extremeWing-config/management_policy[name=key1]/admin[username=key2]/password"
			::= { extremeWingCfgMgmtAdminEntry 3 }

		
		-- 1.3.6.1.4.1.1916.2.131.50.1.3.19.5.1.4
		extremeWingCfgMgmtAdminRole OBJECT-TYPE
			SYNTAX DisplayString
			MAX-ACCESS read-write
			STATUS current
			DESCRIPTION
				"
				
				Values:
				system-admin
				network-admin
				security-admin
				monitor
				helpdesk
				web-user-admin
				
				XPath: /extremeWing-config/management_policy[name=key1]/admin[username=key2]/role"
			DEFVAL { "superuser" }
			::= { extremeWingCfgMgmtAdminEntry 4 }


		extremeWingCfgAutoProvision OBJECT IDENTIFIER ::= { extremeWingConfig 27 }
 
 		
		-- 1.3.6.1.4.1.1916.2.131.50.1.3.27.1
		extremeWingCfgAutoProvisionPolicyTable OBJECT-TYPE
			SYNTAX SEQUENCE OF ExtremeWingCfgAutoProvisionPolicyEntry
			MAX-ACCESS not-accessible
			STATUS current
			DESCRIPTION
				"Description."
			::= { extremeWingCfgAutoProvision 1 }

		
		-- 1.3.6.1.4.1.1916.2.131.50.1.3.27.1.1
		extremeWingCfgAutoProvisionPolicyEntry OBJECT-TYPE
			SYNTAX ExtremeWingCfgAutoProvisionPolicyEntry
			MAX-ACCESS not-accessible
			STATUS current
			DESCRIPTION
				"Description."
			INDEX { extremeWingCfgAutoProvisionPolicyName }
			::= { extremeWingCfgAutoProvisionPolicyTable 1 }

		
		ExtremeWingCfgAutoProvisionPolicyEntry ::=
			SEQUENCE { 
				extremeWingCfgAutoProvisionPolicyName
					ExtremeWingIdentifier,
				extremeWingCfgAutoProvisionPolicyDefaultAdoption
					TruthValue
			 }

		-- 1.3.6.1.4.1.1916.2.131.50.1.3.27.1.1.1
		extremeWingCfgAutoProvisionPolicyName OBJECT-TYPE
			SYNTAX ExtremeWingIdentifier
			MAX-ACCESS read-write
			STATUS current
			DESCRIPTION
				"XPATH: /extremeWing-config/auto_provisioning_policy[name=key1]/name"
			::= { extremeWingCfgAutoProvisionPolicyEntry 1 }

		
		-- 1.3.6.1.4.1.1916.2.131.50.1.3.27.1.1.3
		extremeWingCfgAutoProvisionPolicyDefaultAdoption OBJECT-TYPE
			SYNTAX TruthValue
			MAX-ACCESS read-write
			STATUS current
			DESCRIPTION
				"XPATH: /extremeWing-config/auto_provisioning_policy[name=key1]/default_adoption"
			DEFVAL { false }
			::= { extremeWingCfgAutoProvisionPolicyEntry 3 }

		
		-- 1.3.6.1.4.1.1916.2.131.50.1.3.27.2
		extremeWingCfgAutoProvisionPolicyRuleTable OBJECT-TYPE
			SYNTAX SEQUENCE OF ExtremeWingCfgAutoProvisionPolicyRuleEntry
			MAX-ACCESS not-accessible
			STATUS current
			DESCRIPTION
				"Description."
			::= { extremeWingCfgAutoProvision 2 }

		
		-- 1.3.6.1.4.1.1916.2.131.50.1.3.27.2.1
		extremeWingCfgAutoProvisionPolicyRuleEntry OBJECT-TYPE
			SYNTAX ExtremeWingCfgAutoProvisionPolicyRuleEntry
			MAX-ACCESS not-accessible
			STATUS current
			DESCRIPTION
				"Description."
			INDEX { extremeWingCfgAutoProvisionPolicyName, extremeWingCfgAutoProvisionPolicyRulePrecedence }
			::= { extremeWingCfgAutoProvisionPolicyRuleTable 1 }

		
		ExtremeWingCfgAutoProvisionPolicyRuleEntry ::=
			SEQUENCE { 
				extremeWingCfgAutoProvisionPolicyRulePrecedence
					Unsigned32,
				extremeWingCfgAutoProvisionPolicyRuleOperation
					DisplayString,
				extremeWingCfgAutoProvisionPolicyRuleDevice
					DisplayString,
				extremeWingCfgAutoProvisionPolicyRuleProfileName
					DisplayString,
				extremeWingCfgAutoProvisionPolicyRuleRfDomainName
					DisplayString,
				extremeWingCfgAutoProvisionPolicyRuleControllerName
					DisplayString,
				extremeWingCfgAutoProvisionPolicyRuleArea
					DisplayString,
				extremeWingCfgAutoProvisionPolicyRuleFloor
					DisplayString,
				extremeWingCfgAutoProvisionPolicyRuleType
					DisplayString
			 }

		-- 1.3.6.1.4.1.1916.2.131.50.1.3.27.2.1.1
		extremeWingCfgAutoProvisionPolicyRulePrecedence OBJECT-TYPE
			SYNTAX Unsigned32 (1..10000)
			MAX-ACCESS read-write
			STATUS current
			DESCRIPTION
				"The precedence number for the Provisioning Policy Entry.
				1 is the highest precedence rule and 10000 is the lowest precedence rule.
				XPATH: /extremeWing-config/auto_provisioning_policy[name=key1]/rule[precedence=key2]/precedence"
			::= { extremeWingCfgAutoProvisionPolicyRuleEntry 1 }

		
		-- 1.3.6.1.4.1.1916.2.131.50.1.3.27.2.1.3
		extremeWingCfgAutoProvisionPolicyRuleOperation OBJECT-TYPE
			SYNTAX DisplayString
			MAX-ACCESS read-write
			STATUS current
			DESCRIPTION
				"Action to be taken upon adoption request from AP 		
				allow
				deny
				redirect
				 XPATH: /extremeWing-config/auto_provisioning_policy[name=key1]/rule[precedence=key2]/operation"
			::= { extremeWingCfgAutoProvisionPolicyRuleEntry 3 }

		
		-- 1.3.6.1.4.1.1916.2.131.50.1.3.27.2.1.4
		extremeWingCfgAutoProvisionPolicyRuleDevice OBJECT-TYPE
			SYNTAX DisplayString
			MAX-ACCESS read-write
			STATUS current
			DESCRIPTION
				"The device type serviced by this rule
				
				WIOS_AP81XX
				WIOS_AP4700
				WIOS_AP4600
				WIOS_AP4021
				WIOS_AP4521
				WIOS_AP4511
				WIOS_AP4532
				WIOS_AP4022
				WIOS_AP4522
				WIOS_AP6562
				
				XPATH: /extremeWing-config/auto_provisioning_policy[name=key1]/rule[precedence=key2]/device"
			::= { extremeWingCfgAutoProvisionPolicyRuleEntry 4 }

		
		-- 1.3.6.1.4.1.1916.2.131.50.1.3.27.2.1.5
		extremeWingCfgAutoProvisionPolicyRuleProfileName OBJECT-TYPE
			SYNTAX DisplayString
			MAX-ACCESS read-write
			STATUS current
			DESCRIPTION
				"XPATH: /extremeWing-config/auto_provisioning_policy[name=key1]/rule[precedence=key2]/profile_name"
			::= { extremeWingCfgAutoProvisionPolicyRuleEntry 5 }

		
		-- 1.3.6.1.4.1.1916.2.131.50.1.3.27.2.1.6
		extremeWingCfgAutoProvisionPolicyRuleRfDomainName OBJECT-TYPE
			SYNTAX DisplayString
			MAX-ACCESS read-write
			STATUS current
			DESCRIPTION
				"XPATH: /extremeWing-config/auto_provisioning_policy[name=key1]/rule[precedence=key2]/rf_domain_name"
			::= { extremeWingCfgAutoProvisionPolicyRuleEntry 6 }

		
		-- 1.3.6.1.4.1.1916.2.131.50.1.3.27.2.1.7
		extremeWingCfgAutoProvisionPolicyRuleControllerName OBJECT-TYPE
			SYNTAX DisplayString
			MAX-ACCESS read-write
			STATUS current
			DESCRIPTION
				"
				XPATH: /extremeWing-config/auto_provisioning_policy[name=key1]/rule[precedence=key2]/controller_name"
			::= { extremeWingCfgAutoProvisionPolicyRuleEntry 7 }

		
		-- 1.3.6.1.4.1.1916.2.131.50.1.3.27.2.1.8
		extremeWingCfgAutoProvisionPolicyRuleArea OBJECT-TYPE
			SYNTAX DisplayString (SIZE (0..64))
			MAX-ACCESS read-write
			STATUS current
			DESCRIPTION
				"The area to be assigned for this policy
				
				XPATH: /extremeWing-config/auto_provisioning_policy[name=key1]/rule[precedence=key2]/area"
			DEFVAL { "" }
			::= { extremeWingCfgAutoProvisionPolicyRuleEntry 8 }

		
		-- 1.3.6.1.4.1.1916.2.131.50.1.3.27.2.1.9
		extremeWingCfgAutoProvisionPolicyRuleFloor OBJECT-TYPE
			SYNTAX DisplayString (SIZE (0..32))
			MAX-ACCESS read-write
			STATUS current
			DESCRIPTION
				"The floor name to be assigned to this policy
				
				XPATH: /extremeWing-config/auto_provisioning_policy[name=key1]/rule[precedence=key2]/floor"
			DEFVAL { "" }
			::= { extremeWingCfgAutoProvisionPolicyRuleEntry 9 }

		
		-- 1.3.6.1.4.1.1916.2.131.50.1.3.27.2.1.10
		extremeWingCfgAutoProvisionPolicyRuleType OBJECT-TYPE
			SYNTAX DisplayString
			MAX-ACCESS read-write
			STATUS current
			DESCRIPTION
				"mac
				ip
				vlan
				serial-number
				model-number
				dhcp-option
				fqdn
				cdp-match
				lldp-match
				any
				
				
				XPATH: /extremeWing-config/auto_provisioning_policy[name=key1]/rule[precedence=key2]/type"
			::= { extremeWingCfgAutoProvisionPolicyRuleEntry 10 }


		
-- /extremeWing-config/routing_policy
		-- 1.3.6.1.4.1.1916.2.131.50.1.3.31
		extremeWingCfgRoute OBJECT IDENTIFIER ::= { extremeWingConfig 31 }

		
		-- 1.3.6.1.4.1.1916.2.131.50.1.3.31.1
		extremeWingCfgRouteTable OBJECT-TYPE
			SYNTAX SEQUENCE OF ExtremeWingCfgRouteEntry
			MAX-ACCESS not-accessible
			STATUS current
			DESCRIPTION
				"
				
				/extremeWing-config/routing_policy"
			::= { extremeWingCfgRoute 1 }

		
		-- 1.3.6.1.4.1.1916.2.131.50.1.3.31.1.1
		extremeWingCfgRouteEntry OBJECT-TYPE
			SYNTAX ExtremeWingCfgRouteEntry
			MAX-ACCESS not-accessible
			STATUS current
			DESCRIPTION
				"An entry in the table."
			INDEX { extremeWingCfgRouteName }
			::= { extremeWingCfgRouteTable 1 }

		
		ExtremeWingCfgRouteEntry ::=
			SEQUENCE { 
				extremeWingCfgRouteName
					ExtremeWingIdentifier,
				extremeWingCfgRouteLogging
					TruthValue,
				extremeWingCfgRouteLocalPbr
					TruthValue,
				extremeWingCfgRouteUseCrm
					TruthValue
			 }

		-- 1.3.6.1.4.1.1916.2.131.50.1.3.31.1.1.1
		extremeWingCfgRouteName OBJECT-TYPE
			SYNTAX ExtremeWingIdentifier
			MAX-ACCESS read-only
			STATUS current
			DESCRIPTION
				"Name of the Route Map
				
				XPath: /extremeWing-config/routing_policy[name=key1]/name"
			::= { extremeWingCfgRouteEntry 1 }

		
		-- 1.3.6.1.4.1.1916.2.131.50.1.3.31.1.1.3
		extremeWingCfgRouteLogging OBJECT-TYPE
			SYNTAX TruthValue
			MAX-ACCESS read-write
			STATUS current
			DESCRIPTION
				"Enable / disable logging for this Route Map.
				
				XPath: /extremeWing-config/routing_policy[name=key1]/logging"
			DEFVAL { false }
			::= { extremeWingCfgRouteEntry 3 }

		
		-- 1.3.6.1.4.1.1916.2.131.50.1.3.31.1.1.4
		extremeWingCfgRouteLocalPbr OBJECT-TYPE
			SYNTAX TruthValue
			MAX-ACCESS read-write
			STATUS current
			DESCRIPTION
				"Enable/Disable Policy Based Routing for packets generated by the device.
				
				XPath: /extremeWing-config/routing_policy[name=key1]/local_pbr"
			DEFVAL { true }
			::= { extremeWingCfgRouteEntry 4 }

		
		-- 1.3.6.1.4.1.1916.2.131.50.1.3.31.1.1.5
		extremeWingCfgRouteUseCrm OBJECT-TYPE
			SYNTAX TruthValue
			MAX-ACCESS read-write
			STATUS current
			DESCRIPTION
				"Use Critical Resource Monitoring to monitor the status of a link. This will determine the state of next-hop in Route Map, via which Critical Resources are being monitored. Link monitoring is used for failover to a secondary next-hop
				
				XPath: /extremeWing-config/routing_policy[name=key1]/use_crm"
			DEFVAL { true }
			::= { extremeWingCfgRouteEntry 5 }

		
		-- 1.3.6.1.4.1.1916.2.131.50.1.3.31.2
		extremeWingCfgRouteMapTable OBJECT-TYPE
			SYNTAX SEQUENCE OF ExtremeWingCfgRouteMapEntry
			MAX-ACCESS not-accessible
			STATUS current
			DESCRIPTION
				"
				
				/extremeWing-config/routing_policy"
			::= { extremeWingCfgRoute 2 }

		
		-- 1.3.6.1.4.1.1916.2.131.50.1.3.31.2.1
		extremeWingCfgRouteMapEntry OBJECT-TYPE
			SYNTAX ExtremeWingCfgRouteMapEntry
			MAX-ACCESS not-accessible
			STATUS current
			DESCRIPTION
				"An entry in the table."
			INDEX { extremeWingCfgRouteName, extremeWingCfgRouteMapPrecedence }
			::= { extremeWingCfgRouteMapTable 1 }

		
		ExtremeWingCfgRouteMapEntry ::=
			SEQUENCE { 
				extremeWingCfgRouteMapPrecedence
					Unsigned32,
				extremeWingCfgRouteMapMatchClauseAcl
					ExtremeWingIdentifier,
				extremeWingCfgRouteMapMatchClauseDscp
					Unsigned32,
				extremeWingCfgRouteMapMatchClauseWlan
					ExtremeWingIdentifier,
				extremeWingCfgRouteMapRolePolicy
					ExtremeWingIdentifier,
				extremeWingCfgRouteMapUserRole
					ExtremeWingIdentifier,
				extremeWingCfgRouteMapMatchClauseIncomingInterface
					DisplayString,
				extremeWingCfgRouteMapNextHop1
					DisplayString,
				extremeWingCfgRouteMapNextHop2
					DisplayString,
				extremeWingCfgRouteMapSetClauseDefaultNextHop
					DisplayString,
				extremeWingCfgRouteMapSetClauseFallback
					TruthValue,
				extremeWingCfgRouteMapSetClauseMarkDscp
					Unsigned32
			 }

		-- 1.3.6.1.4.1.1916.2.131.50.1.3.31.2.1.1
		extremeWingCfgRouteMapPrecedence OBJECT-TYPE
			SYNTAX Unsigned32 (1..100)
			MAX-ACCESS read-only
			STATUS current
			DESCRIPTION
				"
				
				XPath: /extremeWing-config/routing_policy[name=key1]/route_map[precedence=key2]/precedence"
			::= { extremeWingCfgRouteMapEntry 1 }

		
		-- 1.3.6.1.4.1.1916.2.131.50.1.3.31.2.1.3
		extremeWingCfgRouteMapMatchClauseAcl OBJECT-TYPE
			SYNTAX ExtremeWingIdentifier
			MAX-ACCESS read-write
			STATUS current
			DESCRIPTION
				"IP access list to be used as match criterion for the route map.
				
				XPath: /extremeWing-config/routing_policy[name=key1]/route_map[precedence=key2]/match_clause_acl"
			::= { extremeWingCfgRouteMapEntry 3 }

		
		-- 1.3.6.1.4.1.1916.2.131.50.1.3.31.2.1.4
		extremeWingCfgRouteMapMatchClauseDscp OBJECT-TYPE
			SYNTAX Unsigned32 (0..63)
			MAX-ACCESS read-write
			STATUS current
			DESCRIPTION
				"IP DSCP value to be used as match criterion for the route map.
				
				XPath: /extremeWing-config/routing_policy[name=key1]/route_map[precedence=key2]/match_clause_dscp"
			::= { extremeWingCfgRouteMapEntry 4 }

		
		-- 1.3.6.1.4.1.1916.2.131.50.1.3.31.2.1.5
		extremeWingCfgRouteMapMatchClauseWlan OBJECT-TYPE
			SYNTAX ExtremeWingIdentifier
			MAX-ACCESS read-write
			STATUS current
			DESCRIPTION
				"WLAN to be used as match criterion for the route map.
				
				XPath: /extremeWing-config/routing_policy[name=key1]/route_map[precedence=key2]/match_clause_wlan"
			::= { extremeWingCfgRouteMapEntry 5 }

		
		-- 1.3.6.1.4.1.1916.2.131.50.1.3.31.2.1.6
		extremeWingCfgRouteMapRolePolicy OBJECT-TYPE
			SYNTAX ExtremeWingIdentifier
			MAX-ACCESS read-write
			STATUS current
			DESCRIPTION
				"
				
				XPath: /extremeWing-config/routing_policy[name=key1]/route_map[precedence=key2]/match_clause_role/role_policy"
			::= { extremeWingCfgRouteMapEntry 6 }

		
		-- 1.3.6.1.4.1.1916.2.131.50.1.3.31.2.1.7
		extremeWingCfgRouteMapUserRole OBJECT-TYPE
			SYNTAX ExtremeWingIdentifier
			MAX-ACCESS read-write
			STATUS current
			DESCRIPTION
				"
				
				XPath: /extremeWing-config/routing_policy[name=key1]/route_map[precedence=key2]/match_clause_role/user_role"
			::= { extremeWingCfgRouteMapEntry 7 }

		
		-- 1.3.6.1.4.1.1916.2.131.50.1.3.31.2.1.8
		extremeWingCfgRouteMapMatchClauseIncomingInterface OBJECT-TYPE
			SYNTAX DisplayString
			MAX-ACCESS read-write
			STATUS current
			DESCRIPTION
				"Name of the interface on which the packet is received. This can be a VLAN or a WWAN interface
				
				XPath: /extremeWing-config/routing_policy[name=key1]/route_map[precedence=key2]/match_clause_incoming_interface"
			::= { extremeWingCfgRouteMapEntry 8 }

		
		-- 1.3.6.1.4.1.1916.2.131.50.1.3.31.2.1.9
		extremeWingCfgRouteMapNextHop1 OBJECT-TYPE
			SYNTAX DisplayString
			MAX-ACCESS read-write
			STATUS current
			DESCRIPTION
				"
				
				XPath: /extremeWing-config/routing_policy[name=key1]/route_map[precedence=key2]/set_clause_next_hop/next_hop1"
			::= { extremeWingCfgRouteMapEntry 9 }

		
		-- 1.3.6.1.4.1.1916.2.131.50.1.3.31.2.1.11
		extremeWingCfgRouteMapNextHop2 OBJECT-TYPE
			SYNTAX DisplayString
			MAX-ACCESS read-write
			STATUS current
			DESCRIPTION
				"
				
				XPath: /extremeWing-config/routing_policy[name=key1]/route_map[precedence=key2]/set_clause_next_hop/next_hop2"
			::= { extremeWingCfgRouteMapEntry 11 }

		
		-- 1.3.6.1.4.1.1916.2.131.50.1.3.31.2.1.13
		extremeWingCfgRouteMapSetClauseDefaultNextHop OBJECT-TYPE
			SYNTAX DisplayString
			MAX-ACCESS read-write
			STATUS current
			DESCRIPTION
				"
				
				XPath: /extremeWing-config/routing_policy[name=key1]/route_map[precedence=key2]/set_clause_default_next_hop"
			::= { extremeWingCfgRouteMapEntry 13 }

		
		-- 1.3.6.1.4.1.1916.2.131.50.1.3.31.2.1.14
		extremeWingCfgRouteMapSetClauseFallback OBJECT-TYPE
			SYNTAX TruthValue
			MAX-ACCESS read-write
			STATUS current
			DESCRIPTION
				"Fallback to destination based routing if none of the next-hops are reachable
				
				XPath: /extremeWing-config/routing_policy[name=key1]/route_map[precedence=key2]/set_clause_fallback"
			DEFVAL { true }
			::= { extremeWingCfgRouteMapEntry 14 }

		
		-- 1.3.6.1.4.1.1916.2.131.50.1.3.31.2.1.15
		extremeWingCfgRouteMapSetClauseMarkDscp OBJECT-TYPE
			SYNTAX Unsigned32 (0..63)
			MAX-ACCESS read-write
			STATUS current
			DESCRIPTION
				"
				
				XPath: /extremeWing-config/routing_policy[name=key1]/route_map[precedence=key2]/set_clause_mark_dscp"
			::= { extremeWingCfgRouteMapEntry 15 }

		
		-- 1.3.6.1.4.1.1916.2.131.50.1.3.32
		extremeWingCfgl2tpv3Policy OBJECT IDENTIFIER ::= { extremeWingConfig 32 }

		
		-- 1.3.6.1.4.1.1916.2.131.50.1.3.32.1
		extremeWingCfgl2tpv3PolicyTable OBJECT-TYPE
			SYNTAX SEQUENCE OF ExtremeWingCfgl2tpv3PolicyEntry
			MAX-ACCESS not-accessible
			STATUS current
			DESCRIPTION
				"extremeWing Cfg l2tpv3 Policy Table"
			::= { extremeWingCfgl2tpv3Policy 1 }

		
		-- 1.3.6.1.4.1.1916.2.131.50.1.3.32.1.1
		extremeWingCfgl2tpv3PolicyEntry OBJECT-TYPE
			SYNTAX ExtremeWingCfgl2tpv3PolicyEntry
			MAX-ACCESS not-accessible
			STATUS current
			DESCRIPTION
				"An entry in the table."
			INDEX { extremeWingCfgl2tpv3PolicyName }
			::= { extremeWingCfgl2tpv3PolicyTable 1 }

		
		ExtremeWingCfgl2tpv3PolicyEntry ::=
			SEQUENCE { 
				extremeWingCfgl2tpv3PolicyName
					ExtremeWingIdentifier,
				extremeWingCfgl2tpv3PolicyHelloInterval
					Unsigned32,
				extremeWingCfgl2tpv3PolicyRetryAttempts
					Unsigned32,
				extremeWingCfgl2tpv3PolicyRetryInterval
					Unsigned32,
				extremeWingCfgl2tpv3PolicyHideAVPs
					TruthValue,
				extremeWingCfgl2tpv3PolicyCookieSize
					DisplayString,
				extremeWingCfgl2tpv3PolicyRxWindowSize
					Unsigned32,
				extremeWingCfgl2tpv3PolicyTxWindowSize
					Unsigned32,
				extremeWingCfgl2tpv3PolicySequencingRequired
					TruthValue,
				extremeWingCfgl2tpv3PolicyReconnectInterval
					Unsigned32,
				extremeWingCfgl2tpv3PolicyReconnectAttempts
					Unsigned32
			 }

		-- 1.3.6.1.4.1.1916.2.131.50.1.3.32.1.1.1
		extremeWingCfgl2tpv3PolicyName OBJECT-TYPE
			SYNTAX ExtremeWingIdentifier (SIZE (1..31))
			MAX-ACCESS read-only
			STATUS current
			DESCRIPTION
				"l2tpv3 Policy Name.
				
				XPath: /extremeWing-config/l2tpv3_policy[name=key1]/name"
			::= { extremeWingCfgl2tpv3PolicyEntry 1 }

		
		-- 1.3.6.1.4.1.1916.2.131.50.1.3.32.1.1.3
		extremeWingCfgl2tpv3PolicyHelloInterval OBJECT-TYPE
			SYNTAX Unsigned32 (1..3600)
			MAX-ACCESS read-write
			STATUS current
			DESCRIPTION
				"Time in seconds for sending Hello Keepalive packets.
				
				XPath: /extremeWing-config/l2tpv3_policy[name=key1]/hello_interval"
			::= { extremeWingCfgl2tpv3PolicyEntry 3 }

		
		-- 1.3.6.1.4.1.1916.2.131.50.1.3.32.1.1.4
		extremeWingCfgl2tpv3PolicyRetryAttempts OBJECT-TYPE
			SYNTAX Unsigned32 (1..10)
			MAX-ACCESS read-write
			STATUS current
			DESCRIPTION
				"Number tries before declaring a peer dead.
				
				XPath: /extremeWing-config/l2tpv3_policy[name=key1]/retry_attempts"
			::= { extremeWingCfgl2tpv3PolicyEntry 4 }

		
		-- 1.3.6.1.4.1.1916.2.131.50.1.3.32.1.1.5
		extremeWingCfgl2tpv3PolicyRetryInterval OBJECT-TYPE
			SYNTAX Unsigned32 (1..250)
			MAX-ACCESS read-write
			STATUS current
			DESCRIPTION
				"Time between successive retries.
				
				XPath: /extremeWing-config/l2tpv3_policy[name=key1]/retry_interval"
			::= { extremeWingCfgl2tpv3PolicyEntry 5 }

		
		-- 1.3.6.1.4.1.1916.2.131.50.1.3.32.1.1.6
		extremeWingCfgl2tpv3PolicyHideAVPs OBJECT-TYPE
			SYNTAX TruthValue
			MAX-ACCESS read-write
			STATUS current
			DESCRIPTION
				"Hide the AVPs.
				
				XPath: /extremeWing-config/l2tpv3_policy[name=key1]/hide_avps"
			::= { extremeWingCfgl2tpv3PolicyEntry 6 }

		
		-- 1.3.6.1.4.1.1916.2.131.50.1.3.32.1.1.7
		extremeWingCfgl2tpv3PolicyCookieSize OBJECT-TYPE
			SYNTAX DisplayString
			MAX-ACCESS read-write
			STATUS current
			DESCRIPTION
				"Size of the Cookies in the session.

                                 Values:
                                 0,
                                 4,
                                 8  
				
				XPath: /extremeWing-config/l2tpv3_policy[name=key1]/cookie_size"
			::= { extremeWingCfgl2tpv3PolicyEntry 7 }

		
		-- 1.3.6.1.4.1.1916.2.131.50.1.3.32.1.1.8
		extremeWingCfgl2tpv3PolicyRxWindowSize OBJECT-TYPE
			SYNTAX Unsigned32 (1..15)
			MAX-ACCESS read-write
			STATUS current
			DESCRIPTION
				"Rx Window size.
				
				XPath: /extremeWing-config/l2tpv3_policy[name=key1]/rx_window_size"
			::= { extremeWingCfgl2tpv3PolicyEntry 8 }

		
		-- 1.3.6.1.4.1.1916.2.131.50.1.3.32.1.1.9
		extremeWingCfgl2tpv3PolicyTxWindowSize OBJECT-TYPE
			SYNTAX Unsigned32 (1..15)
			MAX-ACCESS read-write
			STATUS current
			DESCRIPTION
				"Tx Window size.
				
				XPath: /extremeWing-config/l2tpv3_policy[name=key1]/tx_window_size"
			::= { extremeWingCfgl2tpv3PolicyEntry 9 }

		
		-- 1.3.6.1.4.1.1916.2.131.50.1.3.32.1.1.10
		extremeWingCfgl2tpv3PolicySequencingRequired OBJECT-TYPE
			SYNTAX TruthValue
			MAX-ACCESS read-write
			STATUS current
			DESCRIPTION
				"Sequence the packets receive/sent.
				
				XPath: /extremeWing-config/l2tpv3_policy[name=key1]/sequencing_required"
			::= { extremeWingCfgl2tpv3PolicyEntry 10 }

		
		-- 1.3.6.1.4.1.1916.2.131.50.1.3.32.1.1.11
		extremeWingCfgl2tpv3PolicyReconnectInterval OBJECT-TYPE
			SYNTAX Unsigned32 (1..3600)
			MAX-ACCESS read-write
			STATUS current
			DESCRIPTION
				"Time between two sucessive retry attempts.
				
				XPath: /extremeWing-config/l2tpv3_policy[name=key1]/reconnect_interval"
			::= { extremeWingCfgl2tpv3PolicyEntry 11 }

		
		-- 1.3.6.1.4.1.1916.2.131.50.1.3.32.1.1.12
		extremeWingCfgl2tpv3PolicyReconnectAttempts OBJECT-TYPE
			SYNTAX Unsigned32 (0..250)
			MAX-ACCESS read-write
			STATUS current
			DESCRIPTION
				"Number of reconnect to peer attempts, 0: try to reconnect for ever.
				
				XPath: /extremeWing-config/l2tpv3_policy[name=key1]/reconnect_attempts"
			::= { extremeWingCfgl2tpv3PolicyEntry 12 }

		
		-- 1.3.6.1.4.1.1916.2.131.50.1.3.33
		extremeWingCfgLegacyAp OBJECT IDENTIFIER ::= { extremeWingConfig 33 }

		
		-- 1.3.6.1.4.1.1916.2.131.50.1.3.33.1
		extremeWingCfgLegacyApTable OBJECT-TYPE
			SYNTAX SEQUENCE OF ExtremeWingCfgLegacyApEntry
			MAX-ACCESS not-accessible
			STATUS current
			DESCRIPTION
				"Legacy AP (AP300) configuraion.
				
				/extremeWing-config/ap300"
			::= { extremeWingCfgLegacyAp 1 }

		
		-- 1.3.6.1.4.1.1916.2.131.50.1.3.33.1.1
		extremeWingCfgLegacyApEntry OBJECT-TYPE
			SYNTAX ExtremeWingCfgLegacyApEntry
			MAX-ACCESS not-accessible
			STATUS current
			DESCRIPTION
				"An entry in the table."
			INDEX { extremeWingCfgLegacyApIndex }
			::= { extremeWingCfgLegacyApTable 1 }

		
		ExtremeWingCfgLegacyApEntry ::=
			SEQUENCE { 
				extremeWingCfgLegacyApIndex
					ExtremeWingIdentifier,
				extremeWingCfgLegacyApCountryCode
					DisplayString,
				extremeWingCfgLegacyApLed
					TruthValue,
				extremeWingCfgLegacyApLocation
					DisplayString,
				extremeWingCfgLegacyApIpAddr
					DisplayString,
				extremeWingCfgLegacyApGateway
					IpAddress,
				extremeWingCfgLegacyApPreferredControllerGroup
					DisplayString
			 }

		-- 1.3.6.1.4.1.1916.2.131.50.1.3.33.1.1.1
		extremeWingCfgLegacyApIndex OBJECT-TYPE
			SYNTAX ExtremeWingIdentifier
			MAX-ACCESS read-only
			STATUS current
			DESCRIPTION
				"AP index.
				
				Values:
				MAC address in string format with - as the sepearator,
				e.g. 00-A0-F8-BC-E9-21
				default-ap300
				
				XPath: /extremeWing-config/ap300[mac=key1]/mac"
			::= { extremeWingCfgLegacyApEntry 1 }

		
		-- 1.3.6.1.4.1.1916.2.131.50.1.3.33.1.1.3
		extremeWingCfgLegacyApCountryCode OBJECT-TYPE
			SYNTAX DisplayString
			MAX-ACCESS read-write
			STATUS current
			DESCRIPTION
				"The country of operation.
				
				Values:
				not-set ae ai an ar at au ba bb be bg bh bm bo br bs bw by
				ca ch cl cn co cr cx cy cz de dk do dz ec ee eg es fi fk fr
				gb gf gp gr gt gu gy hk hn hr ht hu id ie il in is it jm jo
				jp ke kr kw ky kz lb li lk lt lu lv ma md mk mq mt mx my mp
				me nf ng ni nl no nu nz na om pa pe ph pk pl pr pt py qa
				ro rs ru sa se sg si sk sv th tr tn tt tw ua us uy ve vg vi
				vn za
				
				XPath: /extremeWing-config/ap300[mac=key1]/country_code"
			::= { extremeWingCfgLegacyApEntry 3 }

		
		-- 1.3.6.1.4.1.1916.2.131.50.1.3.33.1.1.4
		extremeWingCfgLegacyApLed OBJECT-TYPE
			SYNTAX TruthValue
			MAX-ACCESS read-write
			STATUS current
			DESCRIPTION
				"Turn LEDs on/off on the AP.
				
				XPath: /extremeWing-config/ap300[mac=key1]/led"
			DEFVAL { true }
			::= { extremeWingCfgLegacyApEntry 4 }

		
		-- 1.3.6.1.4.1.1916.2.131.50.1.3.33.1.1.5
		extremeWingCfgLegacyApLocation OBJECT-TYPE
			SYNTAX DisplayString (SIZE (0..64))
			MAX-ACCESS read-write
			STATUS current
			DESCRIPTION
				"The location of this AP.
				
				XPath: /extremeWing-config/ap300[mac=key1]/location"
			::= { extremeWingCfgLegacyApEntry 5 }

		
		-- 1.3.6.1.4.1.1916.2.131.50.1.3.33.1.1.6
		extremeWingCfgLegacyApIpAddr OBJECT-TYPE
			SYNTAX DisplayString
			MAX-ACCESS read-write
			STATUS current
			DESCRIPTION
				"The IP address for AP adoption, network mask /32
				has to be specified. (e.g. 10.0.0.1/8)
				
				XPath: /extremeWing-config/ap300[mac=key1]/ap300_ip_address"
			::= { extremeWingCfgLegacyApEntry 6 }

		
		-- 1.3.6.1.4.1.1916.2.131.50.1.3.33.1.1.7
		extremeWingCfgLegacyApGateway OBJECT-TYPE
			SYNTAX IpAddress
			MAX-ACCESS read-write
			STATUS current
			DESCRIPTION
				"The IP gateway for AP adoption (e.g. 10.0.0.1).
				
				XPath: /extremeWing-config/ap300[mac=key1]/ap300_gw"
			::= { extremeWingCfgLegacyApEntry 7 }

		
		-- 1.3.6.1.4.1.1916.2.131.50.1.3.33.1.1.8
		extremeWingCfgLegacyApPreferredControllerGroup OBJECT-TYPE
			SYNTAX DisplayString (SIZE (0..64))
			MAX-ACCESS read-write
			STATUS current
			DESCRIPTION
				"Controller which the AP will prefer for adoption.
				
				XPath: /extremeWing-config/ap300[mac=key1]/preferred_controller_group"
			::= { extremeWingCfgLegacyApEntry 8 }

		
		-- 1.3.6.1.4.1.1916.2.131.50.1.3.33.2
		extremeWingCfgLegacyApIfTable OBJECT-TYPE
			SYNTAX SEQUENCE OF ExtremeWingCfgLegacyApIfEntry
			MAX-ACCESS not-accessible
			STATUS current
			DESCRIPTION
				"Legacy AP radio interface configuration.
				
				/extremeWing-config/ap300/interface"
			::= { extremeWingCfgLegacyAp 2 }

		
		-- 1.3.6.1.4.1.1916.2.131.50.1.3.33.2.1
		extremeWingCfgLegacyApIfEntry OBJECT-TYPE
			SYNTAX ExtremeWingCfgLegacyApIfEntry
			MAX-ACCESS not-accessible
			STATUS current
			DESCRIPTION
				"An entry in the table."
			INDEX { extremeWingCfgLegacyApIndex, extremeWingCfgLegacyApIfName }
			::= { extremeWingCfgLegacyApIfTable 1 }

		
		ExtremeWingCfgLegacyApIfEntry ::=
			SEQUENCE { 
				extremeWingCfgLegacyApIfName
					ExtremeWingIdentifier,
				extremeWingCfgLegacyApIfDescr
					DisplayString,
				extremeWingCfgLegacyApIfShutdown
					TruthValue,
				extremeWingCfgLegacyApIfRfMode
					DisplayString,
				extremeWingCfgLegacyApIfAntennaDiversity
					TruthValue,
				extremeWingCfgLegacyApIfBeaconInterval
					DisplayString,
				extremeWingCfgLegacyApIfChannel
					DisplayString,
				extremeWingCfgLegacyApIfMaxClients
					Unsigned32,
				extremeWingCfgLegacyApIfPlacement
					DisplayString,
				extremeWingCfgLegacyApIfPower
					Unsigned32,
				extremeWingCfgLegacyApIfPreambleShort
					TruthValue,
				extremeWingCfgLegacyApIfOnChannelScan
					TruthValue,
				extremeWingCfgLegacyApIfRtsThreshold
					Unsigned32,
				extremeWingCfgLegacyApIfQosPolicy
					ExtremeWingIdentifier,
				extremeWingCfgLegacyApIfWirelessClientPower
					Unsigned32
			 }

		-- 1.3.6.1.4.1.1916.2.131.50.1.3.33.2.1.1
		extremeWingCfgLegacyApIfName OBJECT-TYPE
			SYNTAX ExtremeWingIdentifier
			MAX-ACCESS read-only
			STATUS current
			DESCRIPTION
				"Radio interface name.
				
				XPath: /extremeWing-config/ap300[mac=key1]/interface[name=key2]/name"
			::= { extremeWingCfgLegacyApIfEntry 1 }

		
		-- 1.3.6.1.4.1.1916.2.131.50.1.3.33.2.1.3
		extremeWingCfgLegacyApIfDescr OBJECT-TYPE
			SYNTAX DisplayString (SIZE (0..64))
			MAX-ACCESS read-write
			STATUS current
			DESCRIPTION
				"Description for the radio.
				
				XPath: /extremeWing-config/ap300[mac=key1]/interface[name=key2]/description"
			::= { extremeWingCfgLegacyApIfEntry 3 }

		
		-- 1.3.6.1.4.1.1916.2.131.50.1.3.33.2.1.4
		extremeWingCfgLegacyApIfShutdown OBJECT-TYPE
			SYNTAX TruthValue
			MAX-ACCESS read-write
			STATUS current
			DESCRIPTION
				"Shutdown the radio interface.
				
				XPath: /extremeWing-config/ap300[mac=key1]/interface[name=key2]/shutdown"
			DEFVAL { false }
			::= { extremeWingCfgLegacyApIfEntry 4 }

		
		-- 1.3.6.1.4.1.1916.2.131.50.1.3.33.2.1.5
		extremeWingCfgLegacyApIfRfMode OBJECT-TYPE
			SYNTAX DisplayString
			MAX-ACCESS read-write
			STATUS current
			DESCRIPTION
				"The rf-mode of operation for the radio.
				
				Values:
				2.4GHz-wlan
				5GHz-wlan
				sensor
				
				XPath: /extremeWing-config/ap300[mac=key1]/interface[name=key2]/rf_mode"
			::= { extremeWingCfgLegacyApIfEntry 5 }

		
		-- 1.3.6.1.4.1.1916.2.131.50.1.3.33.2.1.6
		extremeWingCfgLegacyApIfAntennaDiversity OBJECT-TYPE
			SYNTAX TruthValue
			MAX-ACCESS read-write
			STATUS current
			DESCRIPTION
				"Whether the radio should enable antenna diversity
				for transmit frames at non-11n data-rates.
				
				XPath: /extremeWing-config/ap300[mac=key1]/interface[name=key2]/antenna_diversity"
			DEFVAL { false }
			::= { extremeWingCfgLegacyApIfEntry 6 }

		
		-- 1.3.6.1.4.1.1916.2.131.50.1.3.33.2.1.7
		extremeWingCfgLegacyApIfBeaconInterval OBJECT-TYPE
			SYNTAX DisplayString
			UNITS "milliseconds"
			MAX-ACCESS read-write
			STATUS current
			DESCRIPTION
				"The beacon interval.
				
				Values:
				50
				100
				200
				
				XPath: /extremeWing-config/ap300[mac=key1]/interface[name=key2]/beacon_interval"
			DEFVAL { "100" }
			::= { extremeWingCfgLegacyApIfEntry 7 }

		
		-- 1.3.6.1.4.1.1916.2.131.50.1.3.33.2.1.8
		extremeWingCfgLegacyApIfChannel OBJECT-TYPE
			SYNTAX DisplayString
			MAX-ACCESS read-write
			STATUS current
			DESCRIPTION
				"Channel of operation for the radio.
				
				Values:
				1 2 3 4 5 6 7 8 9 10 11 12 13 14 36 40 44 48 52 56 60 64
				100 104 108 112 116 120 124 128 132 136 140 149 153 157
				161 165 34 38 42 46 acs smart
				
				XPath: /extremeWing-config/ap300[mac=key1]/interface[name=key2]/channel"
			DEFVAL { "smart" }
			::= { extremeWingCfgLegacyApIfEntry 8 }

		
		-- 1.3.6.1.4.1.1916.2.131.50.1.3.33.2.1.9
		extremeWingCfgLegacyApIfMaxClients OBJECT-TYPE
			SYNTAX Unsigned32 (0..256)
			MAX-ACCESS read-write
			STATUS current
			DESCRIPTION
				"The maximum number of clients allowed to associate with
				the radio subject to AP limit.
				
				XPath: /extremeWing-config/ap300[mac=key1]/interface[name=key2]/max_clients"
			DEFVAL { 256 }
			::= { extremeWingCfgLegacyApIfEntry 9 }

		
		-- 1.3.6.1.4.1.1916.2.131.50.1.3.33.2.1.10
		extremeWingCfgLegacyApIfPlacement OBJECT-TYPE
			SYNTAX DisplayString
			MAX-ACCESS read-write
			STATUS current
			DESCRIPTION
				"Location where the radio is operating.
				
				Values:
				indoor
				outdoor
				
				XPath: /extremeWing-config/ap300[mac=key1]/interface[name=key2]/placement"
			DEFVAL { "indoor" }
			::= { extremeWingCfgLegacyApIfEntry 10 }

		
		-- 1.3.6.1.4.1.1916.2.131.50.1.3.33.2.1.11
		extremeWingCfgLegacyApIfPower OBJECT-TYPE
			SYNTAX Unsigned32 (1..20)
			UNITS "dBm"
			MAX-ACCESS read-write
			STATUS current
			DESCRIPTION
				"Transmit power of the radio.  A setting of 0 indicates
				Smart RF is managing the power.
				
				XPath: /extremeWing-config/ap300[mac=key1]/interface[name=key2]/power"
			DEFVAL { 20 }
			::= { extremeWingCfgLegacyApIfEntry 11 }

		
		-- 1.3.6.1.4.1.1916.2.131.50.1.3.33.2.1.12
		extremeWingCfgLegacyApIfPreambleShort OBJECT-TYPE
			SYNTAX TruthValue
			MAX-ACCESS read-write
			STATUS current
			DESCRIPTION
				"Use short preambles on the radio.
				
				XPath: /extremeWing-config/ap300[mac=key1]/interface[name=key2]/preamble_short"
			DEFVAL { false }
			::= { extremeWingCfgLegacyApIfEntry 12 }

		
		-- 1.3.6.1.4.1.1916.2.131.50.1.3.33.2.1.13
		extremeWingCfgLegacyApIfOnChannelScan OBJECT-TYPE
			SYNTAX TruthValue
			MAX-ACCESS read-write
			STATUS current
			DESCRIPTION
				"Enable/disable on channel scan on the radio.
				
				XPath: /extremeWing-config/ap300[mac=key1]/interface[name=key2]/on_channel_scan"
			DEFVAL { false }
			::= { extremeWingCfgLegacyApIfEntry 13 }

		
		-- 1.3.6.1.4.1.1916.2.131.50.1.3.33.2.1.14
		extremeWingCfgLegacyApIfRtsThreshold OBJECT-TYPE
			SYNTAX Unsigned32 (1..2347)
			UNITS "bytes"
			MAX-ACCESS read-write
			STATUS current
			DESCRIPTION
				"RTS threshold on the radio.
				
				XPath: /extremeWing-config/ap300[mac=key1]/interface[name=key2]/rts_threshold"
			DEFVAL { 2347 }
			::= { extremeWingCfgLegacyApIfEntry 14 }

		
		-- 1.3.6.1.4.1.1916.2.131.50.1.3.33.2.1.15
		extremeWingCfgLegacyApIfQosPolicy OBJECT-TYPE
			SYNTAX ExtremeWingIdentifier
			MAX-ACCESS read-write
			STATUS current
			DESCRIPTION
				"QOS policy on the radio.
				
				XPath: /extremeWing-config/ap300[mac=key1]/interface[name=key2]/qos_policy"
			::= { extremeWingCfgLegacyApIfEntry 15 }

		
		-- 1.3.6.1.4.1.1916.2.131.50.1.3.33.2.1.16
		extremeWingCfgLegacyApIfWirelessClientPower OBJECT-TYPE
			SYNTAX Unsigned32 (0..20)
			UNITS "dBm"
			MAX-ACCESS read-write
			STATUS current
			DESCRIPTION
				"Transmit power indicated to wireless clients
				for transmission.
				
				XPath: /extremeWing-config/ap300[mac=key1]/interface[name=key2]/wireless_client_power"
			::= { extremeWingCfgLegacyApIfEntry 16 }

		
		-- 1.3.6.1.4.1.1916.2.131.50.1.3.33.3
		extremeWingCfgLegacyApIfWlanBssMapTable OBJECT-TYPE
			SYNTAX SEQUENCE OF ExtremeWingCfgLegacyApIfWlanBssMapEntry
			MAX-ACCESS not-accessible
			STATUS current
			DESCRIPTION
				"WLANs enabled on this radio.
				
				/extremeWing-config/ap300/interface/wlanbssmap"
			::= { extremeWingCfgLegacyAp 3 }

		
		-- 1.3.6.1.4.1.1916.2.131.50.1.3.33.3.1
		extremeWingCfgLegacyApIfWlanBssMapEntry OBJECT-TYPE
			SYNTAX ExtremeWingCfgLegacyApIfWlanBssMapEntry
			MAX-ACCESS not-accessible
			STATUS current
			DESCRIPTION
				"An entry in the table."
			INDEX { extremeWingCfgLegacyApIndex, extremeWingCfgLegacyApIfName, extremeWingCfgLegacyApIfWlanBssMapWlan }
			::= { extremeWingCfgLegacyApIfWlanBssMapTable 1 }

		
		ExtremeWingCfgLegacyApIfWlanBssMapEntry ::=
			SEQUENCE { 
				extremeWingCfgLegacyApIfWlanBssMapWlan
					ExtremeWingIdentifier,
				extremeWingCfgLegacyApIfWlanBssMapBss
					Unsigned32,
				extremeWingCfgLegacyApIfWlanBssMapPrimary
					TruthValue
			 }

		-- 1.3.6.1.4.1.1916.2.131.50.1.3.33.3.1.1
		extremeWingCfgLegacyApIfWlanBssMapWlan OBJECT-TYPE
			SYNTAX ExtremeWingIdentifier
			MAX-ACCESS read-only
			STATUS current
			DESCRIPTION
				"Name of the WLAN (it must have been already created
				and configured).
				
				XPath: /extremeWing-config/ap300[mac=key1]/interface[name=key2]/wlanbssmap[wlan=key3]/wlan"
			::= { extremeWingCfgLegacyApIfWlanBssMapEntry 1 }

		
		-- 1.3.6.1.4.1.1916.2.131.50.1.3.33.3.1.3
		extremeWingCfgLegacyApIfWlanBssMapBss OBJECT-TYPE
			SYNTAX Unsigned32 (1..4)
			MAX-ACCESS read-write
			STATUS current
			DESCRIPTION
				"BSS number on the radio where this WLAN is to be mapped.
				
				XPath: /extremeWing-config/ap300[mac=key1]/interface[name=key2]/wlanbssmap[wlan=key3]/bss"
			::= { extremeWingCfgLegacyApIfWlanBssMapEntry 3 }

		
		-- 1.3.6.1.4.1.1916.2.131.50.1.3.33.3.1.4
		extremeWingCfgLegacyApIfWlanBssMapPrimary OBJECT-TYPE
			SYNTAX TruthValue
			MAX-ACCESS read-write
			STATUS current
			DESCRIPTION
				"Make this WLAN the primary WLAN if there are multiple WLANs
				on its BSS.
				
				XPath: /extremeWing-config/ap300[mac=key1]/interface[name=key2]/wlanbssmap[wlan=key3]/primary"
			::= { extremeWingCfgLegacyApIfWlanBssMapEntry 4 }

		
-- Alternate read-only implementation of configuration tables
-- used by known network management applications.
		-- 1.3.6.1.4.1.1916.2.131.50.1.3.34
		extremeWingCfgAlt OBJECT IDENTIFIER ::= { extremeWingConfig 34 }

		
		-- 1.3.6.1.4.1.1916.2.131.50.1.3.34.1
		extremeWingCfgAltDevTable OBJECT-TYPE
			SYNTAX SEQUENCE OF ExtremeWingCfgAltDevEntry
			MAX-ACCESS not-accessible
			STATUS current
			DESCRIPTION
				"Copy of extremeWingCfgDevTable.
				
				/extremeWing-config/device"
			::= { extremeWingCfgAlt 1 }

		
		-- 1.3.6.1.4.1.1916.2.131.50.1.3.34.1.1
		extremeWingCfgAltDevEntry OBJECT-TYPE
			SYNTAX ExtremeWingCfgAltDevEntry
			MAX-ACCESS not-accessible
			STATUS current
			DESCRIPTION
				"An entry in the table."
			INDEX { extremeWingCfgAltDevMac }
			::= { extremeWingCfgAltDevTable 1 }

		
		ExtremeWingCfgAltDevEntry ::=
			SEQUENCE { 
				extremeWingCfgAltDevMac
					MacAddress,
				extremeWingCfgAltDevHostname
					DisplayString,
				extremeWingCfgAltDevBuilding
					DisplayString,
				extremeWingCfgAltDevFloor
					DisplayString,
				extremeWingCfgAltDevNumRadios
					Unsigned32,
				extremeWingCfgAltDevProfileName
					ExtremeWingIdentifier,
				extremeWingCfgAltDevRfDomainName
					ExtremeWingIdentifier,
				extremeWingCfgAltDevHttpsTrustpoint
					DisplayString,
				extremeWingCfgAltDevRadiusCaTrustpoint
					DisplayString,
				extremeWingCfgAltDevRadiusServerTrustpoint
					DisplayString,
				extremeWingCfgAltDevSshRsaKey
					ExtremeWingIdentifier,
				extremeWingCfgAltDevHasOverrides
					TruthValue,
			 }

		-- 1.3.6.1.4.1.1916.2.131.50.1.3.34.1.1.1
		extremeWingCfgAltDevMac OBJECT-TYPE
			SYNTAX MacAddress
			MAX-ACCESS read-only
			STATUS current
			DESCRIPTION
				"
				
				XPath: /extremeWing-config/device[mac=key1]/mac"
			::= { extremeWingCfgAltDevEntry 1 }

		
		-- 1.3.6.1.4.1.1916.2.131.50.1.3.34.1.1.3
		extremeWingCfgAltDevHostname OBJECT-TYPE
			SYNTAX DisplayString (SIZE (64))
			MAX-ACCESS read-only
			STATUS current
			DESCRIPTION
				"
				
				XPath: /extremeWing-config/device[mac=key1]/hostname"
			::= { extremeWingCfgAltDevEntry 3 }

		
		-- 1.3.6.1.4.1.1916.2.131.50.1.3.34.1.1.4
		extremeWingCfgAltDevBuilding OBJECT-TYPE
			SYNTAX DisplayString (SIZE (64))
			MAX-ACCESS read-only
			STATUS current
			DESCRIPTION
				"
				
				XPath: /extremeWing-config/device[mac=key1]/building"
			::= { extremeWingCfgAltDevEntry 4 }

		
		-- 1.3.6.1.4.1.1916.2.131.50.1.3.34.1.1.5
		extremeWingCfgAltDevFloor OBJECT-TYPE
			SYNTAX DisplayString (SIZE (32))
			MAX-ACCESS read-only
			STATUS current
			DESCRIPTION
				"
				
				XPath: /extremeWing-config/device[mac=key1]/floor"
			::= { extremeWingCfgAltDevEntry 5 }

		
		-- 1.3.6.1.4.1.1916.2.131.50.1.3.34.1.1.6
		extremeWingCfgAltDevNumRadios OBJECT-TYPE
			SYNTAX Unsigned32 (0..3)
			MAX-ACCESS read-only
			STATUS current
			DESCRIPTION
				"
				
				XPath: /extremeWing-config/device[mac=key1]/num_radios"
			::= { extremeWingCfgAltDevEntry 6 }

		
		-- 1.3.6.1.4.1.1916.2.131.50.1.3.34.1.1.7
		extremeWingCfgAltDevProfileName OBJECT-TYPE
			SYNTAX ExtremeWingIdentifier
			MAX-ACCESS read-only
			STATUS current
			DESCRIPTION
				"
				
				XPath: /extremeWing-config/device[mac=key1]/profile_name"
			::= { extremeWingCfgAltDevEntry 7 }

		
		-- 1.3.6.1.4.1.1916.2.131.50.1.3.34.1.1.8
		extremeWingCfgAltDevRfDomainName OBJECT-TYPE
			SYNTAX ExtremeWingIdentifier
			MAX-ACCESS read-only
			STATUS current
			DESCRIPTION
				"
				
				XPath: /extremeWing-config/device[mac=key1]/rf_domain_name"
			::= { extremeWingCfgAltDevEntry 8 }

		
		-- 1.3.6.1.4.1.1916.2.131.50.1.3.34.1.1.9
		extremeWingCfgAltDevHttpsTrustpoint OBJECT-TYPE
			SYNTAX DisplayString (SIZE (1..32))
			MAX-ACCESS read-only
			STATUS current
			DESCRIPTION
				"
				
				XPath: /extremeWing-config/device[mac=key1]/https-trustpoint"
			DEFVAL { "default-trustpoint" }
			::= { extremeWingCfgAltDevEntry 9 }

		
		-- 1.3.6.1.4.1.1916.2.131.50.1.3.34.1.1.10
		extremeWingCfgAltDevRadiusCaTrustpoint OBJECT-TYPE
			SYNTAX DisplayString (SIZE (1..32))
			MAX-ACCESS read-only
			STATUS current
			DESCRIPTION
				"
				
				XPath: /extremeWing-config/device[mac=key1]/radius-ca-trustpoint"
			::= { extremeWingCfgAltDevEntry 10 }

		
		-- 1.3.6.1.4.1.1916.2.131.50.1.3.34.1.1.11
		extremeWingCfgAltDevRadiusServerTrustpoint OBJECT-TYPE
			SYNTAX DisplayString (SIZE (1..32))
			MAX-ACCESS read-only
			STATUS current
			DESCRIPTION
				"
				
				XPath: /extremeWing-config/device[mac=key1]/radius-server-trustpoint"
			DEFVAL { "default-trustpoint" }
			::= { extremeWingCfgAltDevEntry 11 }

		
		-- 1.3.6.1.4.1.1916.2.131.50.1.3.34.1.1.12
		extremeWingCfgAltDevSshRsaKey OBJECT-TYPE
			SYNTAX ExtremeWingIdentifier
			MAX-ACCESS read-only
			STATUS current
			DESCRIPTION
				"
				
				XPath: /extremeWing-config/device[mac=key1]/ssh-rsa-key"
			DEFVAL { "default_rsa_key" }
			::= { extremeWingCfgAltDevEntry 12 }

		
		-- 1.3.6.1.4.1.1916.2.131.50.1.3.34.1.1.13
		extremeWingCfgAltDevHasOverrides OBJECT-TYPE
			SYNTAX TruthValue
			MAX-ACCESS read-only
			STATUS current
			DESCRIPTION
				"read only value to indicate whether the device has at least one override
				
				XPath: /extremeWing-config/device[mac=key1]/has_overrides"
			DEFVAL { false }
			::= { extremeWingCfgAltDevEntry 13 }

		
		-- 1.3.6.1.4.1.1916.2.131.50.1.3.34.2
		extremeWingCfgAltDevIfTable OBJECT-TYPE
			SYNTAX SEQUENCE OF ExtremeWingCfgAltDevIfEntry
			MAX-ACCESS not-accessible
			STATUS current
			DESCRIPTION
				"Copy of extremeWingCfgDevIfTable.
				
				/extremeWing-config/device/interface"
			::= { extremeWingCfgAlt 2 }

		
		-- 1.3.6.1.4.1.1916.2.131.50.1.3.34.2.1
		extremeWingCfgAltDevIfEntry OBJECT-TYPE
			SYNTAX ExtremeWingCfgAltDevIfEntry
			MAX-ACCESS not-accessible
			STATUS current
			DESCRIPTION
				"An entry in the table."
			INDEX { extremeWingCfgAltDevMac, extremeWingCfgAltDevIfName }
			::= { extremeWingCfgAltDevIfTable 1 }

		
		ExtremeWingCfgAltDevIfEntry ::=
			SEQUENCE { 
				extremeWingCfgAltDevIfName
					ExtremeWingIdentifier,
				extremeWingCfgAltDevIfDescription
					DisplayString,
				extremeWingCfgAltDevIfType
					DisplayString,
				extremeWingCfgAltDevIfShutdown
					TruthValue,
				extremeWingCfgAltDevIfIpInAcl
					ExtremeWingIdentifier,
				extremeWingCfgAltDevIfMacInAcl
					ExtremeWingIdentifier
			 }

		-- 1.3.6.1.4.1.1916.2.131.50.1.3.34.2.1.1
		extremeWingCfgAltDevIfName OBJECT-TYPE
			SYNTAX ExtremeWingIdentifier
			MAX-ACCESS read-only
			STATUS current
			DESCRIPTION
				"
				
				XPath: /extremeWing-config/device[mac=key1]/interface[name=key2]/name"
			::= { extremeWingCfgAltDevIfEntry 1 }

		
		-- 1.3.6.1.4.1.1916.2.131.50.1.3.34.2.1.3
		extremeWingCfgAltDevIfDescription OBJECT-TYPE
			SYNTAX DisplayString
			MAX-ACCESS read-only
			STATUS current
			DESCRIPTION
				"
				
				XPath: /extremeWing-config/device[mac=key1]/interface[name=key2]/description"
			::= { extremeWingCfgAltDevIfEntry 3 }

		
		-- 1.3.6.1.4.1.1916.2.131.50.1.3.34.2.1.4
		extremeWingCfgAltDevIfType OBJECT-TYPE
			SYNTAX DisplayString
			MAX-ACCESS read-only
			STATUS current
			DESCRIPTION
				"Hardware type of the network interface
				
				Values:
				ethernet
				vlan
				radio
				port_channel
				
				XPath: /extremeWing-config/device[mac=key1]/interface[name=key2]/type"
			::= { extremeWingCfgAltDevIfEntry 4 }

		
		-- 1.3.6.1.4.1.1916.2.131.50.1.3.34.2.1.5
		extremeWingCfgAltDevIfShutdown OBJECT-TYPE
			SYNTAX TruthValue
			MAX-ACCESS read-only
			STATUS current
			DESCRIPTION
				"
				
				XPath: /extremeWing-config/device[mac=key1]/interface[name=key2]/shutdown"
			DEFVAL { false }
			::= { extremeWingCfgAltDevIfEntry 5 }

		
		-- 1.3.6.1.4.1.1916.2.131.50.1.3.34.2.1.6
		extremeWingCfgAltDevIfIpInAcl OBJECT-TYPE
			SYNTAX ExtremeWingIdentifier
			MAX-ACCESS read-only
			STATUS current
			DESCRIPTION
				"
				
				XPath: /extremeWing-config/device[mac=key1]/interface[name=key2]/ip_in_acl"
			::= { extremeWingCfgAltDevIfEntry 6 }

		
		-- 1.3.6.1.4.1.1916.2.131.50.1.3.34.2.1.7
		extremeWingCfgAltDevIfMacInAcl OBJECT-TYPE
			SYNTAX ExtremeWingIdentifier
			MAX-ACCESS read-only
			STATUS current
			DESCRIPTION
				"
				
				XPath: /extremeWing-config/device[mac=key1]/interface[name=key2]/mac_in_acl"
			::= { extremeWingCfgAltDevIfEntry 7 }

		
		-- 1.3.6.1.4.1.1916.2.131.50.1.3.34.3
		extremeWingCfgAltDevIfRadioBssmapTable OBJECT-TYPE
			SYNTAX SEQUENCE OF ExtremeWingCfgAltDevIfRadioBssmapEntry
			MAX-ACCESS not-accessible
			STATUS current
			DESCRIPTION
				"Copy of extremeWingCfgDevIfRadioBssmapTable.
				
				/extremeWing-config/device/interface/wlanbssmap"
			::= { extremeWingCfgAlt 3 }

		
		-- 1.3.6.1.4.1.1916.2.131.50.1.3.34.3.1
		extremeWingCfgAltDevIfRadioBssmapEntry OBJECT-TYPE
			SYNTAX ExtremeWingCfgAltDevIfRadioBssmapEntry
			MAX-ACCESS not-accessible
			STATUS current
			DESCRIPTION
				"An entry in the table."
			INDEX { extremeWingCfgAltDevMac, extremeWingCfgAltDevIfName, extremeWingCfgAltDevIfRadioBssmapWlan }
			::= { extremeWingCfgAltDevIfRadioBssmapTable 1 }

		
		ExtremeWingCfgAltDevIfRadioBssmapEntry ::=
			SEQUENCE { 
				extremeWingCfgAltDevIfRadioBssmapWlan
					ExtremeWingIdentifier,
				extremeWingCfgAltDevIfRadioBssmapBss
					Unsigned32,
				extremeWingCfgAltDevIfRadioBssmapPrimary
					TruthValue
			 }

		-- 1.3.6.1.4.1.1916.2.131.50.1.3.34.3.1.1
		extremeWingCfgAltDevIfRadioBssmapWlan OBJECT-TYPE
			SYNTAX ExtremeWingIdentifier
			MAX-ACCESS read-only
			STATUS current
			DESCRIPTION
				"
				
				XPath: /extremeWing-config/device[mac=key1]/interface[name=key2]/wlanbssmap[wlan=key3]/wlan"
			::= { extremeWingCfgAltDevIfRadioBssmapEntry 1 }

		
		-- 1.3.6.1.4.1.1916.2.131.50.1.3.34.3.1.3
		extremeWingCfgAltDevIfRadioBssmapBss OBJECT-TYPE
			SYNTAX Unsigned32 (1..8)
			MAX-ACCESS read-only
			STATUS current
			DESCRIPTION
				"
				
				XPath: /extremeWing-config/device[mac=key1]/interface[name=key2]/wlanbssmap[wlan=key3]/bss"
			::= { extremeWingCfgAltDevIfRadioBssmapEntry 3 }

		
		-- 1.3.6.1.4.1.1916.2.131.50.1.3.34.3.1.4
		extremeWingCfgAltDevIfRadioBssmapPrimary OBJECT-TYPE
			SYNTAX TruthValue
			MAX-ACCESS read-only
			STATUS current
			DESCRIPTION
				"
				
				XPath: /extremeWing-config/device[mac=key1]/interface[name=key2]/wlanbssmap[wlan=key3]/primary"
			::= { extremeWingCfgAltDevIfRadioBssmapEntry 4 }

		
		-- 1.3.6.1.4.1.1916.2.131.50.1.3.35
		extremeWingCfgMcx OBJECT IDENTIFIER ::= { extremeWingConfig 35 }

		
		-- 1.3.6.1.4.1.1916.2.131.50.1.3.35.1
		extremeWingCfgMcxMeshpointTable OBJECT-TYPE
			SYNTAX SEQUENCE OF ExtremeWingCfgMcxMeshpointEntry
			MAX-ACCESS not-accessible
			STATUS current
			DESCRIPTION
				"
				
				/extremeWing-config/meshpoint"
			::= { extremeWingCfgMcx 1 }

		
		-- 1.3.6.1.4.1.1916.2.131.50.1.3.35.1.1
		extremeWingCfgMcxMeshpointEntry OBJECT-TYPE
			SYNTAX ExtremeWingCfgMcxMeshpointEntry
			MAX-ACCESS not-accessible
			STATUS current
			DESCRIPTION
				"An entry in the table."
			INDEX { extremeWingCfgMcxMeshpointName }
			::= { extremeWingCfgMcxMeshpointTable 1 }

		
		ExtremeWingCfgMcxMeshpointEntry ::=
			SEQUENCE { 
				extremeWingCfgMcxMeshpointName
					ExtremeWingIdentifier,
				extremeWingCfgMcxMeshpointShutdown
					TruthValue,
				extremeWingCfgMcxMeshpointMeshid
					DisplayString,
				extremeWingCfgMcxMeshpointDescription
					DisplayString,
				extremeWingCfgMcxMeshpointBeaconFormat
					DisplayString,
				extremeWingCfgMcxMeshpointControlVlan
					Unsigned32,
				extremeWingCfgMcxMeshpointNeighborInactivityTimeout
					Unsigned32,
				extremeWingCfgMcxMeshpointQosPolicy
					ExtremeWingIdentifier,
				extremeWingCfgMcxMeshpointSecurityMode
					DisplayString,
				extremeWingCfgMcxMeshpointWpa2Psk
					DisplayString,
				extremeWingCfgMcxMeshpointWpa2KeyRotationUnicast
					Unsigned32,
				extremeWingCfgMcxMeshpointWpa2KeyRotationBroadcast
					Unsigned32,
				extremeWingCfgMcxMeshpointIsRoot
					TruthValue
			 }

		-- 1.3.6.1.4.1.1916.2.131.50.1.3.35.1.1.1
		extremeWingCfgMcxMeshpointName OBJECT-TYPE
			SYNTAX ExtremeWingIdentifier
			MAX-ACCESS read-write
			STATUS current
			DESCRIPTION
				"
				
				XPath: /extremeWing-config/meshpoint[name=key1]/name"
			::= { extremeWingCfgMcxMeshpointEntry 1 }

		
		-- 1.3.6.1.4.1.1916.2.131.50.1.3.35.1.1.3
		extremeWingCfgMcxMeshpointShutdown OBJECT-TYPE
			SYNTAX TruthValue
			MAX-ACCESS read-write
			STATUS current
			DESCRIPTION
				"
				
				XPath: /extremeWing-config/meshpoint[name=key1]/shutdown"
			DEFVAL { false }
			::= { extremeWingCfgMcxMeshpointEntry 3 }

		
		-- 1.3.6.1.4.1.1916.2.131.50.1.3.35.1.1.4
		extremeWingCfgMcxMeshpointMeshid OBJECT-TYPE
			SYNTAX DisplayString (SIZE (0..32))
			MAX-ACCESS read-write
			STATUS current
			DESCRIPTION
				"Mesh Identifier for this MP.
				
				XPath: /extremeWing-config/meshpoint[name=key1]/meshid"
			::= { extremeWingCfgMcxMeshpointEntry 4 }

		
		-- 1.3.6.1.4.1.1916.2.131.50.1.3.35.1.1.5
		extremeWingCfgMcxMeshpointDescription OBJECT-TYPE
			SYNTAX DisplayString (SIZE (1..64))
			MAX-ACCESS read-write
			STATUS current
			DESCRIPTION
				"Descriptive text about this MP.
				
				XPath: /extremeWing-config/meshpoint[name=key1]/description"
			::= { extremeWingCfgMcxMeshpointEntry 5 }

		
		-- 1.3.6.1.4.1.1916.2.131.50.1.3.35.1.1.6
		extremeWingCfgMcxMeshpointBeaconFormat OBJECT-TYPE
			SYNTAX DisplayString
			MAX-ACCESS read-write
			STATUS current
			DESCRIPTION
				"
				
				Values:
				mesh-point;
				enum
				access-point
				
				XPath: /extremeWing-config/meshpoint[name=key1]/beacon_format"
			DEFVAL { "mesh-point" }
			::= { extremeWingCfgMcxMeshpointEntry 6 }

		
		-- 1.3.6.1.4.1.1916.2.131.50.1.3.35.1.1.7
		extremeWingCfgMcxMeshpointControlVlan OBJECT-TYPE
			SYNTAX Unsigned32 (1..4094)
			MAX-ACCESS read-write
			STATUS current
			DESCRIPTION
				"VLAN for meshpoint control traffic
				
				XPath: /extremeWing-config/meshpoint[name=key1]/control_vlan"
			DEFVAL { 1 }
			::= { extremeWingCfgMcxMeshpointEntry 7 }

		
		-- 1.3.6.1.4.1.1916.2.131.50.1.3.35.1.1.8
		extremeWingCfgMcxMeshpointNeighborInactivityTimeout OBJECT-TYPE
			SYNTAX Unsigned32 (60..86400)
			UNITS "seconds"
			MAX-ACCESS read-write
			STATUS current
			DESCRIPTION
				"If a frame is not received from a neighbor for this amount of time, the neighbor has its client resource revoked.
				
				XPath: /extremeWing-config/meshpoint[name=key1]/neighbor_inactivity_timeout"
			DEFVAL { 120 }
			::= { extremeWingCfgMcxMeshpointEntry 8 }

		
		-- 1.3.6.1.4.1.1916.2.131.50.1.3.35.1.1.9
		extremeWingCfgMcxMeshpointQosPolicy OBJECT-TYPE
			SYNTAX ExtremeWingIdentifier
			MAX-ACCESS read-write
			STATUS current
			DESCRIPTION
				"
				
				XPath: /extremeWing-config/meshpoint[name=key1]/qos_policy"
			::= { extremeWingCfgMcxMeshpointEntry 9 }

		
		-- 1.3.6.1.4.1.1916.2.131.50.1.3.35.1.1.10
		extremeWingCfgMcxMeshpointSecurityMode OBJECT-TYPE
			SYNTAX DisplayString
			MAX-ACCESS read-write
			STATUS current
			DESCRIPTION
				"
				
				Values:
				none;
				enum
				psk
				
				XPath: /extremeWing-config/meshpoint[name=key1]/security_mode"
			DEFVAL { "none" }
			::= { extremeWingCfgMcxMeshpointEntry 10 }

		
		-- 1.3.6.1.4.1.1916.2.131.50.1.3.35.1.1.11
		extremeWingCfgMcxMeshpointWpa2Psk OBJECT-TYPE
			SYNTAX DisplayString (SIZE (8..64))
			MAX-ACCESS read-write
			STATUS current
			DESCRIPTION
				"
				
				XPath: /extremeWing-config/meshpoint[name=key1]/wpa2_psk"
			::= { extremeWingCfgMcxMeshpointEntry 11 }

		
		-- 1.3.6.1.4.1.1916.2.131.50.1.3.35.1.1.12
		extremeWingCfgMcxMeshpointWpa2KeyRotationUnicast OBJECT-TYPE
			SYNTAX Unsigned32 (30..86400)
			UNITS "seconds"
			MAX-ACCESS read-write
			STATUS current
			DESCRIPTION
				"
				
				XPath: /extremeWing-config/meshpoint[name=key1]/wpa2_key_rotation_unicast"
			::= { extremeWingCfgMcxMeshpointEntry 12 }

		
		-- 1.3.6.1.4.1.1916.2.131.50.1.3.35.1.1.13
		extremeWingCfgMcxMeshpointWpa2KeyRotationBroadcast OBJECT-TYPE
			SYNTAX Unsigned32 (30..86400)
			UNITS "seconds"
			MAX-ACCESS read-write
			STATUS current
			DESCRIPTION
				"
				
				XPath: /extremeWing-config/meshpoint[name=key1]/wpa2_key_rotation_broadcast"
			::= { extremeWingCfgMcxMeshpointEntry 13 }

		
		-- 1.3.6.1.4.1.1916.2.131.50.1.3.35.1.1.14
		extremeWingCfgMcxMeshpointIsRoot OBJECT-TYPE
			SYNTAX TruthValue
			MAX-ACCESS read-write
			STATUS current
			DESCRIPTION
				"
				
				XPath: /extremeWing-config/meshpoint[name=key1]/is_root"
			DEFVAL { false }
			::= { extremeWingCfgMcxMeshpointEntry 14 }


		-- 1.3.6.1.4.1.1916.2.131.50.1.3.35.2
		extremeWingCfgMcxMeshpointQosTable OBJECT-TYPE
			SYNTAX SEQUENCE OF ExtremeWingCfgMcxMeshpointQosEntry
			MAX-ACCESS not-accessible
			STATUS current
			DESCRIPTION
				"
				
				/extremeWing-config/meshpoint"
			::= { extremeWingCfgMcx 2 }

		
		-- 1.3.6.1.4.1.1916.2.131.50.1.3.35.2.1
		extremeWingCfgMcxMeshpointQosEntry OBJECT-TYPE
			SYNTAX ExtremeWingCfgMcxMeshpointQosEntry
			MAX-ACCESS not-accessible
			STATUS current
			DESCRIPTION
				"An entry in the table."
			INDEX { extremeWingCfgMcxMeshpointName }
			::= { extremeWingCfgMcxMeshpointQosTable 1 }

		
		ExtremeWingCfgMcxMeshpointQosEntry ::=
			SEQUENCE { 
				extremeWingCfgMcxMeshpointQosName
					ExtremeWingIdentifier,
				extremeWingCfgMcxMeshpointQosMeshpointRlDownEnable
					TruthValue,
				extremeWingCfgMcxMeshpointQosMeshpointRlDownRate
					Unsigned32,
				extremeWingCfgMcxMeshpointQosMeshpointRlDownBurstSize
					Unsigned32,
				extremeWingCfgMcxMeshpointQosMeshpointRlDownThreshBackground
					Unsigned32,
				extremeWingCfgMcxMeshpointQosMeshpointRlDownThreshBestEffort
					Unsigned32,
				extremeWingCfgMcxMeshpointQosMeshpointRlDownThreshVoice
					Unsigned32,
				extremeWingCfgMcxMeshpointQosMeshpointRlDownThreshVideo
					Unsigned32,
				extremeWingCfgMcxMeshpointQosMeshpointRlUpEnable
					TruthValue,
				extremeWingCfgMcxMeshpointQosMeshpointRlUpRate
					Unsigned32,
				extremeWingCfgMcxMeshpointQosMeshpointRlUpBurstSize
					Unsigned32,
				extremeWingCfgMcxMeshpointQosMeshpointRlUpThreshBackground
					Unsigned32,
				extremeWingCfgMcxMeshpointQosMeshpointRlUpThreshBestEffort
					Unsigned32,
				extremeWingCfgMcxMeshpointQosMeshpointRlUpThreshVoice
					Unsigned32,
				extremeWingCfgMcxMeshpointQosMeshpointRlUpThreshVideo
					Unsigned32,
				extremeWingCfgMcxMeshpointQosNeighborRlDownEnable
					TruthValue,
				extremeWingCfgMcxMeshpointQosNeighborRlDownRate
					Unsigned32,
				extremeWingCfgMcxMeshpointQosNeighborRlDownBurstSize
					Unsigned32,
				extremeWingCfgMcxMeshpointQosNeighborRlDownThreshBackground
					Unsigned32,
				extremeWingCfgMcxMeshpointQosNeighborRlDownThreshBestEffort
					Unsigned32,
				extremeWingCfgMcxMeshpointQosNeighborRlDownThreshVoice
					Unsigned32,
				extremeWingCfgMcxMeshpointQosNeighborRlDownThreshVideo
					Unsigned32,
				extremeWingCfgMcxMeshpointQosNeighborRlUpEnable
					TruthValue,
				extremeWingCfgMcxMeshpointQosNeighborRlUpRate
					Unsigned32,
				extremeWingCfgMcxMeshpointQosNeighborRlUpBurstSize
					Unsigned32,
				extremeWingCfgMcxMeshpointQosNeighborRlUpThreshBackground
					Unsigned32,
				extremeWingCfgMcxMeshpointQosNeighborRlUpThreshBestEffort
					Unsigned32,
				extremeWingCfgMcxMeshpointQosNeighborRlUpThreshVoice
					Unsigned32,
				extremeWingCfgMcxMeshpointQosNeighborRlUpThreshVideo
					Unsigned32,
				extremeWingCfgMcxMeshpointQosAddr
					DisplayString,
				extremeWingCfgMcxMeshpointQosPriority
					DisplayString
			 }

		-- 1.3.6.1.4.1.1916.2.131.50.1.3.35.2.1.1
		extremeWingCfgMcxMeshpointQosName OBJECT-TYPE
			SYNTAX ExtremeWingIdentifier
			MAX-ACCESS read-write
			STATUS current
			DESCRIPTION
				"
				
				XPath: /extremeWing-config/meshpoint[name=key1]/name"
			::= { extremeWingCfgMcxMeshpointQosEntry 1 }

		
		-- 1.3.6.1.4.1.1916.2.131.50.1.3.35.2.1.3
		extremeWingCfgMcxMeshpointQosMeshpointRlDownEnable OBJECT-TYPE
			SYNTAX TruthValue
			MAX-ACCESS read-write
			STATUS current
			DESCRIPTION
				"Enable downstream (to air) traffic rate limiting on a MP.
				
				XPath: /extremeWing-config/meshpoint[name=key1]/meshpoint_rl_down_enable"
			DEFVAL { false }
			::= { extremeWingCfgMcxMeshpointQosEntry 3 }

		
		-- 1.3.6.1.4.1.1916.2.131.50.1.3.35.2.1.4
		extremeWingCfgMcxMeshpointQosMeshpointRlDownRate OBJECT-TYPE
			SYNTAX Unsigned32 (50..1000000)
			UNITS "kbps"
			MAX-ACCESS read-write
			STATUS current
			DESCRIPTION
				"Traffic rate for downstream (to air) rate limiting on a MP.
				
				XPath: /extremeWing-config/meshpoint[name=key1]/meshpoint_rl_down_rate"
			DEFVAL { 5000 }
			::= { extremeWingCfgMcxMeshpointQosEntry 4 }

		
		-- 1.3.6.1.4.1.1916.2.131.50.1.3.35.2.1.5
		extremeWingCfgMcxMeshpointQosMeshpointRlDownBurstSize OBJECT-TYPE
			SYNTAX Unsigned32 (2..1024)
			UNITS "kbytes"
			MAX-ACCESS read-write
			STATUS current
			DESCRIPTION
				"Maximum burst size for downstream (to air) rate limiting on a MP.
				
				XPath: /extremeWing-config/meshpoint[name=key1]/meshpoint_rl_down_burst_size"
			DEFVAL { 320 }
			::= { extremeWingCfgMcxMeshpointQosEntry 5 }

		
		-- 1.3.6.1.4.1.1916.2.131.50.1.3.35.2.1.6
		extremeWingCfgMcxMeshpointQosMeshpointRlDownThreshBackground OBJECT-TYPE
			SYNTAX Unsigned32 (0..100)
			UNITS "%"
			MAX-ACCESS read-write
			STATUS current
			DESCRIPTION
				"Random early detection threshold in % of Maximum burst size for low priority traffic (downstream, to air, rate limiting on a MP).
				
				XPath: /extremeWing-config/meshpoint[name=key1]/meshpoint_rl_down_thresh_background"
			DEFVAL { 50 }
			::= { extremeWingCfgMcxMeshpointQosEntry 6 }

		
		-- 1.3.6.1.4.1.1916.2.131.50.1.3.35.2.1.7
		extremeWingCfgMcxMeshpointQosMeshpointRlDownThreshBestEffort OBJECT-TYPE
			SYNTAX Unsigned32 (0..100)
			UNITS "%"
			MAX-ACCESS read-write
			STATUS current
			DESCRIPTION
				"Random early detection threshold in % of Maximum burst size for normal priority traffic (downstream, to air, rate limiting on a MP).
				
				XPath: /extremeWing-config/meshpoint[name=key1]/meshpoint_rl_down_thresh_best_effort"
			DEFVAL { 50 }
			::= { extremeWingCfgMcxMeshpointQosEntry 7 }

		
		-- 1.3.6.1.4.1.1916.2.131.50.1.3.35.2.1.8
		extremeWingCfgMcxMeshpointQosMeshpointRlDownThreshVoice OBJECT-TYPE
			SYNTAX Unsigned32 (0..100)
			UNITS "%"
			MAX-ACCESS read-write
			STATUS current
			DESCRIPTION
				"Random early detection threshold in % of Maximum burst size for voice traffic (downstream, to air, rate limiting on a MP).
				
				XPath: /extremeWing-config/meshpoint[name=key1]/meshpoint_rl_down_thresh_voice"
			DEFVAL { 0 }
			::= { extremeWingCfgMcxMeshpointQosEntry 8 }

		
		-- 1.3.6.1.4.1.1916.2.131.50.1.3.35.2.1.9
		extremeWingCfgMcxMeshpointQosMeshpointRlDownThreshVideo OBJECT-TYPE
			SYNTAX Unsigned32 (0..100)
			UNITS "%"
			MAX-ACCESS read-write
			STATUS current
			DESCRIPTION
				"Random early detection threshold in % of Maximum burst size for video traffic (downstream, to air, rate limiting on a MP).
				
				XPath: /extremeWing-config/meshpoint[name=key1]/meshpoint_rl_down_thresh_video"
			DEFVAL { 25 }
			::= { extremeWingCfgMcxMeshpointQosEntry 9 }

		
		-- 1.3.6.1.4.1.1916.2.131.50.1.3.35.2.1.10
		extremeWingCfgMcxMeshpointQosMeshpointRlUpEnable OBJECT-TYPE
			SYNTAX TruthValue
			MAX-ACCESS read-write
			STATUS current
			DESCRIPTION
				"Enable upstream (from air) traffic rate limiting on a MP.
				
				XPath: /extremeWing-config/meshpoint[name=key1]/meshpoint_rl_up_enable"
			DEFVAL { false }
			::= { extremeWingCfgMcxMeshpointQosEntry 10 }

		
		-- 1.3.6.1.4.1.1916.2.131.50.1.3.35.2.1.11
		extremeWingCfgMcxMeshpointQosMeshpointRlUpRate OBJECT-TYPE
			SYNTAX Unsigned32 (50..1000000)
			UNITS "kbps"
			MAX-ACCESS read-write
			STATUS current
			DESCRIPTION
				"Traffic rate for upstream (from air) rate limiting on a MP.
				
				XPath: /extremeWing-config/meshpoint[name=key1]/meshpoint_rl_up_rate"
			DEFVAL { 5000 }
			::= { extremeWingCfgMcxMeshpointQosEntry 11 }

		
		-- 1.3.6.1.4.1.1916.2.131.50.1.3.35.2.1.12
		extremeWingCfgMcxMeshpointQosMeshpointRlUpBurstSize OBJECT-TYPE
			SYNTAX Unsigned32 (2..1024)
			UNITS "kbytes"
			MAX-ACCESS read-write
			STATUS current
			DESCRIPTION
				"Maximum burst size for upstream (from air) rate limiting on a MP.
				
				XPath: /extremeWing-config/meshpoint[name=key1]/meshpoint_rl_up_burst_size"
			DEFVAL { 320 }
			::= { extremeWingCfgMcxMeshpointQosEntry 12 }

		
		-- 1.3.6.1.4.1.1916.2.131.50.1.3.35.2.1.13
		extremeWingCfgMcxMeshpointQosMeshpointRlUpThreshBackground OBJECT-TYPE
			SYNTAX Unsigned32 (0..100)
			UNITS "%"
			MAX-ACCESS read-write
			STATUS current
			DESCRIPTION
				"Random early detection threshold in % of Maximum burst size for low priority traffic (upstream, from air, rate limiting on a MP).
				
				XPath: /extremeWing-config/meshpoint[name=key1]/meshpoint_rl_up_thresh_background"
			DEFVAL { 50 }
			::= { extremeWingCfgMcxMeshpointQosEntry 13 }

		
		-- 1.3.6.1.4.1.1916.2.131.50.1.3.35.2.1.14
		extremeWingCfgMcxMeshpointQosMeshpointRlUpThreshBestEffort OBJECT-TYPE
			SYNTAX Unsigned32 (0..100)
			UNITS "%"
			MAX-ACCESS read-write
			STATUS current
			DESCRIPTION
				"Random early detection threshold in % of Maximum burst size for normal priority traffic (upstream, from air, rate limiting on a MP).
				
				XPath: /extremeWing-config/meshpoint[name=key1]/meshpoint_rl_up_thresh_best_effort"
			DEFVAL { 50 }
			::= { extremeWingCfgMcxMeshpointQosEntry 14 }

		
		-- 1.3.6.1.4.1.1916.2.131.50.1.3.35.2.1.15
		extremeWingCfgMcxMeshpointQosMeshpointRlUpThreshVoice OBJECT-TYPE
			SYNTAX Unsigned32 (0..100)
			UNITS "%"
			MAX-ACCESS read-write
			STATUS current
			DESCRIPTION
				"Random early detection threshold in % of Maximum burst size for voice traffic (upstream, from air, rate limiting on a MP).
				
				XPath: /extremeWing-config/meshpoint[name=key1]/meshpoint_rl_up_thresh_voice"
			DEFVAL { 0 }
			::= { extremeWingCfgMcxMeshpointQosEntry 15 }

		
		-- 1.3.6.1.4.1.1916.2.131.50.1.3.35.2.1.16
		extremeWingCfgMcxMeshpointQosMeshpointRlUpThreshVideo OBJECT-TYPE
			SYNTAX Unsigned32 (0..100)
			UNITS "%"
			MAX-ACCESS read-write
			STATUS current
			DESCRIPTION
				"Random early detection threshold in % of Maximum burst size for video traffic (upstream, from air, rate limiting on a MP).
				
				XPath: /extremeWing-config/meshpoint[name=key1]/meshpoint_rl_up_thresh_video"
			DEFVAL { 25 }
			::= { extremeWingCfgMcxMeshpointQosEntry 16 }

		
		-- 1.3.6.1.4.1.1916.2.131.50.1.3.35.2.1.17
		extremeWingCfgMcxMeshpointQosNeighborRlDownEnable OBJECT-TYPE
			SYNTAX TruthValue
			MAX-ACCESS read-write
			STATUS current
			DESCRIPTION
				"Enable downstream (to air) traffic rate limiting for Neighbors on a MP.
				
				XPath: /extremeWing-config/meshpoint[name=key1]/neighbor_rl_down_enable"
			DEFVAL { false }
			::= { extremeWingCfgMcxMeshpointQosEntry 17 }

		
		-- 1.3.6.1.4.1.1916.2.131.50.1.3.35.2.1.18
		extremeWingCfgMcxMeshpointQosNeighborRlDownRate OBJECT-TYPE
			SYNTAX Unsigned32 (50..1000000)
			UNITS "kbps"
			MAX-ACCESS read-write
			STATUS current
			DESCRIPTION
				"Traffic rate for downstream (to air) rate limiting for Neighbors on a MP.
				
				XPath: /extremeWing-config/meshpoint[name=key1]/neighbor_rl_down_rate"
			DEFVAL { 1000 }
			::= { extremeWingCfgMcxMeshpointQosEntry 18 }

		
		-- 1.3.6.1.4.1.1916.2.131.50.1.3.35.2.1.19
		extremeWingCfgMcxMeshpointQosNeighborRlDownBurstSize OBJECT-TYPE
			SYNTAX Unsigned32 (2..1024)
			UNITS "kbytes"
			MAX-ACCESS read-write
			STATUS current
			DESCRIPTION
				"Maximum burst size for downstream (to air) rate limiting for Neighbors on a MP.
				
				XPath: /extremeWing-config/meshpoint[name=key1]/neighbor_rl_down_burst_size"
			DEFVAL { 64 }
			::= { extremeWingCfgMcxMeshpointQosEntry 19 }

		
		-- 1.3.6.1.4.1.1916.2.131.50.1.3.35.2.1.20
		extremeWingCfgMcxMeshpointQosNeighborRlDownThreshBackground OBJECT-TYPE
			SYNTAX Unsigned32 (0..100)
			UNITS "%"
			MAX-ACCESS read-write
			STATUS current
			DESCRIPTION
				"Random early detection threshold in % of Maximum burst size for low priority traffic (downstream, to air, rate limiting for neighbors on a MP.
				
				XPath: /extremeWing-config/meshpoint[name=key1]/neighbor_rl_down_thresh_background"
			DEFVAL { 50 }
			::= { extremeWingCfgMcxMeshpointQosEntry 20 }

		
		-- 1.3.6.1.4.1.1916.2.131.50.1.3.35.2.1.21
		extremeWingCfgMcxMeshpointQosNeighborRlDownThreshBestEffort OBJECT-TYPE
			SYNTAX Unsigned32 (0..100)
			UNITS "%"
			MAX-ACCESS read-write
			STATUS current
			DESCRIPTION
				"Random early detection threshold in % of Maximum burst size for low priority traffic (downstream, to air, rate limiting for neighbors on a MP).
				
				XPath: /extremeWing-config/meshpoint[name=key1]/neighbor_rl_down_thresh_best_effort"
			DEFVAL { 50 }
			::= { extremeWingCfgMcxMeshpointQosEntry 21 }

		
		-- 1.3.6.1.4.1.1916.2.131.50.1.3.35.2.1.22
		extremeWingCfgMcxMeshpointQosNeighborRlDownThreshVoice OBJECT-TYPE
			SYNTAX Unsigned32 (0..100)
			UNITS "%"
			MAX-ACCESS read-write
			STATUS current
			DESCRIPTION
				"Random early detection threshold in % of Maximum burst size for voice traffic (downstream, to air, rate limiting for neighbors on a MP).
				
				XPath: /extremeWing-config/meshpoint[name=key1]/neighbor_rl_down_thresh_voice"
			DEFVAL { 0 }
			::= { extremeWingCfgMcxMeshpointQosEntry 22 }

		
		-- 1.3.6.1.4.1.1916.2.131.50.1.3.35.2.1.23
		extremeWingCfgMcxMeshpointQosNeighborRlDownThreshVideo OBJECT-TYPE
			SYNTAX Unsigned32 (0..100)
			UNITS "%"
			MAX-ACCESS read-write
			STATUS current
			DESCRIPTION
				"Random early detection threshold in % of Maximum burst size for video traffic (downstream, to air, rate limiting for neighbors on a MP).
				
				XPath: /extremeWing-config/meshpoint[name=key1]/neighbor_rl_down_thresh_video"
			DEFVAL { 25 }
			::= { extremeWingCfgMcxMeshpointQosEntry 23 }

		
		-- 1.3.6.1.4.1.1916.2.131.50.1.3.35.2.1.24
		extremeWingCfgMcxMeshpointQosNeighborRlUpEnable OBJECT-TYPE
			SYNTAX TruthValue
			MAX-ACCESS read-write
			STATUS current
			DESCRIPTION
				"Enable upstream (from air) traffic rate limiting for Neighbors on a MP.
				
				XPath: /extremeWing-config/meshpoint[name=key1]/neighbor_rl_up_enable"
			DEFVAL { false }
			::= { extremeWingCfgMcxMeshpointQosEntry 24 }

		
		-- 1.3.6.1.4.1.1916.2.131.50.1.3.35.2.1.25
		extremeWingCfgMcxMeshpointQosNeighborRlUpRate OBJECT-TYPE
			SYNTAX Unsigned32 (50..1000000)
			UNITS "kbps"
			MAX-ACCESS read-write
			STATUS current
			DESCRIPTION
				"Traffic rate for upstream (from air) rate limiting for Neighbors on a MP.
				
				XPath: /extremeWing-config/meshpoint[name=key1]/neighbor_rl_up_rate"
			DEFVAL { 1000 }
			::= { extremeWingCfgMcxMeshpointQosEntry 25 }

		
		-- 1.3.6.1.4.1.1916.2.131.50.1.3.35.2.1.26
		extremeWingCfgMcxMeshpointQosNeighborRlUpBurstSize OBJECT-TYPE
			SYNTAX Unsigned32 (2..1024)
			UNITS "kbytes"
			MAX-ACCESS read-write
			STATUS current
			DESCRIPTION
				"Maximum burst size for upstream (from air) rate limiting for Neighbors on a MP.
				
				XPath: /extremeWing-config/meshpoint[name=key1]/neighbor_rl_up_burst_size"
			DEFVAL { 64 }
			::= { extremeWingCfgMcxMeshpointQosEntry 26 }

		
		-- 1.3.6.1.4.1.1916.2.131.50.1.3.35.2.1.27
		extremeWingCfgMcxMeshpointQosNeighborRlUpThreshBackground OBJECT-TYPE
			SYNTAX Unsigned32 (0..100)
			UNITS "%"
			MAX-ACCESS read-write
			STATUS current
			DESCRIPTION
				"Random early detection threshold in % of Maximum burst size for low priority traffic (upstream, from air, rate limiting for neighbors on a MP).
				
				XPath: /extremeWing-config/meshpoint[name=key1]/neighbor_rl_up_thresh_background"
			DEFVAL { 50 }
			::= { extremeWingCfgMcxMeshpointQosEntry 27 }

		
		-- 1.3.6.1.4.1.1916.2.131.50.1.3.35.2.1.28
		extremeWingCfgMcxMeshpointQosNeighborRlUpThreshBestEffort OBJECT-TYPE
			SYNTAX Unsigned32 (0..100)
			UNITS "%"
			MAX-ACCESS read-write
			STATUS current
			DESCRIPTION
				"Random early detection threshold in % of Maximum burst size for normal priority traffic (upstream, from air, rate limiting for neighbors on a MP).
				
				XPath: /extremeWing-config/meshpoint[name=key1]/neighbor_rl_up_thresh_best_effort"
			DEFVAL { 50 }
			::= { extremeWingCfgMcxMeshpointQosEntry 28 }

		
		-- 1.3.6.1.4.1.1916.2.131.50.1.3.35.2.1.29
		extremeWingCfgMcxMeshpointQosNeighborRlUpThreshVoice OBJECT-TYPE
			SYNTAX Unsigned32 (0..100)
			UNITS "%"
			MAX-ACCESS read-write
			STATUS current
			DESCRIPTION
				"Random early detection threshold in % of Maximum burst size for voice traffic (upstream, from air, rate limiting for neighbors on a MP).
				
				XPath: /extremeWing-config/meshpoint[name=key1]/neighbor_rl_up_thresh_voice"
			DEFVAL { 0 }
			::= { extremeWingCfgMcxMeshpointQosEntry 29 }

		
		-- 1.3.6.1.4.1.1916.2.131.50.1.3.35.2.1.30
		extremeWingCfgMcxMeshpointQosNeighborRlUpThreshVideo OBJECT-TYPE
			SYNTAX Unsigned32 (0..100)
			UNITS "%"
			MAX-ACCESS read-write
			STATUS current
			DESCRIPTION
				"Random early detection threshold in % of Maximum burst size for video traffic (upstream, from air, rate limiting for neighbors on a MP).
				
				XPath: /extremeWing-config/meshpoint[name=key1]/neighbor_rl_up_thresh_video"
			DEFVAL { 25 }
			::= { extremeWingCfgMcxMeshpointQosEntry 30 }

		
		-- 1.3.6.1.4.1.1916.2.131.50.1.3.35.2.1.31
		extremeWingCfgMcxMeshpointQosAddr OBJECT-TYPE
			SYNTAX DisplayString
			MAX-ACCESS read-write
			STATUS current
			DESCRIPTION
				"Multicast IP address of the traffic stream that should be selected for accelerated delivery
				
				XPath: /extremeWing-config/meshpoint[name=key1]/addr"
			::= { extremeWingCfgMcxMeshpointQosEntry 31 }

		
		-- 1.3.6.1.4.1.1916.2.131.50.1.3.35.2.1.32
		extremeWingCfgMcxMeshpointQosPriority OBJECT-TYPE
			SYNTAX DisplayString
			MAX-ACCESS read-write
			STATUS current
			DESCRIPTION
				"The forwarding qos classification (traffic class)
				
				Values:
				trust,
				voice,
				video,
				best-effort,
				background
				
				XPath: /extremeWing-config/meshpoint[name=key1]/priority"
			DEFVAL { "trust" }
			::= { extremeWingCfgMcxMeshpointQosEntry 32 }

	
		-- 1.3.6.1.4.1.1916.2.131.50.1.3.36
		extremeWingCfgRadiusUser OBJECT IDENTIFIER ::= { extremeWingConfig 36 }

		
		-- 1.3.6.1.4.1.1916.2.131.50.1.3.36.1
		extremeWingCfgRadiusUserPolicyTable OBJECT-TYPE
			SYNTAX SEQUENCE OF ExtremeWingCfgRadiusUserPolicyEntry
			MAX-ACCESS not-accessible
			STATUS current
			DESCRIPTION
				"Description."
			::= { extremeWingCfgRadiusUser 1 }

		
		-- 1.3.6.1.4.1.1916.2.131.50.1.3.36.1.1
		extremeWingCfgRadiusUserPolicyEntry OBJECT-TYPE
			SYNTAX ExtremeWingCfgRadiusUserPolicyEntry
			MAX-ACCESS not-accessible
			STATUS current
			DESCRIPTION
				"Description."
			INDEX { extremeWingCfgRadiusUserPolicyName }
			::= { extremeWingCfgRadiusUserPolicyTable 1 }

		
		ExtremeWingCfgRadiusUserPolicyEntry ::=
			SEQUENCE { 
				extremeWingCfgRadiusUserPolicyName
					ExtremeWingIdentifier,
				extremeWingCfgRadiusUserPolicyRowStatus
					RowStatus
			 }

		-- 1.3.6.1.4.1.1916.2.131.50.1.3.36.1.1.1
		extremeWingCfgRadiusUserPolicyName OBJECT-TYPE
			SYNTAX ExtremeWingIdentifier
			MAX-ACCESS read-only
			STATUS current
			DESCRIPTION
				"
				XPATH: /extremeWing-config/radius_user_pool[name=key1]/name"
			::= { extremeWingCfgRadiusUserPolicyEntry 1 }

		
		-- 1.3.6.1.4.1.1916.2.131.50.1.3.36.1.1.2
		extremeWingCfgRadiusUserPolicyRowStatus OBJECT-TYPE
			SYNTAX RowStatus
				{
				active(1),
				createAndGo(4),
				destroy(6)
				}
			MAX-ACCESS read-write
			STATUS current
			DESCRIPTION
				"The status of this conceptual row
				XPATH: /extremeWing-config/radius_user_pool[name=key1]/row_status"
			::= { extremeWingCfgRadiusUserPolicyEntry 2 }

		
		-- 1.3.6.1.4.1.1916.2.131.50.1.3.36.2
		extremeWingCfgRadiusUserTable OBJECT-TYPE
			SYNTAX SEQUENCE OF ExtremeWingCfgRadiusUserEntry
			MAX-ACCESS not-accessible
			STATUS current
			DESCRIPTION
				"Description."
			::= { extremeWingCfgRadiusUser 2 }

		
		-- 1.3.6.1.4.1.1916.2.131.50.1.3.36.2.1
		extremeWingCfgRadiusUserEntry OBJECT-TYPE
			SYNTAX ExtremeWingCfgRadiusUserEntry
			MAX-ACCESS not-accessible
			STATUS current
			DESCRIPTION
				"Description."
			INDEX { extremeWingCfgRadiusUserPolicyName, extremeWingCfgRadiusUserName }
			::= { extremeWingCfgRadiusUserTable 1 }

		
		ExtremeWingCfgRadiusUserEntry ::=
			SEQUENCE { 
				extremeWingCfgRadiusUserName
					DisplayString,
				extremeWingCfgRadiusUserRowStatus
					RowStatus,
				extremeWingCfgRadiusUserPassword
					DisplayString,
				extremeWingCfgRadiusUserIsGuest
					TruthValue,
				extremeWingCfgRadiusUserGroupList
					DisplayString,
				extremeWingCfgRadiusUserGroup
					DisplayString,
				extremeWingCfgRadiusUserStartDate
					DisplayString,
				extremeWingCfgRadiusUserStartTime
					DisplayString,
				extremeWingCfgRadiusUserExpiryDate
					DisplayString,
				extremeWingCfgRadiusUserExpiryTime
					DisplayString,
				extremeWingCfgRadiusUserEmailId
					DisplayString,
				extremeWingCfgRadiusUserTelephone
					DisplayString
			 }

		-- 1.3.6.1.4.1.1916.2.131.50.1.3.36.2.1.1
		extremeWingCfgRadiusUserName OBJECT-TYPE
			SYNTAX DisplayString (SIZE (1..64))
			MAX-ACCESS read-write
			STATUS current
			DESCRIPTION
				"The User ID that uniquely identifies this user.
				XPATH: /extremeWing-config/radius_user_pool[name=key1]/users[userid=key2]/userid"
			::= { extremeWingCfgRadiusUserEntry 1 }

		
		-- 1.3.6.1.4.1.1916.2.131.50.1.3.36.2.1.2
		extremeWingCfgRadiusUserRowStatus OBJECT-TYPE
			SYNTAX RowStatus
				{
				active(1),
				createAndGo(4),
				destroy(6)
				}
			MAX-ACCESS read-write
			STATUS current
			DESCRIPTION
				"The status of this conceptual row.
				XPATH: /extremeWing-config/radius_user_pool[name=key1]/users[userid=key2]/row_status"
			::= { extremeWingCfgRadiusUserEntry 2 }

		
		-- 1.3.6.1.4.1.1916.2.131.50.1.3.36.2.1.3
		extremeWingCfgRadiusUserPassword OBJECT-TYPE
			SYNTAX DisplayString (SIZE (1..32))
			MAX-ACCESS read-write
			STATUS current
			DESCRIPTION
				"The password for this user.
				XPATH:  /extremeWing-config/radius_user_pool[name=key1]/users[userid=key2]/password"
			::= { extremeWingCfgRadiusUserEntry 3 }

		
		-- 1.3.6.1.4.1.1916.2.131.50.1.3.36.2.1.4
		extremeWingCfgRadiusUserIsGuest OBJECT-TYPE
			SYNTAX TruthValue
			MAX-ACCESS read-write
			STATUS current
			DESCRIPTION
				"Specify whether this is a guest user or normal user. 
				Marking a user as guest will let you specify additional restrictions for the user like 'start' and 
				'expiry' date/time.
				XPATH: /extremeWing-config/radius_user_pool[name=key1]/users[userid=key2]/is_guest"
			DEFVAL { false }
			::= { extremeWingCfgRadiusUserEntry 4 }

		
		-- 1.3.6.1.4.1.1916.2.131.50.1.3.36.2.1.5
		extremeWingCfgRadiusUserGroupList OBJECT-TYPE
			SYNTAX DisplayString
			MAX-ACCESS read-write
			STATUS current
			DESCRIPTION
				"The group-list for user.
				XPATH: /extremeWing-config/radius_user_pool[name=key1]/users[userid=key2]/group_list "
			::= { extremeWingCfgRadiusUserEntry 5 }

		
		-- 1.3.6.1.4.1.1916.2.131.50.1.3.36.2.1.6
		extremeWingCfgRadiusUserGroup OBJECT-TYPE
			SYNTAX DisplayString
			MAX-ACCESS read-write
			STATUS current
			DESCRIPTION
				"The group for guest user.
				XPATH: /extremeWing-config/radius_user_pool[name=key1]/users[userid=key2]/group"
			::= { extremeWingCfgRadiusUserEntry 6 }

		
		-- 1.3.6.1.4.1.1916.2.131.50.1.3.36.2.1.7
		extremeWingCfgRadiusUserStartDate OBJECT-TYPE
			SYNTAX DisplayString
			MAX-ACCESS read-write
			STATUS current
			DESCRIPTION
				"Specify a start date (MM:DD:YYYY) after which the user will be able to authenticate. 
				This constraint is applicable only for 'guest' users.
				XPATH: /extremeWing-config/radius_user_pool[name=key1]/users[userid=key2]/start_date"
			::= { extremeWingCfgRadiusUserEntry 7 }

		
		-- 1.3.6.1.4.1.1916.2.131.50.1.3.36.2.1.8
		extremeWingCfgRadiusUserStartTime OBJECT-TYPE
			SYNTAX DisplayString
			MAX-ACCESS read-write
			STATUS current
			DESCRIPTION
				"Specify a start time (HH:MM) for the start date after which the user will be able to authenticate. 
				This constraint is applicable only for 'guest' users.
				XPATH: /extremeWing-config/radius_user_pool[name=key1]/users[userid=key2]/start_time"
			::= { extremeWingCfgRadiusUserEntry 8 }

		
		-- 1.3.6.1.4.1.1916.2.131.50.1.3.36.2.1.9
		extremeWingCfgRadiusUserExpiryDate OBJECT-TYPE
			SYNTAX DisplayString
			MAX-ACCESS read-write
			STATUS current
			DESCRIPTION
				"Specify an expiry date (MM:DD:YYYY) after which the user will not be able to authenticate. 
				This constraint is applicable only for 'guest' users.
				XPATH: /extremeWing-config/radius_user_pool[name=key1]/users[userid=key2]/expiry_date"
			::= { extremeWingCfgRadiusUserEntry 9 }

		
		-- 1.3.6.1.4.1.1916.2.131.50.1.3.36.2.1.10
		extremeWingCfgRadiusUserExpiryTime OBJECT-TYPE
			SYNTAX DisplayString
			MAX-ACCESS read-write
			STATUS current
			DESCRIPTION
				"Specify an expiry time (HH:MM) for expiry date after which the user will not be able to authenticate. 
				This constraint is applicable only for 'guest' users.
				XPATH: /extremeWing-config/radius_user_pool[name=key1]/users[userid=key2]/expiry_time"
			::= { extremeWingCfgRadiusUserEntry 10 }

		
		-- 1.3.6.1.4.1.1916.2.131.50.1.3.36.2.1.11
		extremeWingCfgRadiusUserEmailId OBJECT-TYPE
			SYNTAX DisplayString (SIZE (0..64))
			MAX-ACCESS read-write
			STATUS current
			DESCRIPTION
				"Specify the email-id of the user
				XPATH: /extremeWing-config/radius_user_pool[name=key1]/users[userid=key2]/email_id"
			::= { extremeWingCfgRadiusUserEntry 11 }

		
		-- 1.3.6.1.4.1.1916.2.131.50.1.3.36.2.1.12
		extremeWingCfgRadiusUserTelephone OBJECT-TYPE
			SYNTAX DisplayString (SIZE (0..12))
			MAX-ACCESS read-write
			STATUS current
			DESCRIPTION
				"Specify the telephone number of the user
				XPATH: /extremeWing-config/radius_user_pool[name=key1]/users[userid=key2]/telephone"
			::= { extremeWingCfgRadiusUserEntry 12 }


	
		-- 1.3.6.1.4.1.1916.2.131.50.1.4
		extremeWingStats OBJECT IDENTIFIER ::= { extremeWingObjects 4 }

		
-- /extremeWing-stats/noc
		-- 1.3.6.1.4.1.1916.2.131.50.1.4.1
		extremeWingStatsNoc OBJECT IDENTIFIER ::= { extremeWingStats 1 }
		
		-- 1.3.6.1.4.1.1916.2.131.50.1.4.1.2
		extremeWingStatsNocDevTable OBJECT-TYPE
			SYNTAX SEQUENCE OF ExtremeWingStatsNocDevEntry
			MAX-ACCESS not-accessible
			STATUS current
			DESCRIPTION
				"
				
				/extremeWing-stats/noc/device-list"
			::= { extremeWingStatsNoc 2 }

		
		-- 1.3.6.1.4.1.1916.2.131.50.1.4.1.2.1
		extremeWingStatsNocDevEntry OBJECT-TYPE
			SYNTAX ExtremeWingStatsNocDevEntry
			MAX-ACCESS not-accessible
			STATUS current
			DESCRIPTION
				"An entry in the table."
			INDEX { extremeWingStatsNocDevMac }
			::= { extremeWingStatsNocDevTable 1 }

		
		ExtremeWingStatsNocDevEntry ::=
			SEQUENCE { 
				extremeWingStatsNocDevMac
					MacAddress,
				extremeWingStatsNocDevHostname
					DisplayString,
				extremeWingStatsNocDevType
					DisplayString,
				extremeWingStatsNocDevClusterName
					DisplayString,
				extremeWingStatsNocDevRfDomainName
					DisplayString,
				extremeWingStatsNocDevAdoptedBy
					DisplayString,
				extremeWingStatsNocDevOnline
					TruthValue,
				extremeWingStatsNocDevReporter
					MacAddress,
				extremeWingStatsNocDevLastUpdate
					Unsigned32,
				extremeWingStatsNocDevHasRadio
					TruthValue,
				extremeWingStatsNocDevIsController
					TruthValue,
				extremeWingStatsNocDevProfileName
					DisplayString,
				extremeWingStatsNocDevProductName
					DisplayString,
				extremeWingStatsNocDevVersion
					DisplayString,
				extremeWingStatsNocDevSerialNumber
					DisplayString
			 }

		-- 1.3.6.1.4.1.1916.2.131.50.1.4.1.2.1.1
		extremeWingStatsNocDevMac OBJECT-TYPE
			SYNTAX MacAddress
			MAX-ACCESS read-only
			STATUS current
			DESCRIPTION
				"Device mac address
				
				XPath: /extremeWing-stats/noc/device-list[mac=key1]/mac"
			::= { extremeWingStatsNocDevEntry 1 }

		
		-- 1.3.6.1.4.1.1916.2.131.50.1.4.1.2.1.2
		extremeWingStatsNocDevHostname OBJECT-TYPE
			SYNTAX DisplayString (SIZE (64))
			MAX-ACCESS read-only
			STATUS current
			DESCRIPTION
				"
				
				XPath: /extremeWing-stats/noc/device-list[mac=key1]/hostname"
			::= { extremeWingStatsNocDevEntry 2 }

		
		-- 1.3.6.1.4.1.1916.2.131.50.1.4.1.2.1.3
		extremeWingStatsNocDevType OBJECT-TYPE
			SYNTAX DisplayString
			MAX-ACCESS read-only
			STATUS current
			DESCRIPTION
				"Device type
				
				XPath: /extremeWing-stats/noc/device-list[mac=key1]/type"
			::= { extremeWingStatsNocDevEntry 3 }

		
		-- 1.3.6.1.4.1.1916.2.131.50.1.4.1.2.1.4
		extremeWingStatsNocDevClusterName OBJECT-TYPE
			SYNTAX DisplayString (SIZE (64))
			MAX-ACCESS read-only
			STATUS current
			DESCRIPTION
				"Name of the cluster this device belongs to,
				applicable to switch device
				
				XPath: /extremeWing-stats/noc/device-list[mac=key1]/cluster_name"
			::= { extremeWingStatsNocDevEntry 4 }

		
		-- 1.3.6.1.4.1.1916.2.131.50.1.4.1.2.1.5
		extremeWingStatsNocDevRfDomainName OBJECT-TYPE
			SYNTAX DisplayString (SIZE (64))
			MAX-ACCESS read-only
			STATUS current
			DESCRIPTION
				"Rf-domain that this device currently resides in
				
				XPath: /extremeWing-stats/noc/device-list[mac=key1]/rf_domain_name"
			::= { extremeWingStatsNocDevEntry 5 }

		
		-- 1.3.6.1.4.1.1916.2.131.50.1.4.1.2.1.6
		extremeWingStatsNocDevAdoptedBy OBJECT-TYPE
			SYNTAX DisplayString (SIZE (64))
			MAX-ACCESS read-only
			STATUS current
			DESCRIPTION
				"Mac address of parent switch that adopts this device (AP)
				
				XPath: /extremeWing-stats/noc/device-list[mac=key1]/adopted_by"
			::= { extremeWingStatsNocDevEntry 6 }

		
		-- 1.3.6.1.4.1.1916.2.131.50.1.4.1.2.1.7
		extremeWingStatsNocDevOnline OBJECT-TYPE
			SYNTAX TruthValue
			MAX-ACCESS read-only
			STATUS current
			DESCRIPTION
				"
				
				XPath: /extremeWing-stats/noc/device-list[mac=key1]/online"
			::= { extremeWingStatsNocDevEntry 7 }

		
		-- 1.3.6.1.4.1.1916.2.131.50.1.4.1.2.1.8
		extremeWingStatsNocDevReporter OBJECT-TYPE
			SYNTAX MacAddress
			MAX-ACCESS read-only
			STATUS current
			DESCRIPTION
				"Device mac address of the reporting controller
				
				XPath: /extremeWing-stats/noc/device-list[mac=key1]/reporter"
			::= { extremeWingStatsNocDevEntry 8 }

		
		-- 1.3.6.1.4.1.1916.2.131.50.1.4.1.2.1.9
		extremeWingStatsNocDevLastUpdate OBJECT-TYPE
			SYNTAX Unsigned32
			MAX-ACCESS read-only
			STATUS current
			DESCRIPTION
				"The last UTC timestamp from the originating rf-domain manager
				
				XPath: /extremeWing-stats/noc/device-list[mac=key1]/last_update"
			::= { extremeWingStatsNocDevEntry 9 }

		
		-- 1.3.6.1.4.1.1916.2.131.50.1.4.1.2.1.10
		extremeWingStatsNocDevHasRadio OBJECT-TYPE
			SYNTAX TruthValue
			MAX-ACCESS read-only
			STATUS current
			DESCRIPTION
				"Whether the device has wireless radio that can
				service clients
				
				XPath: /extremeWing-stats/noc/device-list[mac=key1]/has_radio"
			::= { extremeWingStatsNocDevEntry 10 }

		
		-- 1.3.6.1.4.1.1916.2.131.50.1.4.1.2.1.11
		extremeWingStatsNocDevIsController OBJECT-TYPE
			SYNTAX TruthValue
			MAX-ACCESS read-only
			STATUS current
			DESCRIPTION
				"Whether the device is a controller device
				
				XPath: /extremeWing-stats/noc/device-list[mac=key1]/is_controller"
			::= { extremeWingStatsNocDevEntry 11 }

		
		-- 1.3.6.1.4.1.1916.2.131.50.1.4.1.2.1.12
		extremeWingStatsNocDevProfileName OBJECT-TYPE
			SYNTAX DisplayString (SIZE (64))
			MAX-ACCESS read-only
			STATUS current
			DESCRIPTION
				"Profile name that this device is using
				
				XPath: /extremeWing-stats/noc/device-list[mac=key1]/profile_name"
			::= { extremeWingStatsNocDevEntry 12 }


		-- 1.3.6.1.4.1.1916.2.131.50.1.4.1.2.1.15
		extremeWingStatsNocDevProductName OBJECT-TYPE
			SYNTAX DisplayString (SIZE (0..32))
			MAX-ACCESS read-only
			STATUS current
			DESCRIPTION
				"Product name string
				
				XPath: /extremeWing-stats/noc/device-list[mac=key1]/product_name"
			::= { extremeWingStatsNocDevEntry 15 }


		-- 1.3.6.1.4.1.1916.2.131.50.1.4.1.2.1.16
		extremeWingStatsNocDevVersion OBJECT-TYPE
			SYNTAX DisplayString
			MAX-ACCESS read-only
			STATUS current
			DESCRIPTION
				"Device software version
				
				XPath: /extremeWing-stats/noc/device-list[mac=key1]/version"
			::= { extremeWingStatsNocDevEntry 16 }


		-- 1.3.6.1.4.1.1916.2.131.50.1.4.1.2.1.17
		extremeWingStatsNocDevSerialNumber OBJECT-TYPE
			SYNTAX DisplayString
			MAX-ACCESS read-only
			STATUS current
			DESCRIPTION
				"Device serial number
				
				XPath: /extremeWing-stats/noc/device-list[mac=key1]/serial_number"
			::= { extremeWingStatsNocDevEntry 17 }

		
-- /extremeWing-stats/noc/adoption
		-- 1.3.6.1.4.1.1916.2.131.50.1.4.1.9
		extremeWingStatsNocAdopt OBJECT IDENTIFIER ::= { extremeWingStatsNoc 9 }

		
		-- 1.3.6.1.4.1.1916.2.131.50.1.4.1.9.1
		extremeWingStatsNocAdoptDevTable OBJECT-TYPE
			SYNTAX SEQUENCE OF ExtremeWingStatsNocAdoptDevEntry
			MAX-ACCESS not-accessible
			STATUS current
			DESCRIPTION
				"Status of currently adopted devices.
				
				/extremeWing-stats/noc/adoption/adopted_device"
			::= { extremeWingStatsNocAdopt 1 }

		
		-- 1.3.6.1.4.1.1916.2.131.50.1.4.1.9.1.1
		extremeWingStatsNocAdoptDevEntry OBJECT-TYPE
			SYNTAX ExtremeWingStatsNocAdoptDevEntry
			MAX-ACCESS not-accessible
			STATUS current
			DESCRIPTION
				"An entry in the table."
			INDEX { extremeWingStatsNocAdoptDevMac }
			::= { extremeWingStatsNocAdoptDevTable 1 }

		
		ExtremeWingStatsNocAdoptDevEntry ::=
			SEQUENCE { 
				extremeWingStatsNocAdoptDevMac
					MacAddress,
				extremeWingStatsNocAdoptDevType
					DisplayString,
				extremeWingStatsNocAdoptDevHostname
					DisplayString,
				extremeWingStatsNocAdoptDevVersion
					DisplayString,
				extremeWingStatsNocAdoptDevSerialNo
					DisplayString,
				extremeWingStatsNocAdoptDevRfDomainName
					DisplayString,
				extremeWingStatsNocAdoptDevOnline
					TruthValue,
				extremeWingStatsNocAdoptDevBy
					MacAddress,
				extremeWingStatsNocAdoptDevLastAdoption
					Unsigned32,
				extremeWingStatsNocAdoptDevModelNumber
					DisplayString,
				extremeWingStatsNocAdoptDevStartup
					Unsigned32,
				extremeWingStatsNocAdoptDevCfgStatus
					DisplayString,
				extremeWingStatsNocAdoptDevProductName
					DisplayString
			 }

		-- 1.3.6.1.4.1.1916.2.131.50.1.4.1.9.1.1.1
		extremeWingStatsNocAdoptDevMac OBJECT-TYPE
			SYNTAX MacAddress
			MAX-ACCESS read-only
			STATUS current
			DESCRIPTION
				"Device MAC
				
				XPath: /extremeWing-stats/noc/adoption/adopted_device[mac=key1]/mac"
			::= { extremeWingStatsNocAdoptDevEntry 1 }

		
		-- 1.3.6.1.4.1.1916.2.131.50.1.4.1.9.1.1.2
		extremeWingStatsNocAdoptDevType OBJECT-TYPE
			SYNTAX DisplayString
			MAX-ACCESS read-only
			STATUS current
			DESCRIPTION
				"Device type
				
				XPath: /extremeWing-stats/noc/adoption/adopted_device[mac=key1]/type"
			::= { extremeWingStatsNocAdoptDevEntry 2 }

		
		-- 1.3.6.1.4.1.1916.2.131.50.1.4.1.9.1.1.3
		extremeWingStatsNocAdoptDevHostname OBJECT-TYPE
			SYNTAX DisplayString
			MAX-ACCESS read-only
			STATUS current
			DESCRIPTION
				"Device hostname
				
				XPath: /extremeWing-stats/noc/adoption/adopted_device[mac=key1]/hostname"
			::= { extremeWingStatsNocAdoptDevEntry 3 }

		
		-- 1.3.6.1.4.1.1916.2.131.50.1.4.1.9.1.1.4
		extremeWingStatsNocAdoptDevVersion OBJECT-TYPE
			SYNTAX DisplayString
			MAX-ACCESS read-only
			STATUS current
			DESCRIPTION
				"Device software version
				
				XPath: /extremeWing-stats/noc/adoption/adopted_device[mac=key1]/version"
			::= { extremeWingStatsNocAdoptDevEntry 4 }

		
		-- 1.3.6.1.4.1.1916.2.131.50.1.4.1.9.1.1.5
		extremeWingStatsNocAdoptDevSerialNo OBJECT-TYPE
			SYNTAX DisplayString
			MAX-ACCESS read-only
			STATUS current
			DESCRIPTION
				"Device serial number
				
				XPath: /extremeWing-stats/noc/adoption/adopted_device[mac=key1]/serial-no"
			::= { extremeWingStatsNocAdoptDevEntry 5 }

		
		-- 1.3.6.1.4.1.1916.2.131.50.1.4.1.9.1.1.6
		extremeWingStatsNocAdoptDevRfDomainName OBJECT-TYPE
			SYNTAX DisplayString
			MAX-ACCESS read-only
			STATUS current
			DESCRIPTION
				"Device RF Domain name
				
				XPath: /extremeWing-stats/noc/adoption/adopted_device[mac=key1]/rf_domain_name"
			::= { extremeWingStatsNocAdoptDevEntry 6 }

		
		-- 1.3.6.1.4.1.1916.2.131.50.1.4.1.9.1.1.7
		extremeWingStatsNocAdoptDevOnline OBJECT-TYPE
			SYNTAX TruthValue
			MAX-ACCESS read-only
			STATUS current
			DESCRIPTION
				"Device online status
				
				XPath: /extremeWing-stats/noc/adoption/adopted_device[mac=key1]/online"
			::= { extremeWingStatsNocAdoptDevEntry 7 }

		
		-- 1.3.6.1.4.1.1916.2.131.50.1.4.1.9.1.1.8
		extremeWingStatsNocAdoptDevBy OBJECT-TYPE
			SYNTAX MacAddress
			MAX-ACCESS read-only
			STATUS current
			DESCRIPTION
				"MAC address of the adopting device.
				
				XPath: /extremeWing-stats/noc/adoption/adopted_device[mac=key1]/adopted_by"
			::= { extremeWingStatsNocAdoptDevEntry 8 }

		
		-- 1.3.6.1.4.1.1916.2.131.50.1.4.1.9.1.1.9
		extremeWingStatsNocAdoptDevLastAdoption OBJECT-TYPE
			SYNTAX Unsigned32
			MAX-ACCESS read-only
			STATUS current
			DESCRIPTION
				"UTC timestamp of the last adoption.
				
				XPath: /extremeWing-stats/noc/adoption/adopted_device[mac=key1]/last_adoption"
			::= { extremeWingStatsNocAdoptDevEntry 9 }

		
		-- 1.3.6.1.4.1.1916.2.131.50.1.4.1.9.1.1.10
		extremeWingStatsNocAdoptDevModelNumber OBJECT-TYPE
			SYNTAX DisplayString
			MAX-ACCESS read-only
			STATUS current
			DESCRIPTION
				"Device model number.
				
				XPath: /extremeWing-stats/noc/adoption/adopted_device[mac=key1]/model_number"
			::= { extremeWingStatsNocAdoptDevEntry 10 }

		
		-- 1.3.6.1.4.1.1916.2.131.50.1.4.1.9.1.1.11
		extremeWingStatsNocAdoptDevStartup OBJECT-TYPE
			SYNTAX Unsigned32
			MAX-ACCESS read-only
			STATUS current
			DESCRIPTION
				"UTC timestamp of device startup. The value 0 indicates that
				the timestamp is not available.
				
				XPath: /extremeWing-stats/noc/adoption/adopted_device[mac=key1]/startup"
			::= { extremeWingStatsNocAdoptDevEntry 11 }

		
		-- 1.3.6.1.4.1.1916.2.131.50.1.4.1.9.1.1.12
		extremeWingStatsNocAdoptDevCfgStatus OBJECT-TYPE
			SYNTAX DisplayString
			MAX-ACCESS read-only
			STATUS current
			DESCRIPTION
				"The configuration status of the device, e.g., pending.
				
				XPath: /extremeWing-stats/noc/adoption/adopted_device[mac=key1]/cfg_status"
			::= { extremeWingStatsNocAdoptDevEntry 12 }

		
		-- 1.3.6.1.4.1.1916.2.131.50.1.4.1.9.1.1.13
		extremeWingStatsNocAdoptDevProductName OBJECT-TYPE
			SYNTAX DisplayString (SIZE (0..32))
			MAX-ACCESS read-only
			STATUS current
			DESCRIPTION
				"Product name string
				
				XPath: /extremeWing-stats/noc/adoption/adopted_device[mac=key1]/product-name"
			::= { extremeWingStatsNocAdoptDevEntry 13 }

		
		-- 1.3.6.1.4.1.1916.2.131.50.1.4.1.9.2
		extremeWingStatsNocAdoptPendingDevTable OBJECT-TYPE
			SYNTAX SEQUENCE OF ExtremeWingStatsNocAdoptPendingDevEntry
			MAX-ACCESS not-accessible
			STATUS current
			DESCRIPTION
				"Status of devices not adopted.
				
				Xpath: /extremeWing-stats/noc/adoption/pending_device"
			::= { extremeWingStatsNocAdopt 2 }

		
		-- 1.3.6.1.4.1.1916.2.131.50.1.4.1.9.2.1
		extremeWingStatsNocAdoptPendingDevEntry OBJECT-TYPE
			SYNTAX ExtremeWingStatsNocAdoptPendingDevEntry
			MAX-ACCESS not-accessible
			STATUS current
			DESCRIPTION
				"An entry in the table."
			INDEX { extremeWingStatsNocAdoptPendingDevMac }
			::= { extremeWingStatsNocAdoptPendingDevTable 1 }

		
		ExtremeWingStatsNocAdoptPendingDevEntry ::=
			SEQUENCE { 
				extremeWingStatsNocAdoptPendingDevMac
					MacAddress,
				extremeWingStatsNocAdoptPendingDevType
					DisplayString,
				extremeWingStatsNocAdoptPendingDevTarget
					DisplayString,
				extremeWingStatsNocAdoptPendingDevDisOption
					DisplayString,
				extremeWingStatsNocAdoptPendingDevVersion
					DisplayString,
				extremeWingStatsNocAdoptPendingDevSerialNumber
					DisplayString,
				extremeWingStatsNocAdoptPendingDevReason
					DisplayString,
				extremeWingStatsNocAdoptPendingDevNumRadios
					Unsigned32,
				extremeWingStatsNocAdoptPendingDevIp
					DisplayString,
				extremeWingStatsNocAdoptPendingDevVlan
					Unsigned32
			 }

		-- 1.3.6.1.4.1.1916.2.131.50.1.4.1.9.2.1.1
		extremeWingStatsNocAdoptPendingDevMac OBJECT-TYPE
			SYNTAX MacAddress
			MAX-ACCESS read-only
			STATUS current
			DESCRIPTION
				"Device MAC
				
				XPath: /extremeWing-stats/noc/adoption/pending_device[mac=key1]/mac"
			::= { extremeWingStatsNocAdoptPendingDevEntry 1 }

		
		-- 1.3.6.1.4.1.1916.2.131.50.1.4.1.9.2.1.2
		extremeWingStatsNocAdoptPendingDevType OBJECT-TYPE
			SYNTAX DisplayString
			MAX-ACCESS read-only
			STATUS current
			DESCRIPTION
				"Device type
				
				XPath: /extremeWing-stats/noc/adoption/pending_device[mac=key1]/type"
			::= { extremeWingStatsNocAdoptPendingDevEntry 2 }

		
		-- 1.3.6.1.4.1.1916.2.131.50.1.4.1.9.2.1.3
		extremeWingStatsNocAdoptPendingDevTarget OBJECT-TYPE
			SYNTAX DisplayString
			MAX-ACCESS read-only
			STATUS current
			DESCRIPTION
				"Target information for the Device.
				
				XPath: /extremeWing-stats/noc/adoption/pending_device[mac=key1]/target"
			::= { extremeWingStatsNocAdoptPendingDevEntry 3 }

		
		-- 1.3.6.1.4.1.1916.2.131.50.1.4.1.9.2.1.4
		extremeWingStatsNocAdoptPendingDevDisOption OBJECT-TYPE
			SYNTAX DisplayString
			MAX-ACCESS read-only
			STATUS current
			DESCRIPTION
				"Discovery option provided by the device.
				
				XPath: /extremeWing-stats/noc/adoption/pending_device[mac=key1]/dis_option"
			::= { extremeWingStatsNocAdoptPendingDevEntry 4 }

		
		-- 1.3.6.1.4.1.1916.2.131.50.1.4.1.9.2.1.5
		extremeWingStatsNocAdoptPendingDevVersion OBJECT-TYPE
			SYNTAX DisplayString
			MAX-ACCESS read-only
			STATUS current
			DESCRIPTION
				"Device software version
				
				XPath: /extremeWing-stats/noc/adoption/pending_device[mac=key1]/version"
			::= { extremeWingStatsNocAdoptPendingDevEntry 5 }

		
		-- 1.3.6.1.4.1.1916.2.131.50.1.4.1.9.2.1.6
		extremeWingStatsNocAdoptPendingDevSerialNumber OBJECT-TYPE
			SYNTAX DisplayString
			MAX-ACCESS read-only
			STATUS current
			DESCRIPTION
				"Device serial number
				
				XPath: /extremeWing-stats/noc/adoption/pending_device[mac=key1]/serial_number"
			::= { extremeWingStatsNocAdoptPendingDevEntry 6 }

		
		-- 1.3.6.1.4.1.1916.2.131.50.1.4.1.9.2.1.7
		extremeWingStatsNocAdoptPendingDevReason OBJECT-TYPE
			SYNTAX DisplayString
			MAX-ACCESS read-only
			STATUS current
			DESCRIPTION
				"Reason for adoption pending.
				
				XPath: /extremeWing-stats/noc/adoption/pending_device[mac=key1]/reason"
			::= { extremeWingStatsNocAdoptPendingDevEntry 7 }

		
		-- 1.3.6.1.4.1.1916.2.131.50.1.4.1.9.2.1.8
		extremeWingStatsNocAdoptPendingDevNumRadios OBJECT-TYPE
			SYNTAX Unsigned32
			MAX-ACCESS read-only
			STATUS current
			DESCRIPTION
				"Number of Radios available in the device.
				
				XPath: /extremeWing-stats/noc/adoption/pending_device[mac=key1]/num_radios"
			::= { extremeWingStatsNocAdoptPendingDevEntry 8 }

		
		-- 1.3.6.1.4.1.1916.2.131.50.1.4.1.9.2.1.9
		extremeWingStatsNocAdoptPendingDevIp OBJECT-TYPE
			SYNTAX DisplayString
			MAX-ACCESS read-only
			STATUS current
			DESCRIPTION
				"IP address configured on the device.
				
				XPath: /extremeWing-stats/noc/adoption/pending_device[mac=key1]/ip"
			::= { extremeWingStatsNocAdoptPendingDevEntry 9 }

		
		-- 1.3.6.1.4.1.1916.2.131.50.1.4.1.9.2.1.10
		extremeWingStatsNocAdoptPendingDevVlan OBJECT-TYPE
			SYNTAX Unsigned32
			MAX-ACCESS read-only
			STATUS current
			DESCRIPTION
				"VLAN of the Device. The value 0 indicates that the VLAN
				is not applicable.
				
				XPath: /extremeWing-stats/noc/adoption/pending_device[mac=key1]/vlan"
			::= { extremeWingStatsNocAdoptPendingDevEntry 10 }
		-- 1.3.6.1.4.1.1916.2.131.50.1.4.1.10
		extremeWingStatsNocLoadApImage OBJECT IDENTIFIER ::= { extremeWingStatsNoc 10 }

		
		-- 1.3.6.1.4.1.1916.2.131.50.1.4.1.10.1
		extremeWingStatsNocLoadApImageStatus OBJECT-TYPE
			SYNTAX DisplayString
			MAX-ACCESS read-only
			STATUS current
			DESCRIPTION
				"'Done' for success, 'failed' for failure, 'In_Progress' for in progress
				XPath: /extremeWing-stats/device/self/ap-upgrade/load-image-status/status
				"
			::= { extremeWingStatsNocLoadApImage 1 }

		
		-- 1.3.6.1.4.1.1916.2.131.50.1.4.1.10.2
		extremeWingStatsNocLoadApImageStatusMsg OBJECT-TYPE
			SYNTAX DisplayString
			MAX-ACCESS read-only
			STATUS current
			DESCRIPTION
				"Detailed status message on success (or) failure
				XPath: /extremeWing-stats/device/self/ap-upgrade/load-image-status/message"
			::= { extremeWingStatsNocLoadApImage 2 }

		
		-- 1.3.6.1.4.1.1916.2.131.50.1.4.1.11
		extremeWingStatsNocSysImgUpgrade OBJECT IDENTIFIER ::= { extremeWingStatsNoc 11 }

		
		-- 1.3.6.1.4.1.1916.2.131.50.1.4.1.11.1
		extremeWingStatsNocSysImgUpgradeStatus OBJECT-TYPE
			SYNTAX DisplayString
			MAX-ACCESS read-only
			STATUS current
			DESCRIPTION
				"XPath: /extremeWing-stats/device/self/system/upgrade-status/status"
			::= { extremeWingStatsNocSysImgUpgrade 1 }

		
		-- 1.3.6.1.4.1.1916.2.131.50.1.4.1.11.2
		extremeWingStatsNocSysImgUpgradeTime OBJECT-TYPE
			SYNTAX DisplayString
			MAX-ACCESS read-only
			STATUS current
			DESCRIPTION
				"time of last upgrade
				XPath: /extremeWing-stats/device/self/system/upgrade-status/time "
			::= { extremeWingStatsNocSysImgUpgrade 2 }

		
		-- 1.3.6.1.4.1.1916.2.131.50.1.4.1.11.3
		extremeWingStatsNocSysImgUpgradeMsg OBJECT-TYPE
			SYNTAX DisplayString
			MAX-ACCESS read-only
			STATUS current
			DESCRIPTION
				"contents of the upgrade related log file
				XPath: /extremeWing-stats/device/self/system/upgrade-status/message"
			::= { extremeWingStatsNocSysImgUpgrade 3 }


		-- 1.3.6.1.4.1.1916.2.131.50.1.4.1.12
		extremeWingtStatsNocAAPLic OBJECT IDENTIFIER ::= { extremeWingStatsNoc 12 }

		
		-- 1.3.6.1.4.1.1916.2.131.50.1.4.1.12.1
		extremeWingStatsNocAAPLicApCount OBJECT-TYPE
			SYNTAX Counter32
			MAX-ACCESS read-only
			STATUS current
			DESCRIPTION
				"Total number of AP license count
				XPath: /extremeWing-stats/device/self/license/aap/count"
			::= { extremeWingtStatsNocAAPLic 1 }

		
		-- 1.3.6.1.4.1.1916.2.131.50.1.4.1.12.2
		extremeWingStatsNocAAPLicApUsage OBJECT-TYPE
			SYNTAX Counter32
			MAX-ACCESS read-only
			STATUS current
			DESCRIPTION
				"Total number of AP license used count
				XPath: /extremeWing-stats/device/self/license/aap/usage "
			::= { extremeWingtStatsNocAAPLic 2 }


		-- 1.3.6.1.4.1.1916.2.131.50.1.4.1.13
		extremeWingtStatsNocDevInfoTable OBJECT-TYPE
			SYNTAX SEQUENCE OF ExtremeWingtStatsNocDevInfoEntry
			MAX-ACCESS not-accessible
			STATUS current
			DESCRIPTION
				"Description."
			::= { extremeWingStatsNoc 13 }

		
		-- 1.3.6.1.4.1.1916.2.131.50.1.4.1.13.1
		extremeWingtStatsNocDevInfoEntry OBJECT-TYPE
			SYNTAX ExtremeWingtStatsNocDevInfoEntry
			MAX-ACCESS not-accessible
			STATUS current
			DESCRIPTION
				"Description."
			INDEX { extremeWingtStatsNocDeviceType }
			::= { extremeWingtStatsNocDevInfoTable 1 }

		
		ExtremeWingtStatsNocDevInfoEntry ::=
			SEQUENCE { 
				extremeWingtStatsNocDeviceType
					DisplayString,
				extremeWingtStatsNocDevAdoptedCount
					Counter32
			 }

		-- 1.3.6.1.4.1.1916.2.131.50.1.4.1.13.1.1
		extremeWingtStatsNocDeviceType OBJECT-TYPE
			SYNTAX DisplayString
			MAX-ACCESS read-only
			STATUS current
			DESCRIPTION
				"device type
				XPATH: /extremeWing-stats/noc/inventory/by_type[type=key1]/type"
			::= { extremeWingtStatsNocDevInfoEntry 1 }

		
		-- 1.3.6.1.4.1.1916.2.131.50.1.4.1.13.1.2
		extremeWingtStatsNocDevAdoptedCount OBJECT-TYPE
			SYNTAX Counter32
			MAX-ACCESS read-only
			STATUS current
			DESCRIPTION
				"number of online devices
				XPATH: /extremeWing-stats/noc/inventory/by_type[type=key1]/num_online"
			::= { extremeWingtStatsNocDevInfoEntry 2 }


-- /extremeWing-stats/device
		-- 1.3.6.1.4.1.1916.2.131.50.1.4.2
		extremeWingStatsDev OBJECT IDENTIFIER ::= { extremeWingStats 2 }

		
		-- 1.3.6.1.4.1.1916.2.131.50.1.4.2.1
		extremeWingStatsDevTable OBJECT-TYPE
			SYNTAX SEQUENCE OF ExtremeWingStatsDevEntry
			MAX-ACCESS not-accessible
			STATUS current
			DESCRIPTION
				"Status of configured and/or discovered devices.
				
				/extremeWing-stats/device"
			::= { extremeWingStatsDev 1 }

		
		-- 1.3.6.1.4.1.1916.2.131.50.1.4.2.1.1
		extremeWingStatsDevEntry OBJECT-TYPE
			SYNTAX ExtremeWingStatsDevEntry
			MAX-ACCESS not-accessible
			STATUS current
			DESCRIPTION
				"An entry in the table."
			INDEX { extremeWingStatsDevMac }
			::= { extremeWingStatsDevTable 1 }

		
		ExtremeWingStatsDevEntry ::=
			SEQUENCE { 
				extremeWingStatsDevMac
					MacAddress,
				extremeWingStatsDevType
					DisplayString,
				extremeWingStatsDevHostname
					DisplayString,
				extremeWingStatsDevVersion
					DisplayString,
				extremeWingStatsDevSerialNo
					DisplayString,
				extremeWingStatsDevRfDomainName
					DisplayString,
				extremeWingStatsDevOnline
					TruthValue
			 }

		-- 1.3.6.1.4.1.1916.2.131.50.1.4.2.1.1.1
		extremeWingStatsDevMac OBJECT-TYPE
			SYNTAX MacAddress
			MAX-ACCESS read-only
			STATUS current
			DESCRIPTION
				"Device MAC
				
				XPath: /extremeWing-stats/device[mac=key1]/mac"
			::= { extremeWingStatsDevEntry 1 }

		
		-- 1.3.6.1.4.1.1916.2.131.50.1.4.2.1.1.2
		extremeWingStatsDevType OBJECT-TYPE
			SYNTAX DisplayString
			MAX-ACCESS read-only
			STATUS current
			DESCRIPTION
				"Device type
				
				XPath: /extremeWing-stats/device[mac=key1]/base/type"
			::= { extremeWingStatsDevEntry 2 }

		
		-- 1.3.6.1.4.1.1916.2.131.50.1.4.2.1.1.3
		extremeWingStatsDevHostname OBJECT-TYPE
			SYNTAX DisplayString
			MAX-ACCESS read-only
			STATUS current
			DESCRIPTION
				"Device hostname
				
				XPath: /extremeWing-stats/device[mac=key1]/base/hostname"
			::= { extremeWingStatsDevEntry 3 }

		
		-- 1.3.6.1.4.1.1916.2.131.50.1.4.2.1.1.4
		extremeWingStatsDevVersion OBJECT-TYPE
			SYNTAX DisplayString
			MAX-ACCESS read-only
			STATUS current
			DESCRIPTION
				"Device software version
				
				XPath: /extremeWing-stats/device[mac=key1]/base/version"
			::= { extremeWingStatsDevEntry 4 }

		
		-- 1.3.6.1.4.1.1916.2.131.50.1.4.2.1.1.5
		extremeWingStatsDevSerialNo OBJECT-TYPE
			SYNTAX DisplayString
			MAX-ACCESS read-only
			STATUS current
			DESCRIPTION
				"Device serial number
				
				XPath: /extremeWing-stats/device[mac=key1]/base/serial-no"
			::= { extremeWingStatsDevEntry 5 }

		
		-- 1.3.6.1.4.1.1916.2.131.50.1.4.2.1.1.6
		extremeWingStatsDevRfDomainName OBJECT-TYPE
			SYNTAX DisplayString
			MAX-ACCESS read-only
			STATUS current
			DESCRIPTION
				"Device RF Domain name
				
				XPath: /extremeWing-stats/device[mac=key1]/base/rf_domain_name"
			::= { extremeWingStatsDevEntry 6 }

		
		-- 1.3.6.1.4.1.1916.2.131.50.1.4.2.1.1.7
		extremeWingStatsDevOnline OBJECT-TYPE
			SYNTAX TruthValue
			MAX-ACCESS read-only
			STATUS current
			DESCRIPTION
				"Device online status
				
				XPath: /extremeWing-stats/device[mac=key1]/base/online"
			::= { extremeWingStatsDevEntry 7 }

		
-- /extremeWing-stats/device/sysinfo
		-- 1.3.6.1.4.1.1916.2.131.50.1.4.2.2
		extremeWingStatsDevSysInfo OBJECT IDENTIFIER ::= { extremeWingStatsDev 2 }

		
		-- 1.3.6.1.4.1.1916.2.131.50.1.4.2.2.1
		extremeWingStatsDevSysInfoTable OBJECT-TYPE
			SYNTAX SEQUENCE OF ExtremeWingStatsDevSysInfoEntry
			MAX-ACCESS not-accessible
			STATUS current
			DESCRIPTION
				"
				
				/extremeWing-stats/device/sysinfo"
			::= { extremeWingStatsDevSysInfo 1 }

		
		-- 1.3.6.1.4.1.1916.2.131.50.1.4.2.2.1.1
		extremeWingStatsDevSysInfoEntry OBJECT-TYPE
			SYNTAX ExtremeWingStatsDevSysInfoEntry
			MAX-ACCESS not-accessible
			STATUS current
			DESCRIPTION
				"An entry in the table."
			INDEX { extremeWingStatsDevMac }
			::= { extremeWingStatsDevSysInfoTable 1 }

		
		ExtremeWingStatsDevSysInfoEntry ::=
			SEQUENCE { 
				extremeWingStatsDevSysInfoFreeMem
					Unsigned32,
				extremeWingStatsDevSysInfoTotalMem
					Unsigned32,
				extremeWingStatsDevSysInfoFreeRamCurrent
					Unsigned32,
				extremeWingStatsDevSysInfoFreeRamLimit
					Unsigned32,
				extremeWingStatsDevSysInfoFdMax
					Unsigned32,
				extremeWingStatsDevSysInfoFdCurrent
					Unsigned32,
				extremeWingStatsDevSysInfoFdLimit
					Unsigned32,
				extremeWingStatsDevSysInfoLoadLimitS0
					Unsigned32,
				extremeWingStatsDevSysInfoLoadLimitS1
					Unsigned32,
				extremeWingStatsDevSysInfoLoadLimitS2
					Unsigned32,
				extremeWingStatsDevSysInfoBufferCurrent0
					Unsigned32,
				extremeWingStatsDevSysInfoBufferCurrent1
					Unsigned32,
				extremeWingStatsDevSysInfoBufferCurrent2
					Unsigned32,
				extremeWingStatsDevSysInfoBufferCurrent3
					Unsigned32,
				extremeWingStatsDevSysInfoBufferCurrent4
					Unsigned32,
				extremeWingStatsDevSysInfoBufferCurrent5
					Unsigned32,
				extremeWingStatsDevSysInfoBufferCurrent6
					Unsigned32,
				extremeWingStatsDevSysInfoBufferCurrent7
					Unsigned32,
				extremeWingStatsDevSysInfoBufferCurrent8
					Unsigned32,
				extremeWingStatsDevSysInfoBufferCurrent9
					Unsigned32,
				extremeWingStatsDevSysInfoBufferCurrent10
					Unsigned32,
				extremeWingStatsDevSysInfoBufferCurrent11
					Unsigned32,
				extremeWingStatsDevSysInfoBufferCurrent12
					Unsigned32,
				extremeWingStatsDevSysInfoBufferTotal0
					Unsigned32,
				extremeWingStatsDevSysInfoBufferTotal1
					Unsigned32,
				extremeWingStatsDevSysInfoBufferTotal2
					Unsigned32,
				extremeWingStatsDevSysInfoBufferTotal3
					Unsigned32,
				extremeWingStatsDevSysInfoBufferTotal4
					Unsigned32,
				extremeWingStatsDevSysInfoBufferTotal5
					Unsigned32,
				extremeWingStatsDevSysInfoBufferTotal6
					Unsigned32,
				extremeWingStatsDevSysInfoBufferTotal7
					Unsigned32,
				extremeWingStatsDevSysInfoBufferTotal8
					Unsigned32,
				extremeWingStatsDevSysInfoBufferTotal9
					Unsigned32,
				extremeWingStatsDevSysInfoBufferTotal10
					Unsigned32,
				extremeWingStatsDevSysInfoBufferTotal11
					Unsigned32,
				extremeWingStatsDevSysInfoBufferTotal12
					Unsigned32
			 }

		-- 1.3.6.1.4.1.1916.2.131.50.1.4.2.2.1.1.1
		extremeWingStatsDevSysInfoFreeMem OBJECT-TYPE
			SYNTAX Unsigned32
			MAX-ACCESS read-only
			STATUS current
			DESCRIPTION
				"Available ram in megabytes
				
				XPath: /extremeWing-stats/device[mac=key1]/sysinfo/free_mem"
			::= { extremeWingStatsDevSysInfoEntry 1 }

		
		-- 1.3.6.1.4.1.1916.2.131.50.1.4.2.2.1.1.2
		extremeWingStatsDevSysInfoTotalMem OBJECT-TYPE
			SYNTAX Unsigned32
			MAX-ACCESS read-only
			STATUS current
			DESCRIPTION
				"Total system ram in megabytes
				
				XPath: /extremeWing-stats/device[mac=key1]/sysinfo/total_mem"
			::= { extremeWingStatsDevSysInfoEntry 2 }

		
		-- 1.3.6.1.4.1.1916.2.131.50.1.4.2.2.1.1.3
		extremeWingStatsDevSysInfoFreeRamCurrent OBJECT-TYPE
			SYNTAX Unsigned32
			MAX-ACCESS read-only
			STATUS current
			DESCRIPTION
				"10 times the percentage of currently free RAM
				(687 => 68.7% is free)
				
				XPath: /extremeWing-stats/device[mac=key1]/sysinfo/free_ram_limit_current"
			::= { extremeWingStatsDevSysInfoEntry 3 }

		
		-- 1.3.6.1.4.1.1916.2.131.50.1.4.2.2.1.1.4
		extremeWingStatsDevSysInfoFreeRamLimit OBJECT-TYPE
			SYNTAX Unsigned32
			MAX-ACCESS read-only
			STATUS current
			DESCRIPTION
				"10 times the recommended minimum available RAM
				(100 => 10% needed)
				
				XPath: /extremeWing-stats/device[mac=key1]/sysinfo/free_ram_limit_limit"
			::= { extremeWingStatsDevSysInfoEntry 4 }

		
		-- 1.3.6.1.4.1.1916.2.131.50.1.4.2.2.1.1.5
		extremeWingStatsDevSysInfoFdMax OBJECT-TYPE
			SYNTAX Unsigned32
			MAX-ACCESS read-only
			STATUS current
			DESCRIPTION
				"Used to calculate the number of 'used' file descriptors
				(fdMax - fdCurrent)
				
				XPath: /extremeWing-stats/device[mac=key1]/sysinfo/fd_max"
			::= { extremeWingStatsDevSysInfoEntry 5 }

		
		-- 1.3.6.1.4.1.1916.2.131.50.1.4.2.2.1.1.6
		extremeWingStatsDevSysInfoFdCurrent OBJECT-TYPE
			SYNTAX Unsigned32
			MAX-ACCESS read-only
			STATUS current
			DESCRIPTION
				"The number of file descriptors currently in use
				
				XPath: /extremeWing-stats/device[mac=key1]/sysinfo/fd_current"
			::= { extremeWingStatsDevSysInfoEntry 6 }

		
		-- 1.3.6.1.4.1.1916.2.131.50.1.4.2.2.1.1.7
		extremeWingStatsDevSysInfoFdLimit OBJECT-TYPE
			SYNTAX Unsigned32
			MAX-ACCESS read-only
			STATUS current
			DESCRIPTION
				"The maximum number of file descriptors
				
				XPath: /extremeWing-stats/device[mac=key1]/sysinfo/fd_limit_limit"
			::= { extremeWingStatsDevSysInfoEntry 7 }

		
		-- 1.3.6.1.4.1.1916.2.131.50.1.4.2.2.1.1.8
		extremeWingStatsDevSysInfoLoadLimitS0 OBJECT-TYPE
			SYNTAX Unsigned32
			MAX-ACCESS read-only
			STATUS current
			DESCRIPTION
				"10 times the average cpu load over the last minute
				(2 => .2 % cpu load)
				
				XPath: /extremeWing-stats/device[mac=key1]/sysinfo/load_limit_s0"
			::= { extremeWingStatsDevSysInfoEntry 8 }

		
		-- 1.3.6.1.4.1.1916.2.131.50.1.4.2.2.1.1.9
		extremeWingStatsDevSysInfoLoadLimitS1 OBJECT-TYPE
			SYNTAX Unsigned32
			MAX-ACCESS read-only
			STATUS current
			DESCRIPTION
				"10 times the average cpu load over the last five minutes
				(2 => .2 % cpu load)
				
				XPath: /extremeWing-stats/device[mac=key1]/sysinfo/load_limit_s1"
			::= { extremeWingStatsDevSysInfoEntry 9 }

		
		-- 1.3.6.1.4.1.1916.2.131.50.1.4.2.2.1.1.10
		extremeWingStatsDevSysInfoLoadLimitS2 OBJECT-TYPE
			SYNTAX Unsigned32
			MAX-ACCESS read-only
			STATUS current
			DESCRIPTION
				"10 times the average cpu load over the last fifteen minutes
				(2 => .2 % cpu load)
				
				XPath: /extremeWing-stats/device[mac=key1]/sysinfo/load_limit_s2"
			::= { extremeWingStatsDevSysInfoEntry 10 }

		
		-- 1.3.6.1.4.1.1916.2.131.50.1.4.2.2.1.1.11
		extremeWingStatsDevSysInfoBufferCurrent0 OBJECT-TYPE
			SYNTAX Unsigned32
			MAX-ACCESS read-only
			STATUS current
			DESCRIPTION
				"The current number of 32 byte buffers in use
				
				XPath: /extremeWing-stats/device[mac=key1]/sysinfo/b_limit_c0"
			::= { extremeWingStatsDevSysInfoEntry 11 }

		
		-- 1.3.6.1.4.1.1916.2.131.50.1.4.2.2.1.1.12
		extremeWingStatsDevSysInfoBufferCurrent1 OBJECT-TYPE
			SYNTAX Unsigned32
			MAX-ACCESS read-only
			STATUS current
			DESCRIPTION
				"The current number of 64 byte buffers in use
				
				XPath: /extremeWing-stats/device[mac=key1]/sysinfo/b_limit_c1"
			::= { extremeWingStatsDevSysInfoEntry 12 }

		
		-- 1.3.6.1.4.1.1916.2.131.50.1.4.2.2.1.1.13
		extremeWingStatsDevSysInfoBufferCurrent2 OBJECT-TYPE
			SYNTAX Unsigned32
			MAX-ACCESS read-only
			STATUS current
			DESCRIPTION
				"The current number of 128 byte buffers in use
				
				XPath: /extremeWing-stats/device[mac=key1]/sysinfo/b_limit_c2"
			::= { extremeWingStatsDevSysInfoEntry 13 }

		
		-- 1.3.6.1.4.1.1916.2.131.50.1.4.2.2.1.1.14
		extremeWingStatsDevSysInfoBufferCurrent3 OBJECT-TYPE
			SYNTAX Unsigned32
			MAX-ACCESS read-only
			STATUS current
			DESCRIPTION
				"The current number of 256 byte buffers in use
				
				XPath: /extremeWing-stats/device[mac=key1]/sysinfo/b_limit_c3"
			::= { extremeWingStatsDevSysInfoEntry 14 }

		
		-- 1.3.6.1.4.1.1916.2.131.50.1.4.2.2.1.1.15
		extremeWingStatsDevSysInfoBufferCurrent4 OBJECT-TYPE
			SYNTAX Unsigned32
			MAX-ACCESS read-only
			STATUS current
			DESCRIPTION
				"The current number of 512 byte buffers in use
				
				XPath: /extremeWing-stats/device[mac=key1]/sysinfo/b_limit_c4"
			::= { extremeWingStatsDevSysInfoEntry 15 }

		
		-- 1.3.6.1.4.1.1916.2.131.50.1.4.2.2.1.1.16
		extremeWingStatsDevSysInfoBufferCurrent5 OBJECT-TYPE
			SYNTAX Unsigned32
			MAX-ACCESS read-only
			STATUS current
			DESCRIPTION
				"The current number of 1Kb buffers in use
				
				XPath: /extremeWing-stats/device[mac=key1]/sysinfo/b_limit_c5"
			::= { extremeWingStatsDevSysInfoEntry 16 }

		
		-- 1.3.6.1.4.1.1916.2.131.50.1.4.2.2.1.1.17
		extremeWingStatsDevSysInfoBufferCurrent6 OBJECT-TYPE
			SYNTAX Unsigned32
			MAX-ACCESS read-only
			STATUS current
			DESCRIPTION
				"The current number of 2Kb buffers in use
				
				XPath: /extremeWing-stats/device[mac=key1]/sysinfo/b_limit_c6"
			::= { extremeWingStatsDevSysInfoEntry 17 }

		
		-- 1.3.6.1.4.1.1916.2.131.50.1.4.2.2.1.1.18
		extremeWingStatsDevSysInfoBufferCurrent7 OBJECT-TYPE
			SYNTAX Unsigned32
			MAX-ACCESS read-only
			STATUS current
			DESCRIPTION
				"The current number of 4Kb byte buffers in use
				
				XPath: /extremeWing-stats/device[mac=key1]/sysinfo/b_limit_c7"
			::= { extremeWingStatsDevSysInfoEntry 18 }

		
		-- 1.3.6.1.4.1.1916.2.131.50.1.4.2.2.1.1.19
		extremeWingStatsDevSysInfoBufferCurrent8 OBJECT-TYPE
			SYNTAX Unsigned32
			MAX-ACCESS read-only
			STATUS current
			DESCRIPTION
				"The current number of 8Kb byte buffers in use
				
				XPath: /extremeWing-stats/device[mac=key1]/sysinfo/b_limit_c8"
			::= { extremeWingStatsDevSysInfoEntry 19 }

		
		-- 1.3.6.1.4.1.1916.2.131.50.1.4.2.2.1.1.20
		extremeWingStatsDevSysInfoBufferCurrent9 OBJECT-TYPE
			SYNTAX Unsigned32
			MAX-ACCESS read-only
			STATUS current
			DESCRIPTION
				"The current number of 16Kb buffers in use
				
				XPath: /extremeWing-stats/device[mac=key1]/sysinfo/b_limit_c9"
			::= { extremeWingStatsDevSysInfoEntry 20 }

		
		-- 1.3.6.1.4.1.1916.2.131.50.1.4.2.2.1.1.21
		extremeWingStatsDevSysInfoBufferCurrent10 OBJECT-TYPE
			SYNTAX Unsigned32
			MAX-ACCESS read-only
			STATUS current
			DESCRIPTION
				"The current number of 32Kb buffers in use
				
				XPath: /extremeWing-stats/device[mac=key1]/sysinfo/b_limit_c10"
			::= { extremeWingStatsDevSysInfoEntry 21 }

		
		-- 1.3.6.1.4.1.1916.2.131.50.1.4.2.2.1.1.22
		extremeWingStatsDevSysInfoBufferCurrent11 OBJECT-TYPE
			SYNTAX Unsigned32
			MAX-ACCESS read-only
			STATUS current
			DESCRIPTION
				"The current number of 64Kb buffers in use
				
				XPath: /extremeWing-stats/device[mac=key1]/sysinfo/b_limit_c11"
			::= { extremeWingStatsDevSysInfoEntry 22 }

		
		-- 1.3.6.1.4.1.1916.2.131.50.1.4.2.2.1.1.23
		extremeWingStatsDevSysInfoBufferCurrent12 OBJECT-TYPE
			SYNTAX Unsigned32
			MAX-ACCESS read-only
			STATUS current
			DESCRIPTION
				"The current number of 128Kb buffers in use
				
				XPath: /extremeWing-stats/device[mac=key1]/sysinfo/b_limit_c12"
			::= { extremeWingStatsDevSysInfoEntry 23 }

		
		-- 1.3.6.1.4.1.1916.2.131.50.1.4.2.2.1.1.24
		extremeWingStatsDevSysInfoBufferTotal0 OBJECT-TYPE
			SYNTAX Unsigned32
			MAX-ACCESS read-only
			STATUS current
			DESCRIPTION
				"The total number of 32 byte buffers available
				
				XPath: /extremeWing-stats/device[mac=key1]/sysinfo/b_limit_l0"
			::= { extremeWingStatsDevSysInfoEntry 24 }

		
		-- 1.3.6.1.4.1.1916.2.131.50.1.4.2.2.1.1.25
		extremeWingStatsDevSysInfoBufferTotal1 OBJECT-TYPE
			SYNTAX Unsigned32
			MAX-ACCESS read-only
			STATUS current
			DESCRIPTION
				"The total number of 64 byte buffers available
				
				XPath: /extremeWing-stats/device[mac=key1]/sysinfo/b_limit_l1"
			::= { extremeWingStatsDevSysInfoEntry 25 }

		
		-- 1.3.6.1.4.1.1916.2.131.50.1.4.2.2.1.1.26
		extremeWingStatsDevSysInfoBufferTotal2 OBJECT-TYPE
			SYNTAX Unsigned32
			MAX-ACCESS read-only
			STATUS current
			DESCRIPTION
				"The total number of 128 byte buffers available
				
				XPath: /extremeWing-stats/device[mac=key1]/sysinfo/b_limit_l2"
			::= { extremeWingStatsDevSysInfoEntry 26 }

		
		-- 1.3.6.1.4.1.1916.2.131.50.1.4.2.2.1.1.27
		extremeWingStatsDevSysInfoBufferTotal3 OBJECT-TYPE
			SYNTAX Unsigned32
			MAX-ACCESS read-only
			STATUS current
			DESCRIPTION
				"The total number of 256 byte buffers available
				
				XPath: /extremeWing-stats/device[mac=key1]/sysinfo/b_limit_l3"
			::= { extremeWingStatsDevSysInfoEntry 27 }

		
		-- 1.3.6.1.4.1.1916.2.131.50.1.4.2.2.1.1.28
		extremeWingStatsDevSysInfoBufferTotal4 OBJECT-TYPE
			SYNTAX Unsigned32
			MAX-ACCESS read-only
			STATUS current
			DESCRIPTION
				"The total number of 512 byte buffers available
				
				XPath: /extremeWing-stats/device[mac=key1]/sysinfo/b_limit_l4"
			::= { extremeWingStatsDevSysInfoEntry 28 }

		
		-- 1.3.6.1.4.1.1916.2.131.50.1.4.2.2.1.1.29
		extremeWingStatsDevSysInfoBufferTotal5 OBJECT-TYPE
			SYNTAX Unsigned32
			MAX-ACCESS read-only
			STATUS current
			DESCRIPTION
				"The total number of 1Kb buffers available
				
				XPath: /extremeWing-stats/device[mac=key1]/sysinfo/b_limit_l5"
			::= { extremeWingStatsDevSysInfoEntry 29 }

		
		-- 1.3.6.1.4.1.1916.2.131.50.1.4.2.2.1.1.30
		extremeWingStatsDevSysInfoBufferTotal6 OBJECT-TYPE
			SYNTAX Unsigned32
			MAX-ACCESS read-only
			STATUS current
			DESCRIPTION
				"The total number of 2Kb buffers available
				
				XPath: /extremeWing-stats/device[mac=key1]/sysinfo/b_limit_l6"
			::= { extremeWingStatsDevSysInfoEntry 30 }

		
		-- 1.3.6.1.4.1.1916.2.131.50.1.4.2.2.1.1.31
		extremeWingStatsDevSysInfoBufferTotal7 OBJECT-TYPE
			SYNTAX Unsigned32
			MAX-ACCESS read-only
			STATUS current
			DESCRIPTION
				"The total number of 4Kb buffers available
				
				XPath: /extremeWing-stats/device[mac=key1]/sysinfo/b_limit_l7"
			::= { extremeWingStatsDevSysInfoEntry 31 }

		
		-- 1.3.6.1.4.1.1916.2.131.50.1.4.2.2.1.1.32
		extremeWingStatsDevSysInfoBufferTotal8 OBJECT-TYPE
			SYNTAX Unsigned32
			MAX-ACCESS read-only
			STATUS current
			DESCRIPTION
				"The total number of 8Kb buffers available
				
				XPath: /extremeWing-stats/device[mac=key1]/sysinfo/b_limit_l8"
			::= { extremeWingStatsDevSysInfoEntry 32 }

		
		-- 1.3.6.1.4.1.1916.2.131.50.1.4.2.2.1.1.33
		extremeWingStatsDevSysInfoBufferTotal9 OBJECT-TYPE
			SYNTAX Unsigned32
			MAX-ACCESS read-only
			STATUS current
			DESCRIPTION
				"The total number of 16Kb buffers available
				
				XPath: /extremeWing-stats/device[mac=key1]/sysinfo/b_limit_l9"
			::= { extremeWingStatsDevSysInfoEntry 33 }

		
		-- 1.3.6.1.4.1.1916.2.131.50.1.4.2.2.1.1.34
		extremeWingStatsDevSysInfoBufferTotal10 OBJECT-TYPE
			SYNTAX Unsigned32
			MAX-ACCESS read-only
			STATUS current
			DESCRIPTION
				"The total number of 32Kb buffers available
				
				XPath: /extremeWing-stats/device[mac=key1]/sysinfo/b_limit_l10"
			::= { extremeWingStatsDevSysInfoEntry 34 }

		
		-- 1.3.6.1.4.1.1916.2.131.50.1.4.2.2.1.1.35
		extremeWingStatsDevSysInfoBufferTotal11 OBJECT-TYPE
			SYNTAX Unsigned32
			MAX-ACCESS read-only
			STATUS current
			DESCRIPTION
				"The total number of 64Kb buffers available
				
				XPath: /extremeWing-stats/device[mac=key1]/sysinfo/b_limit_l11"
			::= { extremeWingStatsDevSysInfoEntry 35 }

		
		-- 1.3.6.1.4.1.1916.2.131.50.1.4.2.2.1.1.36
		extremeWingStatsDevSysInfoBufferTotal12 OBJECT-TYPE
			SYNTAX Unsigned32
			MAX-ACCESS read-only
			STATUS current
			DESCRIPTION
				"The total number of 128Kb buffers available
				
				XPath: /extremeWing-stats/device[mac=key1]/sysinfo/b_limit_l12"
			::= { extremeWingStatsDevSysInfoEntry 36 }

		
-- /extremeWing-stats/device/system
		-- 1.3.6.1.4.1.1916.2.131.50.1.4.2.4
		extremeWingStatsDevSys OBJECT IDENTIFIER ::= { extremeWingStatsDev 4 }

		
		-- 1.3.6.1.4.1.1916.2.131.50.1.4.2.4.1
		extremeWingStatsDevSysTable OBJECT-TYPE
			SYNTAX SEQUENCE OF ExtremeWingStatsDevSysEntry
			MAX-ACCESS not-accessible
			STATUS current
			DESCRIPTION
				"
				
				/extremeWing-stats/device/system"
			::= { extremeWingStatsDevSys 1 }

		
		-- 1.3.6.1.4.1.1916.2.131.50.1.4.2.4.1.1
		extremeWingStatsDevSysEntry OBJECT-TYPE
			SYNTAX ExtremeWingStatsDevSysEntry
			MAX-ACCESS not-accessible
			STATUS current
			DESCRIPTION
				"An entry in the table."
			INDEX { extremeWingStatsDevMac }
			::= { extremeWingStatsDevSysTable 1 }

		
		ExtremeWingStatsDevSysEntry ::=
			SEQUENCE { 
				extremeWingStatsDevSysProductName
					DisplayString,
				extremeWingStatsDevSysSerialNo
					DisplayString,
				extremeWingStatsDevSysVersion
					DisplayString,
				extremeWingStatsDevSysPrimaryVersion
					DisplayString,
				extremeWingStatsDevSysSecondaryVersion
					DisplayString,
				extremeWingStatsDevSysPrimaryBuildDate
					DisplayString,
				extremeWingStatsDevSysSecondaryBuildDate
					DisplayString,
				extremeWingStatsDevSysPrimaryInstallDate
					DisplayString,
				extremeWingStatsDevSysSecondaryInstallDate
					DisplayString,
				extremeWingStatsDevSysBootPartition
					DisplayString,
				extremeWingStatsDevSysNextBoot
					DisplayString,
				extremeWingStatsDevSysIsFallback
					TruthValue,
				extremeWingStatsDevSysImgFallback
					DisplayString,
				extremeWingStatsDevSysUptime
					DisplayString,
				extremeWingStatsDevSysCpu
					DisplayString,
				extremeWingStatsDevSysRam
					DisplayString,
				extremeWingStatsDevSysClock
					DisplayString,
				extremeWingStatsDevSysUpgradeStatus
					DisplayString,
				extremeWingStatsDevSysUpgradeTime
					DisplayString,
				extremeWingStatsDevSysPoeFwVersion
					DisplayString,
				extremeWingStatsDevSysFpgaVersion
					DisplayString,
				extremeWingStatsDevSysModelNumber
					DisplayString
			 }

		-- 1.3.6.1.4.1.1916.2.131.50.1.4.2.4.1.1.1
		extremeWingStatsDevSysProductName OBJECT-TYPE
			SYNTAX DisplayString
			MAX-ACCESS read-only
			STATUS current
			DESCRIPTION
				"Product name string
				
				XPath: /extremeWing-stats/device[mac=key1]/system/product-name"
			::= { extremeWingStatsDevSysEntry 1 }

		
		-- 1.3.6.1.4.1.1916.2.131.50.1.4.2.4.1.1.2
		extremeWingStatsDevSysSerialNo OBJECT-TYPE
			SYNTAX DisplayString
			MAX-ACCESS read-only
			STATUS current
			DESCRIPTION
				"
				
				XPath: /extremeWing-stats/device[mac=key1]/system/serial-no"
			::= { extremeWingStatsDevSysEntry 2 }

		
		-- 1.3.6.1.4.1.1916.2.131.50.1.4.2.4.1.1.3
		extremeWingStatsDevSysVersion OBJECT-TYPE
			SYNTAX DisplayString
			MAX-ACCESS read-only
			STATUS current
			DESCRIPTION
				"Current running device firmware version
				
				XPath: /extremeWing-stats/device[mac=key1]/system/version"
			::= { extremeWingStatsDevSysEntry 3 }

		
		-- 1.3.6.1.4.1.1916.2.131.50.1.4.2.4.1.1.4
		extremeWingStatsDevSysPrimaryVersion OBJECT-TYPE
			SYNTAX DisplayString
			MAX-ACCESS read-only
			STATUS current
			DESCRIPTION
				"Device firmware version installed on primary partition
				
				XPath: /extremeWing-stats/device[mac=key1]/system/primary-version"
			::= { extremeWingStatsDevSysEntry 4 }

		
		-- 1.3.6.1.4.1.1916.2.131.50.1.4.2.4.1.1.5
		extremeWingStatsDevSysSecondaryVersion OBJECT-TYPE
			SYNTAX DisplayString
			MAX-ACCESS read-only
			STATUS current
			DESCRIPTION
				"Device firmware version installed on secondary partition
				
				XPath: /extremeWing-stats/device[mac=key1]/system/secondary-version"
			::= { extremeWingStatsDevSysEntry 5 }

		
		-- 1.3.6.1.4.1.1916.2.131.50.1.4.2.4.1.1.6
		extremeWingStatsDevSysPrimaryBuildDate OBJECT-TYPE
			SYNTAX DisplayString
			MAX-ACCESS read-only
			STATUS current
			DESCRIPTION
				"Firmware build date on primary partition
				
				XPath: /extremeWing-stats/device[mac=key1]/system/primary-build-date"
			::= { extremeWingStatsDevSysEntry 6 }

		
		-- 1.3.6.1.4.1.1916.2.131.50.1.4.2.4.1.1.7
		extremeWingStatsDevSysSecondaryBuildDate OBJECT-TYPE
			SYNTAX DisplayString
			MAX-ACCESS read-only
			STATUS current
			DESCRIPTION
				"Firmware build date on secondary partition
				
				XPath: /extremeWing-stats/device[mac=key1]/system/secondary-build-date"
			::= { extremeWingStatsDevSysEntry 7 }

		
		-- 1.3.6.1.4.1.1916.2.131.50.1.4.2.4.1.1.8
		extremeWingStatsDevSysPrimaryInstallDate OBJECT-TYPE
			SYNTAX DisplayString
			MAX-ACCESS read-only
			STATUS current
			DESCRIPTION
				"Firmware install date on primary partition
				
				XPath: /extremeWing-stats/device[mac=key1]/system/primary-install-date"
			::= { extremeWingStatsDevSysEntry 8 }

		
		-- 1.3.6.1.4.1.1916.2.131.50.1.4.2.4.1.1.9
		extremeWingStatsDevSysSecondaryInstallDate OBJECT-TYPE
			SYNTAX DisplayString
			MAX-ACCESS read-only
			STATUS current
			DESCRIPTION
				"Firmware install date on secondary partition
				
				XPath: /extremeWing-stats/device[mac=key1]/system/secondary-install-date"
			::= { extremeWingStatsDevSysEntry 9 }

		
		-- 1.3.6.1.4.1.1916.2.131.50.1.4.2.4.1.1.10
		extremeWingStatsDevSysBootPartition OBJECT-TYPE
			SYNTAX DisplayString
			MAX-ACCESS read-only
			STATUS current
			DESCRIPTION
				"Current system boot partition name
				
				Values:
				primary,
				secondary,
				unknown
				
				XPath: /extremeWing-stats/device[mac=key1]/system/boot-partition"
			::= { extremeWingStatsDevSysEntry 10 }

		
		-- 1.3.6.1.4.1.1916.2.131.50.1.4.2.4.1.1.11
		extremeWingStatsDevSysNextBoot OBJECT-TYPE
			SYNTAX DisplayString
			MAX-ACCESS read-only
			STATUS current
			DESCRIPTION
				"Next system boot partition name 
				
				Values:
				primary,
				secondary,
				unknown
				
				XPath: /extremeWing-stats/device[mac=key1]/system/next-boot"
			::= { extremeWingStatsDevSysEntry 11 }

		
		-- 1.3.6.1.4.1.1916.2.131.50.1.4.2.4.1.1.12
		extremeWingStatsDevSysIsFallback OBJECT-TYPE
			SYNTAX TruthValue
			MAX-ACCESS read-only
			STATUS current
			DESCRIPTION
				"Whether fallback is enabled or not
				
				XPath: /extremeWing-stats/device[mac=key1]/system/is-fallback"
			::= { extremeWingStatsDevSysEntry 12 }

		
		-- 1.3.6.1.4.1.1916.2.131.50.1.4.2.4.1.1.13
		extremeWingStatsDevSysImgFallback OBJECT-TYPE
			SYNTAX DisplayString
			MAX-ACCESS read-only
			STATUS current
			DESCRIPTION
				"
				
				Values:
				Enabled,
				Disabled
				
				XPath: /extremeWing-stats/device[mac=key1]/system/img-fallback"
			::= { extremeWingStatsDevSysEntry 13 }

		
		-- 1.3.6.1.4.1.1916.2.131.50.1.4.2.4.1.1.14
		extremeWingStatsDevSysUptime OBJECT-TYPE
			SYNTAX DisplayString
			MAX-ACCESS read-only
			STATUS current
			DESCRIPTION
				"Current system uptime
				
				XPath: /extremeWing-stats/device[mac=key1]/system/uptime"
			::= { extremeWingStatsDevSysEntry 14 }

		
		-- 1.3.6.1.4.1.1916.2.131.50.1.4.2.4.1.1.15
		extremeWingStatsDevSysCpu OBJECT-TYPE
			SYNTAX DisplayString
			MAX-ACCESS read-only
			STATUS current
			DESCRIPTION
				"Current cpu info
				
				XPath: /extremeWing-stats/device[mac=key1]/system/cpu"
			::= { extremeWingStatsDevSysEntry 15 }

		
		-- 1.3.6.1.4.1.1916.2.131.50.1.4.2.4.1.1.16
		extremeWingStatsDevSysRam OBJECT-TYPE
			SYNTAX DisplayString
			MAX-ACCESS read-only
			STATUS current
			DESCRIPTION
				"Current system ram info
				
				XPath: /extremeWing-stats/device[mac=key1]/system/ram"
			::= { extremeWingStatsDevSysEntry 16 }

		
		-- 1.3.6.1.4.1.1916.2.131.50.1.4.2.4.1.1.17
		extremeWingStatsDevSysClock OBJECT-TYPE
			SYNTAX DisplayString
			MAX-ACCESS read-only
			STATUS current
			DESCRIPTION
				"Current date and time
				
				XPath: /extremeWing-stats/device[mac=key1]/system/clock"
			::= { extremeWingStatsDevSysEntry 17 }

		
		-- 1.3.6.1.4.1.1916.2.131.50.1.4.2.4.1.1.18
		extremeWingStatsDevSysUpgradeStatus OBJECT-TYPE
			SYNTAX DisplayString
			MAX-ACCESS read-only
			STATUS current
			DESCRIPTION
				"
				
				XPath: /extremeWing-stats/device[mac=key1]/system/upgrade-status/status"
			::= { extremeWingStatsDevSysEntry 18 }

		
		-- 1.3.6.1.4.1.1916.2.131.50.1.4.2.4.1.1.19
		extremeWingStatsDevSysUpgradeTime OBJECT-TYPE
			SYNTAX DisplayString
			MAX-ACCESS read-only
			STATUS current
			DESCRIPTION
				"Time of last upgrade
				
				XPath: /extremeWing-stats/device[mac=key1]/system/upgrade-status/time"
			::= { extremeWingStatsDevSysEntry 19 }

		
		-- 1.3.6.1.4.1.1916.2.131.50.1.4.2.4.1.1.21
		extremeWingStatsDevSysPoeFwVersion OBJECT-TYPE
			SYNTAX DisplayString
			MAX-ACCESS read-only
			STATUS current
			DESCRIPTION
				"Current poe firmware version
				
				XPath: /extremeWing-stats/device[mac=key1]/system/poe-fw-version"
			::= { extremeWingStatsDevSysEntry 21 }

		
		-- 1.3.6.1.4.1.1916.2.131.50.1.4.2.4.1.1.22
		extremeWingStatsDevSysFpgaVersion OBJECT-TYPE
			SYNTAX DisplayString
			MAX-ACCESS read-only
			STATUS current
			DESCRIPTION
				"Current fpga version
				
				XPath: /extremeWing-stats/device[mac=key1]/system/fpga-version"
			::= { extremeWingStatsDevSysEntry 22 }

		
		-- 1.3.6.1.4.1.1916.2.131.50.1.4.2.4.1.1.23
		extremeWingStatsDevSysModelNumber OBJECT-TYPE
			SYNTAX DisplayString
			MAX-ACCESS read-only
			STATUS current
			DESCRIPTION
				"System model number
				
				XPath: /extremeWing-stats/device[mac=key1]/system/model-number"
			::= { extremeWingStatsDevSysEntry 23 }

		
-- /extremeWing-stats/device/interface
		-- 1.3.6.1.4.1.1916.2.131.50.1.4.2.6
		extremeWingStatsDevIf OBJECT IDENTIFIER ::= { extremeWingStatsDev 6 }

		
		-- 1.3.6.1.4.1.1916.2.131.50.1.4.2.6.1
		extremeWingStatsDevIfTable OBJECT-TYPE
			SYNTAX SEQUENCE OF ExtremeWingStatsDevIfEntry
			MAX-ACCESS not-accessible
			STATUS current
			DESCRIPTION
				"
				
				/extremeWing-stats/device/interface"
			::= { extremeWingStatsDevIf 1 }

		
		-- 1.3.6.1.4.1.1916.2.131.50.1.4.2.6.1.1
		extremeWingStatsDevIfEntry OBJECT-TYPE
			SYNTAX ExtremeWingStatsDevIfEntry
			MAX-ACCESS not-accessible
			STATUS current
			DESCRIPTION
				"An entry in the table."
			INDEX { extremeWingStatsDevMac, extremeWingStatsDevIfName }
			::= { extremeWingStatsDevIfTable 1 }

		
		ExtremeWingStatsDevIfEntry ::=
			SEQUENCE { 
				extremeWingStatsDevIfName
					ExtremeWingIdentifier,
				extremeWingStatsDevIfIndex
					Unsigned32,
				extremeWingStatsDevIfHwType
					DisplayString,
				extremeWingStatsDevIfMode
					DisplayString,
				extremeWingStatsDevIfMac
					MacAddress,
				extremeWingStatsDevIfStatusAdmin
					DisplayString,
				extremeWingStatsDevIfMtu
					Unsigned32,
				extremeWingStatsDevIfGoodOctetsRcv
					Counter64,
				extremeWingStatsDevIfGoodPktsRcv
					Counter64,
				extremeWingStatsDevIfDropEvents
					Counter64,
				extremeWingStatsDevIfUcPktsRcv
					Counter64,
				extremeWingStatsDevIfBrdcPktsRcv
					Counter64,
				extremeWingStatsDevIfMcPktsRcv
					Counter64,
				extremeWingStatsDevIfBadPktsRcv
					Counter64,
				extremeWingStatsDevIfUndersizePkts
					Counter64,
				extremeWingStatsDevIfOversizePkts
					Counter64,
				extremeWingStatsDevIfBadCrc
					Counter64,
				extremeWingStatsDevIfMacRcvError
					Counter64,
				extremeWingStatsDevIfFragmentsPkts
					Counter64,
				extremeWingStatsDevIfJabberPkts
					Counter64,
				extremeWingStatsDevIfGoodOctetsSent
					Counter64,
				extremeWingStatsDevIfGoodPktsSent
					Counter64,
				extremeWingStatsDevIfMacTransmitErr
					Counter64,
				extremeWingStatsDevIfUcPktsSent
					Counter64,
				extremeWingStatsDevIfBrdcPktsSent
					Counter64,
				extremeWingStatsDevIfMcPktsSent
					Counter64,
				extremeWingStatsDevIfLateCollisions
					Counter64,
				extremeWingStatsDevIfExcessiveCollisions
					Counter64,
				extremeWingStatsDevIfCollisions
					Counter64,
				extremeWingStatsDevIfMetric
					Integer32,
				extremeWingStatsDevIfRxFifoErrors
					Counter32,
				extremeWingStatsDevIfRxOverErrors
					Counter32,
				extremeWingStatsDevIfTxWindowErrors
					Counter32,
				extremeWingStatsDevIfTxFifoErrors
					Counter32,
				extremeWingStatsDevIfTxAbortedErrors
					Counter32,
				extremeWingStatsDevIfTxCarrierErrors
					Counter32,
				extremeWingStatsDevIfTxDropped
					Counter32,
				extremeWingStatsDevIfRxLengthErrors
					Counter32,
				extremeWingStatsDevIfRxMissedErrors
					Counter32,
				extremeWingStatsDevIfRxFrameErrors
					Counter32,
				extremeWingStatsDevIfTxErrors
					Counter32,
				extremeWingStatsDevIfTxHeartbeatErrors
					Counter32,
				extremeWingStatsDevIfStatusOper
					DisplayString
			 }

		-- 1.3.6.1.4.1.1916.2.131.50.1.4.2.6.1.1.1
		extremeWingStatsDevIfName OBJECT-TYPE
			SYNTAX ExtremeWingIdentifier
			MAX-ACCESS read-only
			STATUS current
			DESCRIPTION
				"Interface name. Eg., ge1, vlan1, radio1 ...
				
				XPath: /extremeWing-stats/device[mac=key1]/interface[name=key2]/name"
			::= { extremeWingStatsDevIfEntry 1 }

		
		-- 1.3.6.1.4.1.1916.2.131.50.1.4.2.6.1.1.2
		extremeWingStatsDevIfIndex OBJECT-TYPE
			SYNTAX Unsigned32
			MAX-ACCESS read-only
			STATUS current
			DESCRIPTION
				"Interface index
				
				XPath: /extremeWing-stats/device[mac=key1]/interface[name=key2]/index"
			::= { extremeWingStatsDevIfEntry 2 }

		
		-- 1.3.6.1.4.1.1916.2.131.50.1.4.2.6.1.1.3
		extremeWingStatsDevIfHwType OBJECT-TYPE
			SYNTAX DisplayString
			MAX-ACCESS read-only
			STATUS current
			DESCRIPTION
				"Hardware type of the network interface
				
				Values:
				ethernet,
				vlan,
				radio,
				aggregate,
				ppp
				
				XPath: /extremeWing-stats/device[mac=key1]/interface[name=key2]/hw_type"
			::= { extremeWingStatsDevIfEntry 3 }

		
		-- 1.3.6.1.4.1.1916.2.131.50.1.4.2.6.1.1.4
		extremeWingStatsDevIfMode OBJECT-TYPE
			SYNTAX DisplayString
			MAX-ACCESS read-only
			STATUS current
			DESCRIPTION
				"
				
				Values:
				Layer 2,
				Layer 3
				
				XPath: /extremeWing-stats/device[mac=key1]/interface[name=key2]/mode"
			::= { extremeWingStatsDevIfEntry 4 }

		
		-- 1.3.6.1.4.1.1916.2.131.50.1.4.2.6.1.1.5
		extremeWingStatsDevIfMac OBJECT-TYPE
			SYNTAX MacAddress
			MAX-ACCESS read-only
			STATUS current
			DESCRIPTION
				"Interface MAC address
				
				XPath: /extremeWing-stats/device[mac=key1]/interface[name=key2]/mac"
			::= { extremeWingStatsDevIfEntry 5 }

		
		-- 1.3.6.1.4.1.1916.2.131.50.1.4.2.6.1.1.6
		extremeWingStatsDevIfStatusAdmin OBJECT-TYPE
			SYNTAX DisplayString
			MAX-ACCESS read-only
			STATUS current
			DESCRIPTION
				"Administrative status of interface (up/down)
				
				Values:
				up
				down
				
				XPath: /extremeWing-stats/device[mac=key1]/interface[name=key2]/status_admin"
			::= { extremeWingStatsDevIfEntry 6 }

		
		-- 1.3.6.1.4.1.1916.2.131.50.1.4.2.6.1.1.7
		extremeWingStatsDevIfMtu OBJECT-TYPE
			SYNTAX Unsigned32
			MAX-ACCESS read-only
			STATUS current
			DESCRIPTION
				"Maximum transmission unit
				
				XPath: /extremeWing-stats/device[mac=key1]/interface[name=key2]/mtu"
			::= { extremeWingStatsDevIfEntry 7 }

		
		-- 1.3.6.1.4.1.1916.2.131.50.1.4.2.6.1.1.8
		extremeWingStatsDevIfGoodOctetsRcv OBJECT-TYPE
			SYNTAX Counter64
			MAX-ACCESS read-only
			STATUS current
			DESCRIPTION
				"Total number of bytes received on the interfaces
				
				XPath: /extremeWing-stats/device[mac=key1]/interface[name=key2]/good_octets_rcv"
			::= { extremeWingStatsDevIfEntry 8 }

		
		-- 1.3.6.1.4.1.1916.2.131.50.1.4.2.6.1.1.9
		extremeWingStatsDevIfGoodPktsRcv OBJECT-TYPE
			SYNTAX Counter64
			MAX-ACCESS read-only
			STATUS current
			DESCRIPTION
				"Total number of packets received on the interface
				
				XPath: /extremeWing-stats/device[mac=key1]/interface[name=key2]/good_pkts_rcv"
			::= { extremeWingStatsDevIfEntry 9 }

		
		-- 1.3.6.1.4.1.1916.2.131.50.1.4.2.6.1.1.10
		extremeWingStatsDevIfDropEvents OBJECT-TYPE
			SYNTAX Counter64
			MAX-ACCESS read-only
			STATUS current
			DESCRIPTION
				"Total number of inbound packets dropped on the interface
				
				XPath: /extremeWing-stats/device[mac=key1]/interface[name=key2]/drop_events"
			::= { extremeWingStatsDevIfEntry 10 }

		
		-- 1.3.6.1.4.1.1916.2.131.50.1.4.2.6.1.1.11
		extremeWingStatsDevIfUcPktsRcv OBJECT-TYPE
			SYNTAX Counter64
			MAX-ACCESS read-only
			STATUS current
			DESCRIPTION
				"Total number of unicast packets received on the interface
				
				XPath: /extremeWing-stats/device[mac=key1]/interface[name=key2]/uc_pkts_rcv"
			::= { extremeWingStatsDevIfEntry 11 }

		
		-- 1.3.6.1.4.1.1916.2.131.50.1.4.2.6.1.1.12
		extremeWingStatsDevIfBrdcPktsRcv OBJECT-TYPE
			SYNTAX Counter64
			MAX-ACCESS read-only
			STATUS current
			DESCRIPTION
				"Total number of broadcast packets received on the interface
				
				XPath: /extremeWing-stats/device[mac=key1]/interface[name=key2]/brdc_pkts_rcv"
			::= { extremeWingStatsDevIfEntry 12 }

		
		-- 1.3.6.1.4.1.1916.2.131.50.1.4.2.6.1.1.13
		extremeWingStatsDevIfMcPktsRcv OBJECT-TYPE
			SYNTAX Counter64
			MAX-ACCESS read-only
			STATUS current
			DESCRIPTION
				"Total number of multicast packets received on the interface
				
				XPath: /extremeWing-stats/device[mac=key1]/interface[name=key2]/mc_pkts_rcv"
			::= { extremeWingStatsDevIfEntry 13 }

		
		-- 1.3.6.1.4.1.1916.2.131.50.1.4.2.6.1.1.14
		extremeWingStatsDevIfBadPktsRcv OBJECT-TYPE
			SYNTAX Counter64
			MAX-ACCESS read-only
			STATUS current
			DESCRIPTION
				"Total number of inbound packets received with error
				on the interface
				
				XPath: /extremeWing-stats/device[mac=key1]/interface[name=key2]/bad_pkts_rcv"
			::= { extremeWingStatsDevIfEntry 14 }

		
		-- 1.3.6.1.4.1.1916.2.131.50.1.4.2.6.1.1.15
		extremeWingStatsDevIfUndersizePkts OBJECT-TYPE
			SYNTAX Counter64
			MAX-ACCESS read-only
			STATUS current
			DESCRIPTION
				"Total number of undersize packets received on the interface
				
				XPath: /extremeWing-stats/device[mac=key1]/interface[name=key2]/undersize_pkts"
			::= { extremeWingStatsDevIfEntry 15 }

		
		-- 1.3.6.1.4.1.1916.2.131.50.1.4.2.6.1.1.16
		extremeWingStatsDevIfOversizePkts OBJECT-TYPE
			SYNTAX Counter64
			MAX-ACCESS read-only
			STATUS current
			DESCRIPTION
				"Total number of oversize packets received on the interface
				
				XPath: /extremeWing-stats/device[mac=key1]/interface[name=key2]/oversize_pkts"
			::= { extremeWingStatsDevIfEntry 16 }

		
		-- 1.3.6.1.4.1.1916.2.131.50.1.4.2.6.1.1.17
		extremeWingStatsDevIfBadCrc OBJECT-TYPE
			SYNTAX Counter64
			MAX-ACCESS read-only
			STATUS current
			DESCRIPTION
				"Total number of packets received with bad crc on the interface
				
				XPath: /extremeWing-stats/device[mac=key1]/interface[name=key2]/bad_crc"
			::= { extremeWingStatsDevIfEntry 17 }

		
		-- 1.3.6.1.4.1.1916.2.131.50.1.4.2.6.1.1.18
		extremeWingStatsDevIfMacRcvError OBJECT-TYPE
			SYNTAX Counter64
			MAX-ACCESS read-only
			STATUS current
			DESCRIPTION
				"Total number of packets received with mac error
				on the interface
				
				XPath: /extremeWing-stats/device[mac=key1]/interface[name=key2]/mac_rcv_error"
			::= { extremeWingStatsDevIfEntry 18 }

		
		-- 1.3.6.1.4.1.1916.2.131.50.1.4.2.6.1.1.19
		extremeWingStatsDevIfFragmentsPkts OBJECT-TYPE
			SYNTAX Counter64
			MAX-ACCESS read-only
			STATUS current
			DESCRIPTION
				"Total number of fragmented packets received on the interface
				
				XPath: /extremeWing-stats/device[mac=key1]/interface[name=key2]/fragments_pkts"
			::= { extremeWingStatsDevIfEntry 19 }

		
		-- 1.3.6.1.4.1.1916.2.131.50.1.4.2.6.1.1.20
		extremeWingStatsDevIfJabberPkts OBJECT-TYPE
			SYNTAX Counter64
			MAX-ACCESS read-only
			STATUS current
			DESCRIPTION
				"Total number of jabber packets received on the interface
				
				XPath: /extremeWing-stats/device[mac=key1]/interface[name=key2]/jabber_pkts"
			::= { extremeWingStatsDevIfEntry 20 }

		
		-- 1.3.6.1.4.1.1916.2.131.50.1.4.2.6.1.1.21
		extremeWingStatsDevIfGoodOctetsSent OBJECT-TYPE
			SYNTAX Counter64
			MAX-ACCESS read-only
			STATUS current
			DESCRIPTION
				"Total number of bytes transmitted on the interfaces
				
				XPath: /extremeWing-stats/device[mac=key1]/interface[name=key2]/good_octets_sent"
			::= { extremeWingStatsDevIfEntry 21 }

		
		-- 1.3.6.1.4.1.1916.2.131.50.1.4.2.6.1.1.22
		extremeWingStatsDevIfGoodPktsSent OBJECT-TYPE
			SYNTAX Counter64
			MAX-ACCESS read-only
			STATUS current
			DESCRIPTION
				"Total number of packets transmitted on the interface
				
				XPath: /extremeWing-stats/device[mac=key1]/interface[name=key2]/good_pkts_sent"
			::= { extremeWingStatsDevIfEntry 22 }

		
		-- 1.3.6.1.4.1.1916.2.131.50.1.4.2.6.1.1.23
		extremeWingStatsDevIfMacTransmitErr OBJECT-TYPE
			SYNTAX Counter64
			MAX-ACCESS read-only
			STATUS current
			DESCRIPTION
				"Total number of packets transmitted with mac error on the interface
				
				XPath: /extremeWing-stats/device[mac=key1]/interface[name=key2]/mac_transmit_err"
			::= { extremeWingStatsDevIfEntry 23 }

		
		-- 1.3.6.1.4.1.1916.2.131.50.1.4.2.6.1.1.24
		extremeWingStatsDevIfUcPktsSent OBJECT-TYPE
			SYNTAX Counter64
			MAX-ACCESS read-only
			STATUS current
			DESCRIPTION
				"Total number of unicast packets transmitted on the interface
				
				XPath: /extremeWing-stats/device[mac=key1]/interface[name=key2]/uc_pkts_sent"
			::= { extremeWingStatsDevIfEntry 24 }

		
		-- 1.3.6.1.4.1.1916.2.131.50.1.4.2.6.1.1.25
		extremeWingStatsDevIfBrdcPktsSent OBJECT-TYPE
			SYNTAX Counter64
			MAX-ACCESS read-only
			STATUS current
			DESCRIPTION
				"Total number of broadcast packets transmitted on the interface
				
				XPath: /extremeWing-stats/device[mac=key1]/interface[name=key2]/brdc_pkts_sent"
			::= { extremeWingStatsDevIfEntry 25 }

		
		-- 1.3.6.1.4.1.1916.2.131.50.1.4.2.6.1.1.26
		extremeWingStatsDevIfMcPktsSent OBJECT-TYPE
			SYNTAX Counter64
			MAX-ACCESS read-only
			STATUS current
			DESCRIPTION
				"Total number of multicast packets transmitted on the interface
				
				XPath: /extremeWing-stats/device[mac=key1]/interface[name=key2]/mc_pkts_sent"
			::= { extremeWingStatsDevIfEntry 26 }

		
		-- 1.3.6.1.4.1.1916.2.131.50.1.4.2.6.1.1.27
		extremeWingStatsDevIfLateCollisions OBJECT-TYPE
			SYNTAX Counter64
			MAX-ACCESS read-only
			STATUS current
			DESCRIPTION
				"Total number of late collisions on the interface
				
				XPath: /extremeWing-stats/device[mac=key1]/interface[name=key2]/late_collisions"
			::= { extremeWingStatsDevIfEntry 27 }

		
		-- 1.3.6.1.4.1.1916.2.131.50.1.4.2.6.1.1.28
		extremeWingStatsDevIfExcessiveCollisions OBJECT-TYPE
			SYNTAX Counter64
			MAX-ACCESS read-only
			STATUS current
			DESCRIPTION
				"Total number of excessive collisions on the interface
				
				XPath: /extremeWing-stats/device[mac=key1]/interface[name=key2]/excessive_collisions"
			::= { extremeWingStatsDevIfEntry 28 }

		
		-- 1.3.6.1.4.1.1916.2.131.50.1.4.2.6.1.1.29
		extremeWingStatsDevIfCollisions OBJECT-TYPE
			SYNTAX Counter64
			MAX-ACCESS read-only
			STATUS current
			DESCRIPTION
				"Total number of collisions on the interface
				
				XPath: /extremeWing-stats/device[mac=key1]/interface[name=key2]/collisions"
			::= { extremeWingStatsDevIfEntry 29 }

		
		-- 1.3.6.1.4.1.1916.2.131.50.1.4.2.6.1.1.30
		extremeWingStatsDevIfMetric OBJECT-TYPE
			SYNTAX Integer32
			MAX-ACCESS read-only
			STATUS current
			DESCRIPTION
				"Interface metric
				
				XPath: /extremeWing-stats/device[mac=key1]/interface[name=key2]/metric"
			::= { extremeWingStatsDevIfEntry 30 }

		
		-- 1.3.6.1.4.1.1916.2.131.50.1.4.2.6.1.1.31
		extremeWingStatsDevIfRxFifoErrors OBJECT-TYPE
			SYNTAX Counter32
			MAX-ACCESS read-only
			STATUS current
			DESCRIPTION
				"RX FIFO errors
				
				XPath: /extremeWing-stats/device[mac=key1]/interface[name=key2]/rx_fifo_errors"
			::= { extremeWingStatsDevIfEntry 31 }

		
		-- 1.3.6.1.4.1.1916.2.131.50.1.4.2.6.1.1.32
		extremeWingStatsDevIfRxOverErrors OBJECT-TYPE
			SYNTAX Counter32
			MAX-ACCESS read-only
			STATUS current
			DESCRIPTION
				"RX overflow errors
				
				XPath: /extremeWing-stats/device[mac=key1]/interface[name=key2]/rx_over_errors"
			::= { extremeWingStatsDevIfEntry 32 }

		
		-- 1.3.6.1.4.1.1916.2.131.50.1.4.2.6.1.1.33
		extremeWingStatsDevIfTxWindowErrors OBJECT-TYPE
			SYNTAX Counter32
			MAX-ACCESS read-only
			STATUS current
			DESCRIPTION
				"TX window errors
				
				XPath: /extremeWing-stats/device[mac=key1]/interface[name=key2]/tx_window_errors"
			::= { extremeWingStatsDevIfEntry 33 }

		
		-- 1.3.6.1.4.1.1916.2.131.50.1.4.2.6.1.1.34
		extremeWingStatsDevIfTxFifoErrors OBJECT-TYPE
			SYNTAX Counter32
			MAX-ACCESS read-only
			STATUS current
			DESCRIPTION
				"TX FIFO errors
				
				XPath: /extremeWing-stats/device[mac=key1]/interface[name=key2]/tx_fifo_errors"
			::= { extremeWingStatsDevIfEntry 34 }

		
		-- 1.3.6.1.4.1.1916.2.131.50.1.4.2.6.1.1.35
		extremeWingStatsDevIfTxAbortedErrors OBJECT-TYPE
			SYNTAX Counter32
			MAX-ACCESS read-only
			STATUS current
			DESCRIPTION
				"TX aborted errors
				
				XPath: /extremeWing-stats/device[mac=key1]/interface[name=key2]/tx_aborted_errors"
			::= { extremeWingStatsDevIfEntry 35 }

		
		-- 1.3.6.1.4.1.1916.2.131.50.1.4.2.6.1.1.36
		extremeWingStatsDevIfTxCarrierErrors OBJECT-TYPE
			SYNTAX Counter32
			MAX-ACCESS read-only
			STATUS current
			DESCRIPTION
				"TX carrier errors
				
				XPath: /extremeWing-stats/device[mac=key1]/interface[name=key2]/tx_carrier_errors"
			::= { extremeWingStatsDevIfEntry 36 }

		
		-- 1.3.6.1.4.1.1916.2.131.50.1.4.2.6.1.1.37
		extremeWingStatsDevIfTxDropped OBJECT-TYPE
			SYNTAX Counter32
			MAX-ACCESS read-only
			STATUS current
			DESCRIPTION
				"TX dropped
				
				XPath: /extremeWing-stats/device[mac=key1]/interface[name=key2]/tx_dropped"
			::= { extremeWingStatsDevIfEntry 37 }

		
		-- 1.3.6.1.4.1.1916.2.131.50.1.4.2.6.1.1.38
		extremeWingStatsDevIfRxLengthErrors OBJECT-TYPE
			SYNTAX Counter32
			MAX-ACCESS read-only
			STATUS current
			DESCRIPTION
				"RX length errors
				
				XPath: /extremeWing-stats/device[mac=key1]/interface[name=key2]/rx_length_errors"
			::= { extremeWingStatsDevIfEntry 38 }

		
		-- 1.3.6.1.4.1.1916.2.131.50.1.4.2.6.1.1.39
		extremeWingStatsDevIfRxMissedErrors OBJECT-TYPE
			SYNTAX Counter32
			MAX-ACCESS read-only
			STATUS current
			DESCRIPTION
				"RX length errors
				
				XPath: /extremeWing-stats/device[mac=key1]/interface[name=key2]/rx_missed_errors"
			::= { extremeWingStatsDevIfEntry 39 }

		
		-- 1.3.6.1.4.1.1916.2.131.50.1.4.2.6.1.1.40
		extremeWingStatsDevIfRxFrameErrors OBJECT-TYPE
			SYNTAX Counter32
			MAX-ACCESS read-only
			STATUS current
			DESCRIPTION
				"RX length errors
				
				XPath: /extremeWing-stats/device[mac=key1]/interface[name=key2]/rx_frame_errors"
			::= { extremeWingStatsDevIfEntry 40 }

		
		-- 1.3.6.1.4.1.1916.2.131.50.1.4.2.6.1.1.41
		extremeWingStatsDevIfTxErrors OBJECT-TYPE
			SYNTAX Counter32
			MAX-ACCESS read-only
			STATUS current
			DESCRIPTION
				"TX  errors
				
				XPath: /extremeWing-stats/device[mac=key1]/interface[name=key2]/tx_errors"
			::= { extremeWingStatsDevIfEntry 41 }

		
		-- 1.3.6.1.4.1.1916.2.131.50.1.4.2.6.1.1.42
		extremeWingStatsDevIfTxHeartbeatErrors OBJECT-TYPE
			SYNTAX Counter32
			MAX-ACCESS read-only
			STATUS current
			DESCRIPTION
				"TX heartbeat  errors
				
				XPath: /extremeWing-stats/device[mac=key1]/interface[name=key2]/tx_heartbeat_errors"
			::= { extremeWingStatsDevIfEntry 42 }

		
		-- 1.3.6.1.4.1.1916.2.131.50.1.4.2.6.1.1.43
		extremeWingStatsDevIfStatusOper OBJECT-TYPE
			SYNTAX DisplayString
			MAX-ACCESS read-only
			STATUS current
			DESCRIPTION
				"Operational status of interface (up/down)
				
				Values:
				up
				down
				
				XPath: /extremeWing-stats/device[mac=key1]/interface[name=key2]/status_oper"
			::= { extremeWingStatsDevIfEntry 43 }

		
-- /extremeWing-stats/device/adoption
		-- 1.3.6.1.4.1.1916.2.131.50.1.4.2.8
		extremeWingStatsDevAdopt OBJECT IDENTIFIER ::= { extremeWingStatsDev 8 }

		
		-- 1.3.6.1.4.1.1916.2.131.50.1.4.2.8.2
		extremeWingStatsDevAdoptDevTable OBJECT-TYPE
			SYNTAX SEQUENCE OF ExtremeWingStatsDevAdoptDevEntry
			MAX-ACCESS not-accessible
			STATUS current
			DESCRIPTION
				"Status of currently adopted devices on AP/Wireless Controller.
				
				/extremeWing-stats/device/adoption/adopted_device"
			::= { extremeWingStatsDevAdopt 2 }

		
		-- 1.3.6.1.4.1.1916.2.131.50.1.4.2.8.2.1
		extremeWingStatsDevAdoptDevEntry OBJECT-TYPE
			SYNTAX ExtremeWingStatsDevAdoptDevEntry
			MAX-ACCESS not-accessible
			STATUS current
			DESCRIPTION
				"An entry in the table."
			INDEX { extremeWingStatsDevMac, extremeWingStatsDevAdoptDevMac }
			::= { extremeWingStatsDevAdoptDevTable 1 }

		
		ExtremeWingStatsDevAdoptDevEntry ::=
			SEQUENCE { 
				extremeWingStatsDevAdoptDevMac
					MacAddress,
				extremeWingStatsDevAdoptDevType
					DisplayString,
				extremeWingStatsDevAdoptDevHostname
					DisplayString,
				extremeWingStatsDevAdoptDevVersion
					DisplayString,
				extremeWingStatsDevAdoptDevSerialNo
					DisplayString,
				extremeWingStatsDevAdoptDevRfDomainName
					DisplayString,
				extremeWingStatsDevAdoptDevOnline
					TruthValue,
				extremeWingStatsDevAdoptDevBy
					MacAddress,
				extremeWingStatsDevAdoptDevLastAdoption
					Unsigned32,
				extremeWingStatsDevAdoptDevModelNumber
					DisplayString,
				extremeWingStatsDevAdoptDevStartup
					Unsigned32,
				extremeWingStatsDevAdoptDevCfgStatus
					DisplayString,
				extremeWingStatsDevAdoptDevProductName
					DisplayString
			 }

		-- 1.3.6.1.4.1.1916.2.131.50.1.4.2.8.2.1.1
		extremeWingStatsDevAdoptDevMac OBJECT-TYPE
			SYNTAX MacAddress
			MAX-ACCESS read-only
			STATUS current
			DESCRIPTION
				"Device MAC
				
				XPath: /extremeWing-stats/device[mac=key1]/adoption/adopted_device[mac=key2]/mac"
			::= { extremeWingStatsDevAdoptDevEntry 1 }

		
		-- 1.3.6.1.4.1.1916.2.131.50.1.4.2.8.2.1.2
		extremeWingStatsDevAdoptDevType OBJECT-TYPE
			SYNTAX DisplayString
			MAX-ACCESS read-only
			STATUS current
			DESCRIPTION
				"Device type
				
				XPath: /extremeWing-stats/device[mac=key1]/adoption/adopted_device[mac=key2]/type"
			::= { extremeWingStatsDevAdoptDevEntry 2 }

		
		-- 1.3.6.1.4.1.1916.2.131.50.1.4.2.8.2.1.3
		extremeWingStatsDevAdoptDevHostname OBJECT-TYPE
			SYNTAX DisplayString
			MAX-ACCESS read-only
			STATUS current
			DESCRIPTION
				"Device hostname
				
				XPath: /extremeWing-stats/device[mac=key1]/adoption/adopted_device[mac=key2]/hostname"
			::= { extremeWingStatsDevAdoptDevEntry 3 }

		
		-- 1.3.6.1.4.1.1916.2.131.50.1.4.2.8.2.1.4
		extremeWingStatsDevAdoptDevVersion OBJECT-TYPE
			SYNTAX DisplayString
			MAX-ACCESS read-only
			STATUS current
			DESCRIPTION
				"Device software version
				
				XPath: /extremeWing-stats/device[mac=key1]/adoption/adopted_device[mac=key2]/version"
			::= { extremeWingStatsDevAdoptDevEntry 4 }

		
		-- 1.3.6.1.4.1.1916.2.131.50.1.4.2.8.2.1.5
		extremeWingStatsDevAdoptDevSerialNo OBJECT-TYPE
			SYNTAX DisplayString
			MAX-ACCESS read-only
			STATUS current
			DESCRIPTION
				"Device serial number
				
				XPath: /extremeWing-stats/device[mac=key1]/adoption/adopted_device[mac=key2]/serial-no"
			::= { extremeWingStatsDevAdoptDevEntry 5 }

		
		-- 1.3.6.1.4.1.1916.2.131.50.1.4.2.8.2.1.6
		extremeWingStatsDevAdoptDevRfDomainName OBJECT-TYPE
			SYNTAX DisplayString
			MAX-ACCESS read-only
			STATUS current
			DESCRIPTION
				"Device RF Domain name
				
				XPath: /extremeWing-stats/device[mac=key1]/adoption/adopted_device[mac=key2]/rf_domain_name"
			::= { extremeWingStatsDevAdoptDevEntry 6 }

		
		-- 1.3.6.1.4.1.1916.2.131.50.1.4.2.8.2.1.7
		extremeWingStatsDevAdoptDevOnline OBJECT-TYPE
			SYNTAX TruthValue
			MAX-ACCESS read-only
			STATUS current
			DESCRIPTION
				"Device online status
				
				XPath: /extremeWing-stats/device[mac=key1]/adoption/adopted_device[mac=key2]/online"
			::= { extremeWingStatsDevAdoptDevEntry 7 }

		
		-- 1.3.6.1.4.1.1916.2.131.50.1.4.2.8.2.1.8
		extremeWingStatsDevAdoptDevBy OBJECT-TYPE
			SYNTAX MacAddress
			MAX-ACCESS read-only
			STATUS current
			DESCRIPTION
				"MAC address of the adopting device.
				
				XPath: /extremeWing-stats/device[mac=key1]/adoption/adopted_device[mac=key2]/adopted_by"
			::= { extremeWingStatsDevAdoptDevEntry 8 }

		
		-- 1.3.6.1.4.1.1916.2.131.50.1.4.2.8.2.1.9
		extremeWingStatsDevAdoptDevLastAdoption OBJECT-TYPE
			SYNTAX Unsigned32
			MAX-ACCESS read-only
			STATUS current
			DESCRIPTION
				"UTC timestamp of the last adoption.
				
				XPath: /extremeWing-stats/device[mac=key1]/adoption/adopted_device[mac=key2]/last_adoption"
			::= { extremeWingStatsDevAdoptDevEntry 9 }

		
		-- 1.3.6.1.4.1.1916.2.131.50.1.4.2.8.2.1.10
		extremeWingStatsDevAdoptDevModelNumber OBJECT-TYPE
			SYNTAX DisplayString (SIZE (0..32))
			MAX-ACCESS read-only
			STATUS current
			DESCRIPTION
				"Device model number.
				
				XPath: /extremeWing-stats/device[mac=key1]/adoption/adopted_device[mac=key2]/model_number"
			::= { extremeWingStatsDevAdoptDevEntry 10 }

		
		-- 1.3.6.1.4.1.1916.2.131.50.1.4.2.8.2.1.11
		extremeWingStatsDevAdoptDevStartup OBJECT-TYPE
			SYNTAX Unsigned32
			MAX-ACCESS read-only
			STATUS current
			DESCRIPTION
				"UTC timestamp of device startup.
				
				XPath: /extremeWing-stats/device[mac=key1]/adoption/adopted_device[mac=key2]/startup"
			::= { extremeWingStatsDevAdoptDevEntry 11 }

		
		-- 1.3.6.1.4.1.1916.2.131.50.1.4.2.8.2.1.12
		extremeWingStatsDevAdoptDevCfgStatus OBJECT-TYPE
			SYNTAX DisplayString (SIZE (0..32))
			MAX-ACCESS read-only
			STATUS current
			DESCRIPTION
				"The configuration status of the device, e.g., pending.
				
				XPath: /extremeWing-stats/device[mac=key1]/adoption/adopted_device[mac=key2]/cfg_status"
			::= { extremeWingStatsDevAdoptDevEntry 12 }

		
		-- 1.3.6.1.4.1.1916.2.131.50.1.4.2.8.2.1.13
		extremeWingStatsDevAdoptDevProductName OBJECT-TYPE
			SYNTAX DisplayString (SIZE (0..32))
			MAX-ACCESS read-only
			STATUS current
			DESCRIPTION
				"Product name string
				
				XPath: /extremeWing-stats/device[mac=key1]/adoption/adopted_device[mac=key2]/product-name"
			::= { extremeWingStatsDevAdoptDevEntry 13 }

		
		-- 1.3.6.1.4.1.1916.2.131.50.1.4.2.8.3
		extremeWingStatsDevAdoptPendingDevTable OBJECT-TYPE
			SYNTAX SEQUENCE OF ExtremeWingStatsDevAdoptPendingDevEntry
			MAX-ACCESS not-accessible
			STATUS current
			DESCRIPTION
				"Status of devices not adopted on AP/Wireless Controller.
				
				Xpath: /extremeWing-stats/device/adoption/pending_device"
			::= { extremeWingStatsDevAdopt 3 }

		
		-- 1.3.6.1.4.1.1916.2.131.50.1.4.2.8.3.1
		extremeWingStatsDevAdoptPendingDevEntry OBJECT-TYPE
			SYNTAX ExtremeWingStatsDevAdoptPendingDevEntry
			MAX-ACCESS not-accessible
			STATUS current
			DESCRIPTION
				"An entry in the table."
			INDEX { extremeWingStatsDevMac, extremeWingStatsDevAdoptPendingDevMac }
			::= { extremeWingStatsDevAdoptPendingDevTable 1 }

		
		ExtremeWingStatsDevAdoptPendingDevEntry ::=
			SEQUENCE { 
				extremeWingStatsDevAdoptPendingDevMac
					MacAddress,
				extremeWingStatsDevAdoptPendingDevType
					DisplayString,
				extremeWingStatsDevAdoptPendingDevTarget
					DisplayString,
				extremeWingStatsDevAdoptPendingDevDisOption
					DisplayString,
				extremeWingStatsDevAdoptPendingDevVersion
					DisplayString,
				extremeWingStatsDevAdoptPendingDevSerialNumber
					DisplayString,
				extremeWingStatsDevAdoptPendingDevReason
					DisplayString,
				extremeWingStatsDevAdoptPendingDevNumRadios
					Unsigned32,
				extremeWingStatsDevAdoptPendingDevIp
					DisplayString,
				extremeWingStatsDevAdoptPendingDevVlan
					Unsigned32
			 }

		-- 1.3.6.1.4.1.1916.2.131.50.1.4.2.8.3.1.1
		extremeWingStatsDevAdoptPendingDevMac OBJECT-TYPE
			SYNTAX MacAddress
			MAX-ACCESS read-only
			STATUS current
			DESCRIPTION
				"Device MAC
				
				XPath: /extremeWing-stats/device[mac=key1]/adoption/pending_device[mac=key2]/mac"
			::= { extremeWingStatsDevAdoptPendingDevEntry 1 }

		
		-- 1.3.6.1.4.1.1916.2.131.50.1.4.2.8.3.1.2
		extremeWingStatsDevAdoptPendingDevType OBJECT-TYPE
			SYNTAX DisplayString
			MAX-ACCESS read-only
			STATUS current
			DESCRIPTION
				"Device type
				
				XPath: /extremeWing-stats/device[mac=key1]/adoption/pending_device[mac=key2]/type"
			::= { extremeWingStatsDevAdoptPendingDevEntry 2 }

		
		-- 1.3.6.1.4.1.1916.2.131.50.1.4.2.8.3.1.3
		extremeWingStatsDevAdoptPendingDevTarget OBJECT-TYPE
			SYNTAX DisplayString
			MAX-ACCESS read-only
			STATUS current
			DESCRIPTION
				"Target information for the Device.
				
				XPath: /extremeWing-stats/device[mac=key1]/adoption/pending_device[mac=key2]/target"
			::= { extremeWingStatsDevAdoptPendingDevEntry 3 }

		
		-- 1.3.6.1.4.1.1916.2.131.50.1.4.2.8.3.1.4
		extremeWingStatsDevAdoptPendingDevDisOption OBJECT-TYPE
			SYNTAX DisplayString
			MAX-ACCESS read-only
			STATUS current
			DESCRIPTION
				"Discovery option provided by the device.
				
				XPath: /extremeWing-stats/device[mac=key1]/adoption/pending_device[mac=key2]/dis_option"
			::= { extremeWingStatsDevAdoptPendingDevEntry 4 }

		
		-- 1.3.6.1.4.1.1916.2.131.50.1.4.2.8.3.1.5
		extremeWingStatsDevAdoptPendingDevVersion OBJECT-TYPE
			SYNTAX DisplayString
			MAX-ACCESS read-only
			STATUS current
			DESCRIPTION
				"Device software version
				
				XPath: /extremeWing-stats/device[mac=key1]/adoption/pending_device[mac=key2]/version"
			::= { extremeWingStatsDevAdoptPendingDevEntry 5 }

		
		-- 1.3.6.1.4.1.1916.2.131.50.1.4.2.8.3.1.6
		extremeWingStatsDevAdoptPendingDevSerialNumber OBJECT-TYPE
			SYNTAX DisplayString
			MAX-ACCESS read-only
			STATUS current
			DESCRIPTION
				"Device serial number
				
				XPath: /extremeWing-stats/device[mac=key1]/adoption/pending_device[mac=key2]/serial_number"
			::= { extremeWingStatsDevAdoptPendingDevEntry 6 }

		
		-- 1.3.6.1.4.1.1916.2.131.50.1.4.2.8.3.1.7
		extremeWingStatsDevAdoptPendingDevReason OBJECT-TYPE
			SYNTAX DisplayString
			MAX-ACCESS read-only
			STATUS current
			DESCRIPTION
				"Reason for adoption pending.
				
				XPath: /extremeWing-stats/device[mac=key1]/adoption/pending_device[mac=key2]/reason"
			::= { extremeWingStatsDevAdoptPendingDevEntry 7 }

		
		-- 1.3.6.1.4.1.1916.2.131.50.1.4.2.8.3.1.8
		extremeWingStatsDevAdoptPendingDevNumRadios OBJECT-TYPE
			SYNTAX Unsigned32
			MAX-ACCESS read-only
			STATUS current
			DESCRIPTION
				"Number of Radios available in the device.
				
				XPath: /extremeWing-stats/device[mac=key1]/adoption/pending_device[mac=key2]/num_radios"
			::= { extremeWingStatsDevAdoptPendingDevEntry 8 }

		
		-- 1.3.6.1.4.1.1916.2.131.50.1.4.2.8.3.1.9
		extremeWingStatsDevAdoptPendingDevIp OBJECT-TYPE
			SYNTAX DisplayString
			MAX-ACCESS read-only
			STATUS current
			DESCRIPTION
				"IP address configured on the device.
				
				XPath: /extremeWing-stats/device[mac=key1]/adoption/pending_device[mac=key2]/ip"
			::= { extremeWingStatsDevAdoptPendingDevEntry 9 }

		
		-- 1.3.6.1.4.1.1916.2.131.50.1.4.2.8.3.1.10
		extremeWingStatsDevAdoptPendingDevVlan OBJECT-TYPE
			SYNTAX Unsigned32
			MAX-ACCESS read-only
			STATUS current
			DESCRIPTION
				"VLAN of the Device. The value 0 indicates that the VLAN
				is not applicable.
				
				XPath: /extremeWing-stats/device[mac=key1]/adoption/pending_device[mac=key2]/vlan"
			::= { extremeWingStatsDevAdoptPendingDevEntry 10 }


-- /extremeWing-stats/device/vpn
		-- 1.3.6.1.4.1.1916.2.131.50.1.4.2.11
		extremeWingStatsDevVpn OBJECT IDENTIFIER ::= { extremeWingStatsDev 11 }

		
		-- 1.3.6.1.4.1.1916.2.131.50.1.4.2.11.1
		extremeWingStatsDevVpnIkesaTable OBJECT-TYPE
			SYNTAX SEQUENCE OF ExtremeWingStatsDevVpnIkesaEntry
			MAX-ACCESS not-accessible
			STATUS current
			DESCRIPTION
				"VPN IKESA stats.
				
				/extremeWing-stats/device/vpn/ikesa"
			::= { extremeWingStatsDevVpn 1 }

		
		-- 1.3.6.1.4.1.1916.2.131.50.1.4.2.11.1.1
		extremeWingStatsDevVpnIkesaEntry OBJECT-TYPE
			SYNTAX ExtremeWingStatsDevVpnIkesaEntry
			MAX-ACCESS not-accessible
			STATUS current
			DESCRIPTION
				"An entry in the table."
			INDEX { extremeWingStatsDevMac, extremeWingStatsDevVpnIkesaIndex }
			::= { extremeWingStatsDevVpnIkesaTable 1 }

		
		ExtremeWingStatsDevVpnIkesaEntry ::=
			SEQUENCE { 
				extremeWingStatsDevVpnIkesaIndex
					Unsigned32,
				extremeWingStatsDevVpnIkesaVersion
					DisplayString,
				extremeWingStatsDevVpnIkesapeer
					DisplayString,
				extremeWingStatsDevVpnIkesaLocalIP
					DisplayString,
				extremeWingStatsDevVpnIkesaMeBehindNat
					TruthValue,
				extremeWingStatsDevVpnIkesaPeerBehindNat
					TruthValue,
				extremeWingStatsDevVpnIkesaEncr
					DisplayString,
				extremeWingStatsDevVpnIkesaHash
					DisplayString,
				extremeWingStatsDevVpnIkesaDhGroup
					DisplayString,
				extremeWingStatsDevVpnIkesaPolicyDes
					DisplayString,
				extremeWingStatsDevVpnIkesaIkeSaLifetime
					Integer32,
				extremeWingStatsDevVpnIkesaIkeState
					DisplayString
			 }

		-- 1.3.6.1.4.1.1916.2.131.50.1.4.2.11.1.1.1
		extremeWingStatsDevVpnIkesaIndex OBJECT-TYPE
			SYNTAX Unsigned32
			MAX-ACCESS read-only
			STATUS current
			DESCRIPTION
				"Ikesa Index
				XPath: /extremeWing-stats/device[mac=key1]/vpn/ikesa[index=key2]/index
				"
			::= { extremeWingStatsDevVpnIkesaEntry 1 }

		
		-- 1.3.6.1.4.1.1916.2.131.50.1.4.2.11.1.1.2
		extremeWingStatsDevVpnIkesaVersion OBJECT-TYPE
			SYNTAX DisplayString
			MAX-ACCESS read-only
			STATUS current
			DESCRIPTION
				"enum IKEv1
				enum IKEv2
				
				
				XPath: /extremeWing-stats/device[mac=key1]/vpn/ikesa[index=key2]/version"
			::= { extremeWingStatsDevVpnIkesaEntry 2 }

		
		-- 1.3.6.1.4.1.1916.2.131.50.1.4.2.11.1.1.3
		extremeWingStatsDevVpnIkesapeer OBJECT-TYPE
			SYNTAX DisplayString
			MAX-ACCESS read-only
			STATUS current
			DESCRIPTION
				"Peer Ip Address
				
				XPath: /extremeWing-stats/device[mac=key1]/vpn/ikesa[index=key2]/peer"
			::= { extremeWingStatsDevVpnIkesaEntry 3 }

		
		-- 1.3.6.1.4.1.1916.2.131.50.1.4.2.11.1.1.4
		extremeWingStatsDevVpnIkesaLocalIP OBJECT-TYPE
			SYNTAX DisplayString
			MAX-ACCESS read-only
			STATUS current
			DESCRIPTION
				"Local Ip Address
				
				XPath: /extremeWing-stats/device[mac=key1]/vpn/ikesa[index=key2]/local_ip"
			::= { extremeWingStatsDevVpnIkesaEntry 4 }

		
		-- 1.3.6.1.4.1.1916.2.131.50.1.4.2.11.1.1.5
		extremeWingStatsDevVpnIkesaMeBehindNat OBJECT-TYPE
			SYNTAX TruthValue
			MAX-ACCESS read-only
			STATUS current
			DESCRIPTION
				"Local(Me) behind NAT.
				
				XPath: /extremeWing-stats/device[mac=key1]/vpn/ikesa[index=key2]/me_behind_nat"
			::= { extremeWingStatsDevVpnIkesaEntry 5 }

		
		-- 1.3.6.1.4.1.1916.2.131.50.1.4.2.11.1.1.6
		extremeWingStatsDevVpnIkesaPeerBehindNat OBJECT-TYPE
			SYNTAX TruthValue
			MAX-ACCESS read-only
			STATUS current
			DESCRIPTION
				"Remote(Peer) behind NAT.
				
				XPath: /extremeWing-stats/device[mac=key1]/vpn/ikesa[index=key2]/peer_behind_nat"
			::= { extremeWingStatsDevVpnIkesaEntry 6 }

		
		-- 1.3.6.1.4.1.1916.2.131.50.1.4.2.11.1.1.7
		extremeWingStatsDevVpnIkesaEncr OBJECT-TYPE
			SYNTAX DisplayString
			MAX-ACCESS read-only
			STATUS current
			DESCRIPTION
				"Encr.
				
				XPath: /extremeWing-stats/device[mac=key1]/vpn/ikesa[index=key2]/encr"
			::= { extremeWingStatsDevVpnIkesaEntry 7 }

		
		-- 1.3.6.1.4.1.1916.2.131.50.1.4.2.11.1.1.8
		extremeWingStatsDevVpnIkesaHash OBJECT-TYPE
			SYNTAX DisplayString
			MAX-ACCESS read-only
			STATUS current
			DESCRIPTION
				"Hash.
				
				XPath: /extremeWing-stats/device[mac=key1]/vpn/ikesa[index=key2]/hash"
			::= { extremeWingStatsDevVpnIkesaEntry 8 }

		
		-- 1.3.6.1.4.1.1916.2.131.50.1.4.2.11.1.1.9
		extremeWingStatsDevVpnIkesaDhGroup OBJECT-TYPE
			SYNTAX DisplayString
			MAX-ACCESS read-only
			STATUS current
			DESCRIPTION
				"Dhgroup.
				
				XPath: /extremeWing-stats/device[mac=key1]/vpn/ikesa[index=key2]/dhgroup"
			::= { extremeWingStatsDevVpnIkesaEntry 9 }

		
		-- 1.3.6.1.4.1.1916.2.131.50.1.4.2.11.1.1.10
		extremeWingStatsDevVpnIkesaPolicyDes OBJECT-TYPE
			SYNTAX DisplayString
			MAX-ACCESS read-only
			STATUS current
			DESCRIPTION
				"Policy des.
				
				XPath: /extremeWing-stats/device[mac=key1]/vpn/ikesa[index=key2]/policy_des"
			::= { extremeWingStatsDevVpnIkesaEntry 10 }

		
		-- 1.3.6.1.4.1.1916.2.131.50.1.4.2.11.1.1.11
		extremeWingStatsDevVpnIkesaIkeSaLifetime OBJECT-TYPE
			SYNTAX Integer32
			MAX-ACCESS read-only
			STATUS current
			DESCRIPTION
				"Ike sa Lifetime.
				
				XPath: /extremeWing-stats/device[mac=key1]/vpn/ikesa[index=key2]/ike_sa_lifetime"
			::= { extremeWingStatsDevVpnIkesaEntry 11 }

		
		-- 1.3.6.1.4.1.1916.2.131.50.1.4.2.11.1.1.12
		extremeWingStatsDevVpnIkesaIkeState OBJECT-TYPE
			SYNTAX DisplayString
			MAX-ACCESS read-only
			STATUS current
			DESCRIPTION
				"Ike State.
				
				XPath: /extremeWing-stats/device[mac=key1]/vpn/ikesa[index=key2]/ike_state"
			::= { extremeWingStatsDevVpnIkesaEntry 12 }

		
		-- 1.3.6.1.4.1.1916.2.131.50.1.4.2.11.2
		extremeWingStatsDevVpnIpsecSaTable OBJECT-TYPE
			SYNTAX SEQUENCE OF ExtremeWingStatsDevVpnIpsecSaEntry
			MAX-ACCESS not-accessible
			STATUS current
			DESCRIPTION
				"Description."
			::= { extremeWingStatsDevVpn 2 }

		
		-- 1.3.6.1.4.1.1916.2.131.50.1.4.2.11.2.1
		extremeWingStatsDevVpnIpsecSaEntry OBJECT-TYPE
			SYNTAX ExtremeWingStatsDevVpnIpsecSaEntry
			MAX-ACCESS not-accessible
			STATUS current
			DESCRIPTION
				"Description."
			INDEX { extremeWingStatsDevMac, extremeWingStatsDevVpnIpsecSaIpsIndex}
			::= { extremeWingStatsDevVpnIpsecSaTable 1 }

		
		ExtremeWingStatsDevVpnIpsecSaEntry ::=
			SEQUENCE { 
				extremeWingStatsDevVpnIpsecSaIpsIndex
					DisplayString,
				extremeWingStatsDevVpnIpsecSaPeer
					IpAddress,
				extremeWingStatsDevVpnIpsecSaSpiIn
					DisplayString,
				extremeWingStatsDevVpnIpsecSaSpiOut
					DisplayString,
				extremeWingStatsDevVpnIpsecSaProtocol
					DisplayString,
				extremeWingStatsDevVpnIpsecSaLocalIp
					IpAddress,
				extremeWingStatsDevVpnIpsecSaState
					DisplayString,
				extremeWingStatsDevVpnIpsecSaEncrAlgo
					DisplayString,
				extremeWingStatsDevVpnIpsecSaAuthAlgo
					DisplayString,
				extremeWingStatsDevVpnIpsecSaMode
					DisplayString,
				extremeWingStatsDevVpnIpsecSaReplayEnabled
					TruthValue,
				extremeWingStatsDevVpnIpsecSaReplayWindowSize
					DisplayString,
				extremeWingStatsDevVpnIpsecSaReplaySequenceNumber
					DisplayString,
				extremeWingStatsDevVpnIpsecSaNatPresent
					TruthValue,
				extremeWingStatsDevVpnIpsecSaNatSport
					Unsigned32,
				extremeWingStatsDevVpnIpsecSaNatDport
					Unsigned32,
				extremeWingStatsDevVpnIpsecSaConfigAgeKb
					Unsigned32,
				extremeWingStatsDevVpnIpsecSaConfigAgeSeconds
					Unsigned32,
				extremeWingStatsDevVpnIpsecSaRemAgeKb
					Unsigned32,
				extremeWingStatsDevVpnIpsecSaRemAgeSeconds
					Unsigned32
			 }

		-- 1.3.6.1.4.1.1916.2.131.50.1.4.2.11.2.1.1
		extremeWingStatsDevVpnIpsecSaIpsIndex OBJECT-TYPE
			SYNTAX DisplayString
			MAX-ACCESS read-only
			STATUS current
			DESCRIPTION
				"IpSec: index
				XPath: /extremeWing-stats/device[mac=key1]/vpn/ipsec_sa[peer=key2,spi_in=key2,spi_out=key2,protocol=key2]/ips_index"
			::= { extremeWingStatsDevVpnIpsecSaEntry 1 }


		-- 1.3.6.1.4.1.1916.2.131.50.1.4.2.11.2.1.2
		extremeWingStatsDevVpnIpsecSaPeer OBJECT-TYPE
			SYNTAX IpAddress
			MAX-ACCESS read-only
			STATUS current
			DESCRIPTION
				"Peer IP of SA
				XPath: /extremeWing-stats/device[mac=key1]/vpn/ipsec_sa[peer=key2,spi_in=key2,spi_out=key2,protocol=key2]/peer"
			::= { extremeWingStatsDevVpnIpsecSaEntry 2 }

		
		-- 1.3.6.1.4.1.1916.2.131.50.1.4.2.11.2.1.3
		extremeWingStatsDevVpnIpsecSaSpiIn OBJECT-TYPE
			SYNTAX DisplayString
			MAX-ACCESS read-only
			STATUS current
			DESCRIPTION
				"Incoming packet from peer are using this SPI
				XPath: /extremeWing-stats/device[mac=key1]/vpn/ipsec_sa[peer=key2,spi_in=key2,spi_out=key2,protocol=key2]/spi_in"
			::= { extremeWingStatsDevVpnIpsecSaEntry 3 }

		
		-- 1.3.6.1.4.1.1916.2.131.50.1.4.2.11.2.1.4
		extremeWingStatsDevVpnIpsecSaSpiOut OBJECT-TYPE
			SYNTAX DisplayString
			MAX-ACCESS read-only
			STATUS current
			DESCRIPTION
				"Outgoing packet to peer are using this SPI
				XPath: /extremeWing-stats/device[mac=key1]/vpn/ipsec_sa[peer=key2,spi_in=key2,spi_out=key2,protocol=key2]/spi_out"
			::= { extremeWingStatsDevVpnIpsecSaEntry 4 }

		
		-- 1.3.6.1.4.1.1916.2.131.50.1.4.2.11.2.1.5
		extremeWingStatsDevVpnIpsecSaProtocol OBJECT-TYPE
			SYNTAX DisplayString
			MAX-ACCESS read-only
			STATUS current
			DESCRIPTION
				"enum ESP
				enum AH
				XPath: /extremeWing-stats/device[mac=key1]/vpn/ipsec_sa[peer=key2,spi_in=key2,spi_out=key2,protocol=key2]/protocol"
			::= { extremeWingStatsDevVpnIpsecSaEntry 5 }

		
		-- 1.3.6.1.4.1.1916.2.131.50.1.4.2.11.2.1.6
		extremeWingStatsDevVpnIpsecSaLocalIp OBJECT-TYPE
			SYNTAX IpAddress
			MAX-ACCESS read-only
			STATUS current
			DESCRIPTION
				"Local IP of SA
				XPath: /extremeWing-stats/device[mac=key1]/vpn/ipsec_sa[peer=key2,spi_in=key2,spi_out=key2,protocol=key2]/local_ip"
			::= { extremeWingStatsDevVpnIpsecSaEntry 6 }

		
		-- 1.3.6.1.4.1.1916.2.131.50.1.4.2.11.2.1.7
		extremeWingStatsDevVpnIpsecSaState OBJECT-TYPE
			SYNTAX DisplayString
			MAX-ACCESS read-only
			STATUS current
			DESCRIPTION
				"Current State of SA, valid, rekeying (soft expiring), or expired
				XPath: /extremeWing-stats/device[mac=key1]/vpn/ipsec_sa[peer=key2,spi_in=key2,spi_out=key2,protocol=key2]/state"
			::= { extremeWingStatsDevVpnIpsecSaEntry 7 }

		
		-- 1.3.6.1.4.1.1916.2.131.50.1.4.2.11.2.1.8
		extremeWingStatsDevVpnIpsecSaEncrAlgo OBJECT-TYPE
			SYNTAX DisplayString
			MAX-ACCESS read-only
			STATUS current
			DESCRIPTION
				"Encription Algorithm used
				XPath: /extremeWing-stats/device[mac=key1]/vpn/ipsec_sa[peer=key2,spi_in=key2,spi_out=key2,protocol=key2]/encr_algo"
			::= { extremeWingStatsDevVpnIpsecSaEntry 8 }

		
		-- 1.3.6.1.4.1.1916.2.131.50.1.4.2.11.2.1.9
		extremeWingStatsDevVpnIpsecSaAuthAlgo OBJECT-TYPE
			SYNTAX DisplayString
			MAX-ACCESS read-only
			STATUS current
			DESCRIPTION
				"Authentication/Hash Algorithm used
				XPath: /extremeWing-stats/device[mac=key1]/vpn/ipsec_sa[peer=key2,spi_in=key2,spi_out=key2,protocol=key2]/auth_algo"
			::= { extremeWingStatsDevVpnIpsecSaEntry 9 }

		
		-- 1.3.6.1.4.1.1916.2.131.50.1.4.2.11.2.1.10
		extremeWingStatsDevVpnIpsecSaMode OBJECT-TYPE
			SYNTAX DisplayString
			MAX-ACCESS read-only
			STATUS current
			DESCRIPTION
				"enum tunnel
				enum transport
				
				XPath: /extremeWing-stats/device[mac=key1]/vpn/ipsec_sa[peer=key2,spi_in=key2,spi_out=key2,protocol=key2]/mode"
			::= { extremeWingStatsDevVpnIpsecSaEntry 10 }

		
		-- 1.3.6.1.4.1.1916.2.131.50.1.4.2.11.2.1.11
		extremeWingStatsDevVpnIpsecSaReplayEnabled OBJECT-TYPE
			SYNTAX TruthValue
			MAX-ACCESS read-only
			STATUS current
			DESCRIPTION
				"XPath: /extremeWing-stats/device[mac=key1]/vpn/ipsec_sa[peer=key2,spi_in=key2,spi_out=key2,protocol=key2]/
				replay_enabled"
			::= { extremeWingStatsDevVpnIpsecSaEntry 11 }

		
		-- 1.3.6.1.4.1.1916.2.131.50.1.4.2.11.2.1.12
		extremeWingStatsDevVpnIpsecSaReplayWindowSize OBJECT-TYPE
			SYNTAX DisplayString
			MAX-ACCESS read-only
			STATUS current
			DESCRIPTION
				"XPath: /extremeWing-stats/device[mac=key1]/vpn/ipsec_sa[peer=key2,spi_in=key2,spi_out=key2,protocol=key2]/
				replay_window_size"
			::= { extremeWingStatsDevVpnIpsecSaEntry 12 }

		
		-- 1.3.6.1.4.1.1916.2.131.50.1.4.2.11.2.1.13
		extremeWingStatsDevVpnIpsecSaReplaySequenceNumber OBJECT-TYPE
			SYNTAX DisplayString
			MAX-ACCESS read-only
			STATUS current
			DESCRIPTION
				"Current replay sequence number
				XPath: /extremeWing-stats/device[mac=key1]/vpn/ipsec_sa[peer=key2,spi_in=key2,spi_out=key2,protocol=key2]/
				replay_sequence_number"
			::= { extremeWingStatsDevVpnIpsecSaEntry 13 }

		
		-- 1.3.6.1.4.1.1916.2.131.50.1.4.2.11.2.1.14
		extremeWingStatsDevVpnIpsecSaNatPresent OBJECT-TYPE
			SYNTAX TruthValue
			MAX-ACCESS read-only
			STATUS current
			DESCRIPTION
				"Nat presence
				XPath: /extremeWing-stats/device[mac=key1]/vpn/ipsec_sa[peer=key2,spi_in=key2,spi_out=key2,protocol=key2]/
				nat_present"
			::= { extremeWingStatsDevVpnIpsecSaEntry 14 }

		
		-- 1.3.6.1.4.1.1916.2.131.50.1.4.2.11.2.1.15
		extremeWingStatsDevVpnIpsecSaNatSport OBJECT-TYPE
			SYNTAX Unsigned32
			MAX-ACCESS read-only
			STATUS current
			DESCRIPTION
				"XPath: /extremeWing-stats/device[mac=key1]/vpn/ipsec_sa[peer=key2,spi_in=key2,spi_out=key2,protocol=key2]/
				nat_sport"
			::= { extremeWingStatsDevVpnIpsecSaEntry 15 }

		
		-- 1.3.6.1.4.1.1916.2.131.50.1.4.2.11.2.1.16
		extremeWingStatsDevVpnIpsecSaNatDport OBJECT-TYPE
			SYNTAX Unsigned32
			MAX-ACCESS read-write
			STATUS current
			DESCRIPTION
				"XPath: /extremeWing-stats/device[mac=key1]/vpn/ipsec_sa[peer=key2,spi_in=key2,spi_out=key2,protocol=key2]/
				nat_dport"
			::= { extremeWingStatsDevVpnIpsecSaEntry 16 }

		
		-- 1.3.6.1.4.1.1916.2.131.50.1.4.2.11.2.1.17
		extremeWingStatsDevVpnIpsecSaConfigAgeKb OBJECT-TYPE
			SYNTAX Unsigned32
			UNITS "kilobytes"
			MAX-ACCESS read-only
			STATUS current
			DESCRIPTION
				"XPath: /extremeWing-stats/device[mac=key1]/vpn/ipsec_sa[peer=key2,spi_in=key2,spi_out=key2,protocol=key2]/
				config_age_kb"
			::= { extremeWingStatsDevVpnIpsecSaEntry 17 }

		
		-- 1.3.6.1.4.1.1916.2.131.50.1.4.2.11.2.1.18
		extremeWingStatsDevVpnIpsecSaConfigAgeSeconds OBJECT-TYPE
			SYNTAX Unsigned32
			UNITS "seconds"
			MAX-ACCESS read-only
			STATUS current
			DESCRIPTION
				"XPath: /extremeWing-stats/device[mac=key1]/vpn/ipsec_sa[peer=key2,spi_in=key2,spi_out=key2,protocol=key2]/
				config_age_seconds"
			::= { extremeWingStatsDevVpnIpsecSaEntry 18 }

		
		-- 1.3.6.1.4.1.1916.2.131.50.1.4.2.11.2.1.19
		extremeWingStatsDevVpnIpsecSaRemAgeKb OBJECT-TYPE
			SYNTAX Unsigned32
			UNITS "kilobytes"
			MAX-ACCESS read-only
			STATUS current
			DESCRIPTION
				"XPath: /extremeWing-stats/device[mac=key1]/vpn/ipsec_sa[peer=key2,spi_in=key2,spi_out=key2,protocol=key2]/
				rem_age_kb"
			::= { extremeWingStatsDevVpnIpsecSaEntry 19 }

		
		-- 1.3.6.1.4.1.1916.2.131.50.1.4.2.11.2.1.20
		extremeWingStatsDevVpnIpsecSaRemAgeSeconds OBJECT-TYPE
			SYNTAX Unsigned32
			UNITS "kilobytes"
			MAX-ACCESS read-only
			STATUS current
			DESCRIPTION
				"XPath: /extremeWing-stats/device[mac=key1]/vpn/ipsec_sa[peer=key2,spi_in=key2,spi_out=key2,protocol=key2]/
				rem_age_seconds"
			::= { extremeWingStatsDevVpnIpsecSaEntry 20 }

		
		-- 1.3.6.1.4.1.1916.2.131.50.1.4.2.11.3
		extremeWingStatsDevVpnIpsecSaTrafficSelectorTable OBJECT-TYPE
			SYNTAX SEQUENCE OF ExtremeWingStatsDevVpnIpsecSaTrafficSelectorEntry
			MAX-ACCESS not-accessible
			STATUS current
			DESCRIPTION
				"Description."
			::= { extremeWingStatsDevVpn 3 }

		
		-- 1.3.6.1.4.1.1916.2.131.50.1.4.2.11.3.1
		extremeWingStatsDevVpnIpsecSaTrafficSelectorEntry OBJECT-TYPE
			SYNTAX ExtremeWingStatsDevVpnIpsecSaTrafficSelectorEntry
			MAX-ACCESS not-accessible
			STATUS current
			DESCRIPTION
				"Description."
			INDEX { extremeWingStatsDevMac, extremeWingStatsDevVpnIpsecSaIpsIndex, extremeWingStatsDevVpnIpsecSaTrafficSelectorTsIndex }
			::= { extremeWingStatsDevVpnIpsecSaTrafficSelectorTable 1 }

		
		ExtremeWingStatsDevVpnIpsecSaTrafficSelectorEntry ::=
			SEQUENCE {
				extremeWingStatsDevVpnIpsecSaTrafficSelectorTsIndex
					Unsigned32, 
				extremeWingStatsDevVpnIpsecSaTrafficSelectorSourceSubnet
					DisplayString,
				extremeWingStatsDevVpnIpsecSaTrafficSelectorDestinationSubnet
					DisplayString,
				extremeWingStatsDevVpnIpsecSaTrafficSelectorSourcePort
					DisplayString,
				extremeWingStatsDevVpnIpsecSaTrafficSelectorDestinationPort
					DisplayString,
				extremeWingStatsDevVpnIpsecSaTrafficSelectorProtocol
					DisplayString
			 }

		-- 1.3.6.1.4.1.1916.2.131.50.1.4.2.11.3.1.1
		extremeWingStatsDevVpnIpsecSaTrafficSelectorTsIndex OBJECT-TYPE
			SYNTAX Unsigned32
			MAX-ACCESS read-only
			STATUS current
			DESCRIPTION
				"IPSec SA traffic selector table index.

				XPath: /extremeWing-stats/device[mac=key1]/vpn/ipsec_sa[peer=key2,spi_in=key2,spi_out=key2,protocol=key2]/
				traffic_selector[source_subnet=key3,destination_subnet=key3,source_port=key3,destination_port=key3,
				protocol=key3]/ts_index"
			::= { extremeWingStatsDevVpnIpsecSaTrafficSelectorEntry 1 }

		
		-- 1.3.6.1.4.1.1916.2.131.50.1.4.2.11.3.1.2
		extremeWingStatsDevVpnIpsecSaTrafficSelectorSourceSubnet OBJECT-TYPE
			SYNTAX DisplayString
			MAX-ACCESS read-only
			STATUS current
			DESCRIPTION
				"XPath: /extremeWing-stats/device[mac=key1]/vpn/ipsec_sa[peer=key2,spi_in=key2,spi_out=key2,protocol=key2]/
				traffic_selector[source_subnet=key3,destination_subnet=key3,source_port=key3,destination_port=key3,
				protocol=key3]/source_subnet"
			::= { extremeWingStatsDevVpnIpsecSaTrafficSelectorEntry 2 }

		
		-- 1.3.6.1.4.1.1916.2.131.50.1.4.2.11.3.1.3
		extremeWingStatsDevVpnIpsecSaTrafficSelectorDestinationSubnet OBJECT-TYPE
			SYNTAX DisplayString
			MAX-ACCESS read-only
			STATUS current
			DESCRIPTION
				"XPath: /extremeWing-stats/device[mac=key1]/vpn/ipsec_sa[peer=key2,spi_in=key2,spi_out=key2,protocol=key2]/
				traffic_selector[source_subnet=key3,destination_subnet=key3,source_port=key3,destination_port=key3,
				protocol=key3]/destination_subnet"
			::= { extremeWingStatsDevVpnIpsecSaTrafficSelectorEntry 3 }

		
		-- 1.3.6.1.4.1.1916.2.131.50.1.4.2.11.3.1.4
		extremeWingStatsDevVpnIpsecSaTrafficSelectorSourcePort OBJECT-TYPE
			SYNTAX DisplayString
			MAX-ACCESS read-only
			STATUS current
			DESCRIPTION
				"XPath: /extremeWing-stats/device[mac=key1]/vpn/ipsec_sa[peer=key2,spi_in=key2,spi_out=key2,protocol=key2]/
				traffic_selector[source_subnet=key3,destination_subnet=key3,source_port=key3,destination_port=key3,
				protocol=key3]/source_port"
			::= { extremeWingStatsDevVpnIpsecSaTrafficSelectorEntry 4 }

		
		-- 1.3.6.1.4.1.1916.2.131.50.1.4.2.11.3.1.5
		extremeWingStatsDevVpnIpsecSaTrafficSelectorDestinationPort OBJECT-TYPE
			SYNTAX DisplayString
			MAX-ACCESS read-only
			STATUS current
			DESCRIPTION
				"XPath: /extremeWing-stats/device[mac=key1]/vpn/ipsec_sa[peer=key2,spi_in=key2,spi_out=key2,protocol=key2]/
				traffic_selector[source_subnet=key3,destination_subnet=key3,source_port=key3,destination_port=key3,
				protocol=key3]/destination_port"
			::= { extremeWingStatsDevVpnIpsecSaTrafficSelectorEntry 5 }

		
		-- 1.3.6.1.4.1.1916.2.131.50.1.4.2.11.3.1.6
		extremeWingStatsDevVpnIpsecSaTrafficSelectorProtocol OBJECT-TYPE
			SYNTAX DisplayString
			MAX-ACCESS read-only
			STATUS current
			DESCRIPTION
				"XPath: /extremeWing-stats/device[mac=key1]/vpn/ipsec_sa[peer=key2,spi_in=key2,spi_out=key2,protocol=key2]/
				traffic_selector[source_subnet=key3,destination_subnet=key3,source_port=key3,destination_port=key3,
				protocol=key3]/protocol"
			::= { extremeWingStatsDevVpnIpsecSaTrafficSelectorEntry 6 }


-- CDP neighbors
-- /extremeWing-stats/device/cdp-neighbors
		-- 1.3.6.1.4.1.1916.2.131.50.1.4.2.17
		extremeWingStatsDevCdpNeighbor OBJECT IDENTIFIER ::= { extremeWingStatsDev 17 }

		
		-- 1.3.6.1.4.1.1916.2.131.50.1.4.2.17.1
		extremeWingStatsDevCdpNeighborTable OBJECT-TYPE
			SYNTAX SEQUENCE OF ExtremeWingStatsDevCdpNeighborEntry
			MAX-ACCESS not-accessible
			STATUS current
			DESCRIPTION
				"CDP neighbors
				
				/extremeWing-stats/device/cdp-neighbors"
			::= { extremeWingStatsDevCdpNeighbor 1 }

		
		-- 1.3.6.1.4.1.1916.2.131.50.1.4.2.17.1.1
		extremeWingStatsDevCdpNeighborEntry OBJECT-TYPE
			SYNTAX ExtremeWingStatsDevCdpNeighborEntry
			MAX-ACCESS not-accessible
			STATUS current
			DESCRIPTION
				"An entry in the table."
			INDEX { extremeWingStatsDevMac, extremeWingStatsDevCdpNeighborIndex }
			::= { extremeWingStatsDevCdpNeighborTable 1 }

		
		ExtremeWingStatsDevCdpNeighborEntry ::=
			SEQUENCE { 
				extremeWingStatsDevCdpNeighborIndex
					ExtremeWingIdentifier,
				extremeWingStatsDevCdpNeighborDevId
					DisplayString,
				extremeWingStatsDevCdpNeighborPlatform
					DisplayString,
				extremeWingStatsDevCdpNeighborIpList
					DisplayString,
				extremeWingStatsDevCdpNeighborPortId
					DisplayString,
				extremeWingStatsDevCdpNeighborTtl
					Unsigned32,
				extremeWingStatsDevCdpNeighborLocalPort
					DisplayString,
				extremeWingStatsDevCdpNeighborDuplex
					DisplayString,
				extremeWingStatsDevCdpNeighborAdvertisedVersion
					Unsigned32,
				extremeWingStatsDevCdpNeighborVtpDomain
					DisplayString,
				extremeWingStatsDevCdpNeighborNativeVlan
					Unsigned32,
				extremeWingStatsDevCdpNeighborUntrustedPortCos
					Unsigned32,
				extremeWingStatsDevCdpNeighborMgmtAddrList
					DisplayString,
				extremeWingStatsDevCdpNeighborVersion
					DisplayString
			 }

		-- 1.3.6.1.4.1.1916.2.131.50.1.4.2.17.1.1.1
		extremeWingStatsDevCdpNeighborIndex OBJECT-TYPE
			SYNTAX ExtremeWingIdentifier
			MAX-ACCESS read-only
			STATUS current
			DESCRIPTION
				"Unique ID for each neighbor in the form of Device ID:Local Port
				
				XPath: /extremeWing-stats/device[mac=key1]/cdp-neighbors[neighbor_id=key2]/neighbor_id"
			::= { extremeWingStatsDevCdpNeighborEntry 1 }

		
		-- 1.3.6.1.4.1.1916.2.131.50.1.4.2.17.1.1.2
		extremeWingStatsDevCdpNeighborDevId OBJECT-TYPE
			SYNTAX DisplayString
			MAX-ACCESS read-only
			STATUS current
			DESCRIPTION
				"Device ID
				
				XPath: /extremeWing-stats/device[mac=key1]/cdp-neighbors[neighbor_id=key2]/dev_id"
			::= { extremeWingStatsDevCdpNeighborEntry 2 }

		
		-- 1.3.6.1.4.1.1916.2.131.50.1.4.2.17.1.1.3
		extremeWingStatsDevCdpNeighborPlatform OBJECT-TYPE
			SYNTAX DisplayString
			MAX-ACCESS read-only
			STATUS current
			DESCRIPTION
				"Platform
				
				XPath: /extremeWing-stats/device[mac=key1]/cdp-neighbors[neighbor_id=key2]/platform"
			::= { extremeWingStatsDevCdpNeighborEntry 3 }

		
		-- 1.3.6.1.4.1.1916.2.131.50.1.4.2.17.1.1.4
		extremeWingStatsDevCdpNeighborIpList OBJECT-TYPE
			SYNTAX DisplayString
			MAX-ACCESS read-only
			STATUS current
			DESCRIPTION
				"IP addresses
				
				XPath: /extremeWing-stats/device[mac=key1]/cdp-neighbors[neighbor_id=key2]/ip_list"
			::= { extremeWingStatsDevCdpNeighborEntry 4 }

		
		-- 1.3.6.1.4.1.1916.2.131.50.1.4.2.17.1.1.5
		extremeWingStatsDevCdpNeighborPortId OBJECT-TYPE
			SYNTAX DisplayString
			MAX-ACCESS read-only
			STATUS current
			DESCRIPTION
				"Port ID (outgoing port)
				
				XPath: /extremeWing-stats/device[mac=key1]/cdp-neighbors[neighbor_id=key2]/port_id"
			::= { extremeWingStatsDevCdpNeighborEntry 5 }

		
		-- 1.3.6.1.4.1.1916.2.131.50.1.4.2.17.1.1.6
		extremeWingStatsDevCdpNeighborTtl OBJECT-TYPE
			SYNTAX Unsigned32
			MAX-ACCESS read-only
			STATUS current
			DESCRIPTION
				"Hold time
				
				XPath: /extremeWing-stats/device[mac=key1]/cdp-neighbors[neighbor_id=key2]/ttl"
			::= { extremeWingStatsDevCdpNeighborEntry 6 }

		
		-- 1.3.6.1.4.1.1916.2.131.50.1.4.2.17.1.1.7
		extremeWingStatsDevCdpNeighborLocalPort OBJECT-TYPE
			SYNTAX DisplayString
			MAX-ACCESS read-only
			STATUS current
			DESCRIPTION
				"Local port
				
				XPath: /extremeWing-stats/device[mac=key1]/cdp-neighbors[neighbor_id=key2]/local_port"
			::= { extremeWingStatsDevCdpNeighborEntry 7 }

		
		-- 1.3.6.1.4.1.1916.2.131.50.1.4.2.17.1.1.8
		extremeWingStatsDevCdpNeighborDuplex OBJECT-TYPE
			SYNTAX DisplayString
			MAX-ACCESS read-only
			STATUS current
			DESCRIPTION
				"Duplex
				
				Values:
				full,
				half
				
				XPath: /extremeWing-stats/device[mac=key1]/cdp-neighbors[neighbor_id=key2]/duplex"
			::= { extremeWingStatsDevCdpNeighborEntry 8 }

		
		-- 1.3.6.1.4.1.1916.2.131.50.1.4.2.17.1.1.9
		extremeWingStatsDevCdpNeighborAdvertisedVersion OBJECT-TYPE
			SYNTAX Unsigned32
			MAX-ACCESS read-only
			STATUS current
			DESCRIPTION
				"Advertisement Version
				
				XPath: /extremeWing-stats/device[mac=key1]/cdp-neighbors[neighbor_id=key2]/advertised_version"
			::= { extremeWingStatsDevCdpNeighborEntry 9 }

		
		-- 1.3.6.1.4.1.1916.2.131.50.1.4.2.17.1.1.10
		extremeWingStatsDevCdpNeighborVtpDomain OBJECT-TYPE
			SYNTAX DisplayString
			MAX-ACCESS read-only
			STATUS current
			DESCRIPTION
				"VTP Management Domain
				
				XPath: /extremeWing-stats/device[mac=key1]/cdp-neighbors[neighbor_id=key2]/vtp_domain"
			::= { extremeWingStatsDevCdpNeighborEntry 10 }

		
		-- 1.3.6.1.4.1.1916.2.131.50.1.4.2.17.1.1.11
		extremeWingStatsDevCdpNeighborNativeVlan OBJECT-TYPE
			SYNTAX Unsigned32
			MAX-ACCESS read-only
			STATUS current
			DESCRIPTION
				"Native VLAN
				
				XPath: /extremeWing-stats/device[mac=key1]/cdp-neighbors[neighbor_id=key2]/native_vlan"
			::= { extremeWingStatsDevCdpNeighborEntry 11 }

		
		-- 1.3.6.1.4.1.1916.2.131.50.1.4.2.17.1.1.12
		extremeWingStatsDevCdpNeighborUntrustedPortCos OBJECT-TYPE
			SYNTAX Unsigned32
			MAX-ACCESS read-only
			STATUS current
			DESCRIPTION
				"Untrusted port CoS
				
				XPath: /extremeWing-stats/device[mac=key1]/cdp-neighbors[neighbor_id=key2]/untrusted_port_cos"
			::= { extremeWingStatsDevCdpNeighborEntry 12 }

		
		-- 1.3.6.1.4.1.1916.2.131.50.1.4.2.17.1.1.13
		extremeWingStatsDevCdpNeighborMgmtAddrList OBJECT-TYPE
			SYNTAX DisplayString
			MAX-ACCESS read-only
			STATUS current
			DESCRIPTION
				"the list of management addresses separated by comma
				
				XPath: /extremeWing-stats/device[mac=key1]/cdp-neighbors[neighbor_id=key2]/mgmt_addr_list"
			::= { extremeWingStatsDevCdpNeighborEntry 13 }

		
		-- 1.3.6.1.4.1.1916.2.131.50.1.4.2.17.1.1.14
		extremeWingStatsDevCdpNeighborVersion OBJECT-TYPE
			SYNTAX DisplayString
			MAX-ACCESS read-only
			STATUS current
			DESCRIPTION
				"Version
				
				XPath: /extremeWing-stats/device[mac=key1]/cdp-neighbors[neighbor_id=key2]/version"
			::= { extremeWingStatsDevCdpNeighborEntry 14 }

		
-- Wireless statistics information on AP/Wireless Controller
-- /extremeWing-stats/device/wireless
		-- 1.3.6.1.4.1.1916.2.131.50.1.4.2.25
		extremeWingStatsDevWl OBJECT IDENTIFIER ::= { extremeWingStatsDev 25 }

		
-- /extremeWing-stats/device/wireless/ap-info
		-- 1.3.6.1.4.1.1916.2.131.50.1.4.2.25.1
		extremeWingStatsDevWlApInfo OBJECT IDENTIFIER ::= { extremeWingStatsDevWl 1 }

		
		-- 1.3.6.1.4.1.1916.2.131.50.1.4.2.25.1.1
		extremeWingStatsDevWlApInfoTable OBJECT-TYPE
			SYNTAX SEQUENCE OF ExtremeWingStatsDevWlApInfoEntry
			MAX-ACCESS not-accessible
			STATUS current
			DESCRIPTION
				"Status of managed Access Points
				
				/extremeWing-stats/device/wireless/ap-info"
			::= { extremeWingStatsDevWlApInfo 1 }

		
		-- 1.3.6.1.4.1.1916.2.131.50.1.4.2.25.1.1.1
		extremeWingStatsDevWlApInfoEntry OBJECT-TYPE
			SYNTAX ExtremeWingStatsDevWlApInfoEntry
			MAX-ACCESS not-accessible
			STATUS current
			DESCRIPTION
				"An entry in the table."
			INDEX { extremeWingStatsDevMac, extremeWingStatsDevWlApInfoMac }
			::= { extremeWingStatsDevWlApInfoTable 1 }

		
		ExtremeWingStatsDevWlApInfoEntry ::=
			SEQUENCE { 
				extremeWingStatsDevWlApInfoMac
					MacAddress,
				extremeWingStatsDevWlApInfoFaultDetected
					TruthValue,
				extremeWingStatsDevWlApInfoNumRadios
					Unsigned32,
				extremeWingStatsDevWlApInfoNumClients
					Unsigned32,
				extremeWingStatsDevWlApInfoLastCalTime
					DisplayString,
				extremeWingStatsDevWlApInfoType
					DisplayString,
				extremeWingStatsDevWlApInfoStatsMode
					DisplayString,
				extremeWingStatsDevWlApInfoStatsInterval
					Unsigned32,
				extremeWingStatsDevWlApInfoHostname
					DisplayString,
				extremeWingStatsDevWlApInfoRfDomainName
					DisplayString,
				extremeWingStatsDevWlApInfoLocation
					DisplayString,
				extremeWingStatsDevWlApInfoAdoptedTo
					MacAddress,
				extremeWingStatsDevWlApInfoIp
					DisplayString
			 }

		-- 1.3.6.1.4.1.1916.2.131.50.1.4.2.25.1.1.1.1
		extremeWingStatsDevWlApInfoMac OBJECT-TYPE
			SYNTAX MacAddress
			MAX-ACCESS read-only
			STATUS current
			DESCRIPTION
				"AP MAC address
				
				XPath: /extremeWing-stats/device[mac=key1]/wireless/ap-info[mac=key2]/mac"
			::= { extremeWingStatsDevWlApInfoEntry 1 }

		
		-- 1.3.6.1.4.1.1916.2.131.50.1.4.2.25.1.1.1.2
		extremeWingStatsDevWlApInfoFaultDetected OBJECT-TYPE
			SYNTAX TruthValue
			MAX-ACCESS read-only
			STATUS current
			DESCRIPTION
				"Whether any fault has been detected on the AP
				
				XPath: /extremeWing-stats/device[mac=key1]/wireless/ap-info[mac=key2]/fault_detected"
			::= { extremeWingStatsDevWlApInfoEntry 2 }

		
		-- 1.3.6.1.4.1.1916.2.131.50.1.4.2.25.1.1.1.3
		extremeWingStatsDevWlApInfoNumRadios OBJECT-TYPE
			SYNTAX Unsigned32
			MAX-ACCESS read-only
			STATUS current
			DESCRIPTION
				"Number of radios on the AP
				
				XPath: /extremeWing-stats/device[mac=key1]/wireless/ap-info[mac=key2]/num_radios"
			::= { extremeWingStatsDevWlApInfoEntry 3 }

		
		-- 1.3.6.1.4.1.1916.2.131.50.1.4.2.25.1.1.1.4
		extremeWingStatsDevWlApInfoNumClients OBJECT-TYPE
			SYNTAX Unsigned32
			MAX-ACCESS read-only
			STATUS current
			DESCRIPTION
				"Number of wireless clients on the AP
				
				XPath: /extremeWing-stats/device[mac=key1]/wireless/ap-info[mac=key2]/num_clients"
			::= { extremeWingStatsDevWlApInfoEntry 4 }

		
		-- 1.3.6.1.4.1.1916.2.131.50.1.4.2.25.1.1.1.5
		extremeWingStatsDevWlApInfoLastCalTime OBJECT-TYPE
			SYNTAX DisplayString (SIZE (0..64))
			MAX-ACCESS read-only
			STATUS current
			DESCRIPTION
				"Last Smart-RF Calibration time on the AP
				
				XPath: /extremeWing-stats/device[mac=key1]/wireless/ap-info[mac=key2]/last_cal_time"
			::= { extremeWingStatsDevWlApInfoEntry 5 }

		
		-- 1.3.6.1.4.1.1916.2.131.50.1.4.2.25.1.1.1.6
		extremeWingStatsDevWlApInfoType OBJECT-TYPE
			SYNTAX DisplayString (SIZE (0..32))
			MAX-ACCESS read-only
			STATUS current
			DESCRIPTION
				"AP device type
				
				XPath: /extremeWing-stats/device[mac=key1]/wireless/ap-info[mac=key2]/type"
			::= { extremeWingStatsDevWlApInfoEntry 6 }

		
		-- 1.3.6.1.4.1.1916.2.131.50.1.4.2.25.1.1.1.7
		extremeWingStatsDevWlApInfoStatsMode OBJECT-TYPE
			SYNTAX DisplayString (SIZE (0..32))
			MAX-ACCESS read-only
			STATUS current
			DESCRIPTION
				"Statistics update mode
				
				Values:
				auto
				fixed
				
				XPath: /extremeWing-stats/device[mac=key1]/wireless/ap-info[mac=key2]/stats_mode"
			::= { extremeWingStatsDevWlApInfoEntry 7 }

		
		-- 1.3.6.1.4.1.1916.2.131.50.1.4.2.25.1.1.1.8
		extremeWingStatsDevWlApInfoStatsInterval OBJECT-TYPE
			SYNTAX Unsigned32
			MAX-ACCESS read-only
			STATUS current
			DESCRIPTION
				"The current statistics update interval in seconds
				
				XPath: /extremeWing-stats/device[mac=key1]/wireless/ap-info[mac=key2]/stats_interval"
			::= { extremeWingStatsDevWlApInfoEntry 8 }

		
		-- 1.3.6.1.4.1.1916.2.131.50.1.4.2.25.1.1.1.9
		extremeWingStatsDevWlApInfoHostname OBJECT-TYPE
			SYNTAX DisplayString (SIZE (0..64))
			MAX-ACCESS read-only
			STATUS current
			DESCRIPTION
				"Hostname of the AP
				
				XPath: /extremeWing-stats/device[mac=key1]/wireless/ap-info[mac=key2]/hostname"
			::= { extremeWingStatsDevWlApInfoEntry 9 }

		
		-- 1.3.6.1.4.1.1916.2.131.50.1.4.2.25.1.1.1.10
		extremeWingStatsDevWlApInfoRfDomainName OBJECT-TYPE
			SYNTAX DisplayString (SIZE (0..64))
			MAX-ACCESS read-only
			STATUS current
			DESCRIPTION
				"RF Domain name of the AP
				
				XPath: /extremeWing-stats/device[mac=key1]/wireless/ap-info[mac=key2]/rf_domain_name"
			::= { extremeWingStatsDevWlApInfoEntry 10 }

		
		-- 1.3.6.1.4.1.1916.2.131.50.1.4.2.25.1.1.1.11
		extremeWingStatsDevWlApInfoLocation OBJECT-TYPE
			SYNTAX DisplayString (SIZE (0..64))
			MAX-ACCESS read-only
			STATUS current
			DESCRIPTION
				"Location description of the AP
				
				XPath: /extremeWing-stats/device[mac=key1]/wireless/ap-info[mac=key2]/location"
			::= { extremeWingStatsDevWlApInfoEntry 11 }

		
		-- 1.3.6.1.4.1.1916.2.131.50.1.4.2.25.1.1.1.12
		extremeWingStatsDevWlApInfoAdoptedTo OBJECT-TYPE
			SYNTAX MacAddress
			MAX-ACCESS read-only
			STATUS current
			DESCRIPTION
				"MAC address of the parent wireless controller that the AP
				is adopted to.
				
				XPath: /extremeWing-stats/device[mac=key1]/wireless/ap-info[mac=key2]/adopted_to"
			::= { extremeWingStatsDevWlApInfoEntry 12 }

		
		-- 1.3.6.1.4.1.1916.2.131.50.1.4.2.25.1.1.1.13
		extremeWingStatsDevWlApInfoIp OBJECT-TYPE
			SYNTAX DisplayString (SIZE (0..32))
			MAX-ACCESS read-only
			STATUS current
			DESCRIPTION
				"Adopted AP IP address
				
				XPath: /extremeWing-stats/device[mac=key1]/wireless/ap-info[mac=key2]/ip"
			::= { extremeWingStatsDevWlApInfoEntry 13 }

		
-- /extremeWing-stats/device/wireless/client
		-- 1.3.6.1.4.1.1916.2.131.50.1.4.2.25.3
		extremeWingStatsDevWlClient OBJECT IDENTIFIER ::= { extremeWingStatsDevWl 3 }

		
		-- 1.3.6.1.4.1.1916.2.131.50.1.4.2.25.3.1
		extremeWingStatsDevWlClientTable OBJECT-TYPE
			SYNTAX SEQUENCE OF ExtremeWingStatsDevWlClientEntry
			MAX-ACCESS not-accessible
			STATUS current
			DESCRIPTION
				"Status of wireless clients associated currently
				on AP/Wireless Controller.
				
				/extremeWing-stats/device/wireless/client"
			::= { extremeWingStatsDevWlClient 1 }

		
		-- 1.3.6.1.4.1.1916.2.131.50.1.4.2.25.3.1.1
		extremeWingStatsDevWlClientEntry OBJECT-TYPE
			SYNTAX ExtremeWingStatsDevWlClientEntry
			MAX-ACCESS not-accessible
			STATUS current
			DESCRIPTION
				"An entry in the table"
			INDEX { extremeWingStatsDevMac, extremeWingStatsDevWlClientMac }
			::= { extremeWingStatsDevWlClientTable 1 }

		
		ExtremeWingStatsDevWlClientEntry ::=
			SEQUENCE { 
				extremeWingStatsDevWlClientMac
					MacAddress,
				extremeWingStatsDevWlClientMacName
					DisplayString,
				extremeWingStatsDevWlClientVendor
					DisplayString,
				extremeWingStatsDevWlClientBss
					MacAddress,
				extremeWingStatsDevWlClientAp
					MacAddress,
				extremeWingStatsDevWlClientRadioNum
					Unsigned32,
				extremeWingStatsDevWlClientRadioType
					DisplayString,
				extremeWingStatsDevWlClientRadioEnc
					DisplayString,
				extremeWingStatsDevWlClientRadioAuth
					DisplayString,
				extremeWingStatsDevWlClientWlan
					DisplayString,
				extremeWingStatsDevWlClientState
					DisplayString,
				extremeWingStatsDevWlClientHotspotAuthed
					TruthValue,
				extremeWingStatsDevWlClientVlan
					Unsigned32,
				extremeWingStatsDevWlClientUserName
					DisplayString,
				extremeWingStatsDevWlClientIp
					DisplayString,
				extremeWingStatsDevWlClientRfdName
					DisplayString,
				extremeWingStatsDevWlClientHostname
					DisplayString,
				extremeWingStatsDevWlClientLocation
					DisplayString,
				extremeWingStatsDevWlClientRadioId
					DisplayString,
				extremeWingStatsDevWlClientRadioAlias
					DisplayString
			 }

		-- 1.3.6.1.4.1.1916.2.131.50.1.4.2.25.3.1.1.1
		extremeWingStatsDevWlClientMac OBJECT-TYPE
			SYNTAX MacAddress
			MAX-ACCESS read-only
			STATUS current
			DESCRIPTION
				"Client MAC
				
				XPath: /extremeWing-stats/device[mac=key1]/wireless/client[mac=key2]/mac"
			::= { extremeWingStatsDevWlClientEntry 1 }

		
		-- 1.3.6.1.4.1.1916.2.131.50.1.4.2.25.3.1.1.2
		extremeWingStatsDevWlClientMacName OBJECT-TYPE
			SYNTAX DisplayString
			MAX-ACCESS read-only
			STATUS current
			DESCRIPTION
				"Hostname of the client which could be obtained from
				packet sniffing or by manually configured via
				mac-name configuration.
				
				XPath: /extremeWing-stats/device[mac=key1]/wireless/client[mac=key2]/hostname"
			::= { extremeWingStatsDevWlClientEntry 2 }

		
		-- 1.3.6.1.4.1.1916.2.131.50.1.4.2.25.3.1.1.3
		extremeWingStatsDevWlClientVendor OBJECT-TYPE
			SYNTAX DisplayString
			MAX-ACCESS read-only
			STATUS current
			DESCRIPTION
				"Client vendor name based on the MAC OUI lookup
				
				XPath: /extremeWing-stats/device[mac=key1]/wireless/client[mac=key2]/vendor"
			::= { extremeWingStatsDevWlClientEntry 3 }

		
		-- 1.3.6.1.4.1.1916.2.131.50.1.4.2.25.3.1.1.4
		extremeWingStatsDevWlClientBss OBJECT-TYPE
			SYNTAX MacAddress
			MAX-ACCESS read-only
			STATUS current
			DESCRIPTION
				"BSSID where the client is associated
				
				XPath: /extremeWing-stats/device[mac=key1]/wireless/client[mac=key2]/bss"
			::= { extremeWingStatsDevWlClientEntry 4 }

		
		-- 1.3.6.1.4.1.1916.2.131.50.1.4.2.25.3.1.1.5
		extremeWingStatsDevWlClientAp OBJECT-TYPE
			SYNTAX MacAddress
			MAX-ACCESS read-only
			STATUS current
			DESCRIPTION
				"MAC address of the AP where the client is associated
				
				XPath: /extremeWing-stats/device[mac=key1]/wireless/client[mac=key2]/ap"
			::= { extremeWingStatsDevWlClientEntry 5 }

		
		-- 1.3.6.1.4.1.1916.2.131.50.1.4.2.25.3.1.1.6
		extremeWingStatsDevWlClientRadioNum OBJECT-TYPE
			SYNTAX Unsigned32
			MAX-ACCESS read-only
			STATUS current
			DESCRIPTION
				"Radio number on AP where the client is associated
				
				XPath: /extremeWing-stats/device[mac=key1]/wireless/client[mac=key2]/radio_num"
			::= { extremeWingStatsDevWlClientEntry 6 }

		
		-- 1.3.6.1.4.1.1916.2.131.50.1.4.2.25.3.1.1.7
		extremeWingStatsDevWlClientRadioType OBJECT-TYPE
			SYNTAX DisplayString
			MAX-ACCESS read-only
			STATUS current
			DESCRIPTION
				"802.11 radio-type of the client
				
				XPath: /extremeWing-stats/device[mac=key1]/wireless/client[mac=key2]/radio_type"
			::= { extremeWingStatsDevWlClientEntry 7 }

		
		-- 1.3.6.1.4.1.1916.2.131.50.1.4.2.25.3.1.1.8
		extremeWingStatsDevWlClientRadioEnc OBJECT-TYPE
			SYNTAX DisplayString
			MAX-ACCESS read-only
			STATUS current
			DESCRIPTION
				"Encryption type
				
				XPath: /extremeWing-stats/device[mac=key1]/wireless/client[mac=key2]/enc"
			::= { extremeWingStatsDevWlClientEntry 8 }

		
		-- 1.3.6.1.4.1.1916.2.131.50.1.4.2.25.3.1.1.9
		extremeWingStatsDevWlClientRadioAuth OBJECT-TYPE
			SYNTAX DisplayString
			MAX-ACCESS read-only
			STATUS current
			DESCRIPTION
				"Authentication type
				
				XPath: /extremeWing-stats/device[mac=key1]/wireless/client[mac=key2]/auth"
			::= { extremeWingStatsDevWlClientEntry 9 }

		
		-- 1.3.6.1.4.1.1916.2.131.50.1.4.2.25.3.1.1.10
		extremeWingStatsDevWlClientWlan OBJECT-TYPE
			SYNTAX DisplayString
			MAX-ACCESS read-only
			STATUS current
			DESCRIPTION
				"WLAN where the client is associated
				
				XPath: /extremeWing-stats/device[mac=key1]/wireless/client[mac=key2]/wlan"
			::= { extremeWingStatsDevWlClientEntry 10 }

		
		-- 1.3.6.1.4.1.1916.2.131.50.1.4.2.25.3.1.1.11
		extremeWingStatsDevWlClientState OBJECT-TYPE
			SYNTAX DisplayString
			MAX-ACCESS read-only
			STATUS current
			DESCRIPTION
				"Current state of the client
				
				XPath: /extremeWing-stats/device[mac=key1]/wireless/client[mac=key2]/state"
			::= { extremeWingStatsDevWlClientEntry 11 }

		
		-- 1.3.6.1.4.1.1916.2.131.50.1.4.2.25.3.1.1.12
		extremeWingStatsDevWlClientHotspotAuthed OBJECT-TYPE
			SYNTAX TruthValue
			MAX-ACCESS read-only
			STATUS current
			DESCRIPTION
				"Whether the client has succeeded in guest access
				authentication.
				
				XPath: /extremeWing-stats/device[mac=key1]/wireless/client[mac=key2]/hotspot_authed"
			::= { extremeWingStatsDevWlClientEntry 12 }

		
		-- 1.3.6.1.4.1.1916.2.131.50.1.4.2.25.3.1.1.13
		extremeWingStatsDevWlClientVlan OBJECT-TYPE
			SYNTAX Unsigned32
			MAX-ACCESS read-only
			STATUS current
			DESCRIPTION
				"The VLAN assigned to the client
				
				XPath: /extremeWing-stats/device[mac=key1]/wireless/client[mac=key2]/vlan"
			::= { extremeWingStatsDevWlClientEntry 13 }

		
		-- 1.3.6.1.4.1.1916.2.131.50.1.4.2.25.3.1.1.14
		extremeWingStatsDevWlClientUserName OBJECT-TYPE
			SYNTAX DisplayString
			MAX-ACCESS read-only
			STATUS current
			DESCRIPTION
				"Username of the client, if available
				
				XPath: /extremeWing-stats/device[mac=key1]/wireless/client[mac=key2]/username"
			::= { extremeWingStatsDevWlClientEntry 14 }

		
		-- 1.3.6.1.4.1.1916.2.131.50.1.4.2.25.3.1.1.15
		extremeWingStatsDevWlClientIp OBJECT-TYPE
			SYNTAX DisplayString
			MAX-ACCESS read-only
			STATUS current
			DESCRIPTION
				"IP address of the client (if known)
				
				XPath: /extremeWing-stats/device[mac=key1]/wireless/client[mac=key2]/ip"
			::= { extremeWingStatsDevWlClientEntry 15 }

		
		-- 1.3.6.1.4.1.1916.2.131.50.1.4.2.25.3.1.1.16
		extremeWingStatsDevWlClientRfdName OBJECT-TYPE
			SYNTAX DisplayString
			MAX-ACCESS read-only
			STATUS current
			DESCRIPTION
				"RF Domain that the client is in
				
				XPath: /extremeWing-stats/device[mac=key1]/wireless/client[mac=key2]/rf_domain_name"
			::= { extremeWingStatsDevWlClientEntry 16 }

		
		-- 1.3.6.1.4.1.1916.2.131.50.1.4.2.25.3.1.1.17
		extremeWingStatsDevWlClientHostname OBJECT-TYPE
			SYNTAX DisplayString
			MAX-ACCESS read-only
			STATUS current
			DESCRIPTION
				"Hostname of the AP the client is associated to
				
				XPath: /extremeWing-stats/device[mac=key1]/wireless/client[mac=key2]/ap_hostname"
			::= { extremeWingStatsDevWlClientEntry 17 }

		
		-- 1.3.6.1.4.1.1916.2.131.50.1.4.2.25.3.1.1.18
		extremeWingStatsDevWlClientLocation OBJECT-TYPE
			SYNTAX DisplayString
			MAX-ACCESS read-only
			STATUS current
			DESCRIPTION
				"Location of the AP the client is associated to.
				
				XPath: /extremeWing-stats/device[mac=key1]/wireless/client[mac=key2]/location"
			::= { extremeWingStatsDevWlClientEntry 18 }

		
		-- 1.3.6.1.4.1.1916.2.131.50.1.4.2.25.3.1.1.19
		extremeWingStatsDevWlClientRadioId OBJECT-TYPE
			SYNTAX DisplayString
			MAX-ACCESS read-only
			STATUS current
			DESCRIPTION
				"Unique ID for its associated radio in the form of
				AP-MAC:R%d. E.g., 00-A0-F8-00-00-00:R1
				
				XPath: /extremeWing-stats/device[mac=key1]/wireless/client[mac=key2]/radio_id"
			::= { extremeWingStatsDevWlClientEntry 19 }

		
		-- 1.3.6.1.4.1.1916.2.131.50.1.4.2.25.3.1.1.20
		extremeWingStatsDevWlClientRadioAlias OBJECT-TYPE
			SYNTAX DisplayString
			MAX-ACCESS read-only
			STATUS current
			DESCRIPTION
				"A radio ID alias of its associated radio in the form of
				hostname:R%d. E.g., wm3400-22A24E:R1
				
				XPath: /extremeWing-stats/device[mac=key1]/wireless/client[mac=key2]/radio_alias"
			::= { extremeWingStatsDevWlClientEntry 20 }

		
-- /extremeWing-stats/device/wireless/client-stats
		-- 1.3.6.1.4.1.1916.2.131.50.1.4.2.25.5
		extremeWingStatsDevWlClientStat OBJECT IDENTIFIER ::= { extremeWingStatsDevWl 5 }

		
		-- 1.3.6.1.4.1.1916.2.131.50.1.4.2.25.5.1
		extremeWingStatsDevWlClientStatTable OBJECT-TYPE
			SYNTAX SEQUENCE OF ExtremeWingStatsDevWlClientStatEntry
			MAX-ACCESS not-accessible
			STATUS current
			DESCRIPTION
				"Statistical information of wireless clients associated
				currently.
				
				/extremeWing-stats/device/wireless/client-stats"
			::= { extremeWingStatsDevWlClientStat 1 }

		
		-- 1.3.6.1.4.1.1916.2.131.50.1.4.2.25.5.1.1
		extremeWingStatsDevWlClientStatEntry OBJECT-TYPE
			SYNTAX ExtremeWingStatsDevWlClientStatEntry
			MAX-ACCESS not-accessible
			STATUS current
			DESCRIPTION
				"An entry in the table."
			INDEX { extremeWingStatsDevMac, extremeWingStatsDevWlClientStatMac }
			::= { extremeWingStatsDevWlClientStatTable 1 }

		
		ExtremeWingStatsDevWlClientStatEntry ::=
			SEQUENCE { 
				extremeWingStatsDevWlClientStatMac
					MacAddress,
				extremeWingStatsDevWlClientStatMacName
					DisplayString,
				extremeWingStatsDevWlClientStatVendor
					DisplayString,
				extremeWingStatsDevWlClientStatAp
					MacAddress,
				extremeWingStatsDevWlClientStatTxBytes
					Counter64,
				extremeWingStatsDevWlClientStatRxBytes
					Counter64,
				extremeWingStatsDevWlClientStatTxPkts
					Counter64,
				extremeWingStatsDevWlClientStatRxPkts
					Counter64,
				extremeWingStatsDevWlClientStatTxDropped
					Counter64,
				extremeWingStatsDevWlClientStatRxErrors
					Counter64,
				extremeWingStatsDevWlClientStatTIndex
					Integer32,
				extremeWingStatsDevWlClientStatTxBps
					Unsigned32,
				extremeWingStatsDevWlClientStatRxBps
					Unsigned32,
				extremeWingStatsDevWlClientStatSignal
					Integer32,
				extremeWingStatsDevWlClientStatNoise
					Integer32,
				extremeWingStatsDevWlClientStatSnr
					Integer32,
				extremeWingStatsDevWlClientStatTxRate
					Unsigned32,
				extremeWingStatsDevWlClientStatRxRate
					Unsigned32,
				extremeWingStatsDevWlClientStatErrorRate
					Unsigned32,
				extremeWingStatsDevWlClientStatQIndex
					Integer32
			 }

		-- 1.3.6.1.4.1.1916.2.131.50.1.4.2.25.5.1.1.1
		extremeWingStatsDevWlClientStatMac OBJECT-TYPE
			SYNTAX MacAddress
			MAX-ACCESS read-only
			STATUS current
			DESCRIPTION
				"Client MAC
				
				XPath: /extremeWing-stats/device[mac=key1]/wireless/client-stats[mac=key2]/mac"
			::= { extremeWingStatsDevWlClientStatEntry 1 }

		
		-- 1.3.6.1.4.1.1916.2.131.50.1.4.2.25.5.1.1.2
		extremeWingStatsDevWlClientStatMacName OBJECT-TYPE
			SYNTAX DisplayString (SIZE (0..64))
			MAX-ACCESS read-only
			STATUS current
			DESCRIPTION
				"Hostname of the client which could be obtained from
				packet sniffing or by manually configured via
				mac-name configuration.
				
				XPath: /extremeWing-stats/device[mac=key1]/wireless/client-stats[mac=key2]/hostname"
			::= { extremeWingStatsDevWlClientStatEntry 2 }

		
		-- 1.3.6.1.4.1.1916.2.131.50.1.4.2.25.5.1.1.3
		extremeWingStatsDevWlClientStatVendor OBJECT-TYPE
			SYNTAX DisplayString (SIZE (0..64))
			MAX-ACCESS read-only
			STATUS current
			DESCRIPTION
				"Client vendor name based on the MAC OUI lookup
				
				XPath: /extremeWing-stats/device[mac=key1]/wireless/client-stats[mac=key2]/vendor"
			::= { extremeWingStatsDevWlClientStatEntry 3 }

		
		-- 1.3.6.1.4.1.1916.2.131.50.1.4.2.25.5.1.1.4
		extremeWingStatsDevWlClientStatAp OBJECT-TYPE
			SYNTAX MacAddress
			MAX-ACCESS read-only
			STATUS current
			DESCRIPTION
				"MAC address of AP where the client is associated.
				
				XPath: /extremeWing-stats/device[mac=key1]/wireless/client-stats[mac=key2]/ap"
			::= { extremeWingStatsDevWlClientStatEntry 4 }

		
		-- 1.3.6.1.4.1.1916.2.131.50.1.4.2.25.5.1.1.5
		extremeWingStatsDevWlClientStatTxBytes OBJECT-TYPE
			SYNTAX Counter64
			MAX-ACCESS read-only
			STATUS current
			DESCRIPTION
				"Number of data bytes transmitted from AP to client
				
				XPath: /extremeWing-stats/device[mac=key1]/wireless/client-stats[mac=key2]/tx_bytes"
			::= { extremeWingStatsDevWlClientStatEntry 5 }

		
		-- 1.3.6.1.4.1.1916.2.131.50.1.4.2.25.5.1.1.6
		extremeWingStatsDevWlClientStatRxBytes OBJECT-TYPE
			SYNTAX Counter64
			MAX-ACCESS read-only
			STATUS current
			DESCRIPTION
				"Number of data bytes received from client to AP
				
				XPath: /extremeWing-stats/device[mac=key1]/wireless/client-stats[mac=key2]/rx_bytes"
			::= { extremeWingStatsDevWlClientStatEntry 6 }

		
		-- 1.3.6.1.4.1.1916.2.131.50.1.4.2.25.5.1.1.7
		extremeWingStatsDevWlClientStatTxPkts OBJECT-TYPE
			SYNTAX Counter64
			MAX-ACCESS read-only
			STATUS current
			DESCRIPTION
				"Number of packets of data transmitted from AP to client
				
				XPath: /extremeWing-stats/device[mac=key1]/wireless/client-stats[mac=key2]/tx_pkts"
			::= { extremeWingStatsDevWlClientStatEntry 7 }

		
		-- 1.3.6.1.4.1.1916.2.131.50.1.4.2.25.5.1.1.8
		extremeWingStatsDevWlClientStatRxPkts OBJECT-TYPE
			SYNTAX Counter64
			MAX-ACCESS read-only
			STATUS current
			DESCRIPTION
				"Number of packets of data received from client to AP
				
				XPath: /extremeWing-stats/device[mac=key1]/wireless/client-stats[mac=key2]/rx_pkts"
			::= { extremeWingStatsDevWlClientStatEntry 8 }

		
		-- 1.3.6.1.4.1.1916.2.131.50.1.4.2.25.5.1.1.9
		extremeWingStatsDevWlClientStatTxDropped OBJECT-TYPE
			SYNTAX Counter64
			MAX-ACCESS read-only
			STATUS current
			DESCRIPTION
				"Number of packets of data dropped on transmission
				
				XPath: /extremeWing-stats/device[mac=key1]/wireless/client-stats[mac=key2]/tx_dropped"
			::= { extremeWingStatsDevWlClientStatEntry 9 }

		
		-- 1.3.6.1.4.1.1916.2.131.50.1.4.2.25.5.1.1.10
		extremeWingStatsDevWlClientStatRxErrors OBJECT-TYPE
			SYNTAX Counter64
			MAX-ACCESS read-only
			STATUS current
			DESCRIPTION
				"Number of packets of data received with errors
				
				XPath: /extremeWing-stats/device[mac=key1]/wireless/client-stats[mac=key2]/rx_errors"
			::= { extremeWingStatsDevWlClientStatEntry 10 }

		
		-- 1.3.6.1.4.1.1916.2.131.50.1.4.2.25.5.1.1.11
		extremeWingStatsDevWlClientStatTIndex OBJECT-TYPE
			SYNTAX Integer32
			MAX-ACCESS read-only
			STATUS current
			DESCRIPTION
				"Traffic Utilization Index
				
				Measures the efficiency the medium under consideration
				is used. It is the percentage of the current data throughput
				over the theoretical data rate limit, which is derived
				the current maximum physical rate configured over the medium
				based on past empirical data. This index could assist end user
				in site planning and expansion. The numerical value might be
				further classified as:
				  -1: no data available ( e.g. radio is not in wlan operation
				                          mode )
				  0-20 : very low utilization
				  20-40: low utilization
				  40-60: moderate utilization
				  60 and above: high utilization
				
				XPath: /extremeWing-stats/device[mac=key1]/wireless/client-stats[mac=key2]/t_index"
			::= { extremeWingStatsDevWlClientStatEntry 11 }

		
		-- 1.3.6.1.4.1.1916.2.131.50.1.4.2.25.5.1.1.12
		extremeWingStatsDevWlClientStatTxBps OBJECT-TYPE
			SYNTAX Unsigned32
			UNITS "kbps"
			MAX-ACCESS read-only
			STATUS current
			DESCRIPTION
				"User data transmit rate
				
				XPath: /extremeWing-stats/device[mac=key1]/wireless/client-stats[mac=key2]/tx_bps"
			::= { extremeWingStatsDevWlClientStatEntry 12 }

		
		-- 1.3.6.1.4.1.1916.2.131.50.1.4.2.25.5.1.1.13
		extremeWingStatsDevWlClientStatRxBps OBJECT-TYPE
			SYNTAX Unsigned32
			UNITS "kbps"
			MAX-ACCESS read-only
			STATUS current
			DESCRIPTION
				"User data receive rate
				
				XPath: /extremeWing-stats/device[mac=key1]/wireless/client-stats[mac=key2]/rx_bps"
			::= { extremeWingStatsDevWlClientStatEntry 13 }

		
		-- 1.3.6.1.4.1.1916.2.131.50.1.4.2.25.5.1.1.14
		extremeWingStatsDevWlClientStatSignal OBJECT-TYPE
			SYNTAX Integer32
			UNITS "dbm"
			MAX-ACCESS read-only
			STATUS current
			DESCRIPTION
				"Signal strength
				
				XPath: /extremeWing-stats/device[mac=key1]/wireless/client-stats[mac=key2]/signal"
			::= { extremeWingStatsDevWlClientStatEntry 14 }

		
		-- 1.3.6.1.4.1.1916.2.131.50.1.4.2.25.5.1.1.15
		extremeWingStatsDevWlClientStatNoise OBJECT-TYPE
			SYNTAX Integer32
			UNITS "dbm"
			MAX-ACCESS read-only
			STATUS current
			DESCRIPTION
				"Noise level in units of dbm
				
				XPath: /extremeWing-stats/device[mac=key1]/wireless/client-stats[mac=key2]/noise"
			::= { extremeWingStatsDevWlClientStatEntry 15 }

		
		-- 1.3.6.1.4.1.1916.2.131.50.1.4.2.25.5.1.1.16
		extremeWingStatsDevWlClientStatSnr OBJECT-TYPE
			SYNTAX Integer32
			UNITS "db"
			MAX-ACCESS read-only
			STATUS current
			DESCRIPTION
				"Signal to noise ratio in units of db
				
				XPath: /extremeWing-stats/device[mac=key1]/wireless/client-stats[mac=key2]/snr"
			::= { extremeWingStatsDevWlClientStatEntry 16 }

		
		-- 1.3.6.1.4.1.1916.2.131.50.1.4.2.25.5.1.1.17
		extremeWingStatsDevWlClientStatTxRate OBJECT-TYPE
			SYNTAX Unsigned32
			UNITS "Mbps"
			MAX-ACCESS read-only
			STATUS current
			DESCRIPTION
				"The effective phy-layer transmit rate
				
				XPath: /extremeWing-stats/device[mac=key1]/wireless/client-stats[mac=key2]/tx_rate"
			::= { extremeWingStatsDevWlClientStatEntry 17 }

		
		-- 1.3.6.1.4.1.1916.2.131.50.1.4.2.25.5.1.1.18
		extremeWingStatsDevWlClientStatRxRate OBJECT-TYPE
			SYNTAX Unsigned32
			UNITS "Mbps"
			MAX-ACCESS read-only
			STATUS current
			DESCRIPTION
				"The effective phy-layer receive rate
				
				XPath: /extremeWing-stats/device[mac=key1]/wireless/client-stats[mac=key2]/rx_rate"
			::= { extremeWingStatsDevWlClientStatEntry 18 }

		
		-- 1.3.6.1.4.1.1916.2.131.50.1.4.2.25.5.1.1.19
		extremeWingStatsDevWlClientStatErrorRate OBJECT-TYPE
			SYNTAX Unsigned32
			MAX-ACCESS read-only
			STATUS current
			DESCRIPTION
				"Ratio of errors to rx-packets in percentage
				
				XPath: /extremeWing-stats/device[mac=key1]/wireless/client-stats[mac=key2]/error_rate"
			::= { extremeWingStatsDevWlClientStatEntry 19 }

		
		-- 1.3.6.1.4.1.1916.2.131.50.1.4.2.25.5.1.1.20
		extremeWingStatsDevWlClientStatQIndex OBJECT-TYPE
			SYNTAX Integer32
			MAX-ACCESS read-only
			STATUS current
			DESCRIPTION
				"RF quality Index
				
				Measure the quality of the medium in percentage. It is a
				function of average retries and error rate. Its range is from
				0-100. Typically:
				  -1: no data available ( e.g. radio is not in wlan operation
				                          mode )
				  0-20: very poor quality
				  20-40: poor quality
				  40-60: average quality
				  60-100: good quality
				
				XPath: /extremeWing-stats/device[mac=key1]/wireless/client-stats[mac=key2]/q_index"
			::= { extremeWingStatsDevWlClientStatEntry 20 }

		
-- /extremeWing-stats/device/wireless/radio
		-- 1.3.6.1.4.1.1916.2.131.50.1.4.2.25.9
		extremeWingStatsDevWlRadio OBJECT IDENTIFIER ::= { extremeWingStatsDevWl 9 }

		
		-- 1.3.6.1.4.1.1916.2.131.50.1.4.2.25.9.1
		extremeWingStatsDevWlRadioTable OBJECT-TYPE
			SYNTAX SEQUENCE OF ExtremeWingStatsDevWlRadioEntry
			MAX-ACCESS not-accessible
			STATUS current
			DESCRIPTION
				"Status of radios on AP
				
				/extremeWing-stats/device/wireless/radio"
			::= { extremeWingStatsDevWlRadio 1 }

		
		-- 1.3.6.1.4.1.1916.2.131.50.1.4.2.25.9.1.1
		extremeWingStatsDevWlRadioEntry OBJECT-TYPE
			SYNTAX ExtremeWingStatsDevWlRadioEntry
			MAX-ACCESS not-accessible
			STATUS current
			DESCRIPTION
				"An entry in the table."
			INDEX { extremeWingStatsDevMac, extremeWingStatsDevWlRadioId }
			::= { extremeWingStatsDevWlRadioTable 1 }

		
		ExtremeWingStatsDevWlRadioEntry ::=
			SEQUENCE { 
				extremeWingStatsDevWlRadioId
					ExtremeWingIdentifier,
				extremeWingStatsDevWlRadioDeviceMac
					MacAddress,
				extremeWingStatsDevWlRadioAlias
					ExtremeWingIdentifier,
				extremeWingStatsDevWlRadioMac
					MacAddress,
				extremeWingStatsDevWlRadioType
					DisplayString,
				extremeWingStatsDevWlRadioHostname
					DisplayString,
				extremeWingStatsDevWlRadioRfdName
					DisplayString,
				extremeWingStatsDevWlRadioLocation
					DisplayString,
				extremeWingStatsDevWlRadioState
					DisplayString,
				extremeWingStatsDevWlRadioCurChannel
					DisplayString,
				extremeWingStatsDevWlRadioConfigChannel
					DisplayString,
				extremeWingStatsDevWlRadioCurPower
					Unsigned32,
				extremeWingStatsDevWlRadioConfigPower
					DisplayString,
				extremeWingStatsDevWlRadioMaxUserRate
					Counter64,
				extremeWingStatsDevWlRadioNumClient
					Unsigned32,
				extremeWingStatsDevWlRadioProtocol
					Unsigned32
			 }

		-- 1.3.6.1.4.1.1916.2.131.50.1.4.2.25.9.1.1.1
		extremeWingStatsDevWlRadioId OBJECT-TYPE
			SYNTAX ExtremeWingIdentifier
			MAX-ACCESS read-only
			STATUS current
			DESCRIPTION
				"Unique ID for each radio interface in the form of
				AP-MAC:R%d. E.g., 00-A0-F8-00-00-00:R1
				
				XPath: /extremeWing-stats/device[mac=key1]/wireless/radio[radio_id=key2]/radio_id"
			::= { extremeWingStatsDevWlRadioEntry 1 }

		
		-- 1.3.6.1.4.1.1916.2.131.50.1.4.2.25.9.1.1.2
		extremeWingStatsDevWlRadioDeviceMac OBJECT-TYPE
			SYNTAX MacAddress
			MAX-ACCESS read-only
			STATUS current
			DESCRIPTION
				"MAC address of the AP the radio belongs to.
				
				XPath: /extremeWing-stats/device[mac=key1]/wireless/radio[radio_id=key2]/device_mac"
			::= { extremeWingStatsDevWlRadioEntry 2 }

		
		-- 1.3.6.1.4.1.1916.2.131.50.1.4.2.25.9.1.1.3
		extremeWingStatsDevWlRadioAlias OBJECT-TYPE
			SYNTAX ExtremeWingIdentifier
			MAX-ACCESS read-only
			STATUS current
			DESCRIPTION
				"An alias to radio id in the form of hostname:R%d.
				E.g., wm3400-22A24E:R1
				
				XPath: /extremeWing-stats/device[mac=key1]/wireless/radio[radio_id=key2]/radio_alias"
			::= { extremeWingStatsDevWlRadioEntry 3 }

		
		-- 1.3.6.1.4.1.1916.2.131.50.1.4.2.25.9.1.1.4
		extremeWingStatsDevWlRadioMac OBJECT-TYPE
			SYNTAX MacAddress
			MAX-ACCESS read-only
			STATUS current
			DESCRIPTION
				"MAC address of the radio interface
				
				XPath: /extremeWing-stats/device[mac=key1]/wireless/radio[radio_id=key2]/radio_mac"
			::= { extremeWingStatsDevWlRadioEntry 4 }

		
		-- 1.3.6.1.4.1.1916.2.131.50.1.4.2.25.9.1.1.5
		extremeWingStatsDevWlRadioType OBJECT-TYPE
			SYNTAX DisplayString (SIZE (0..64))
			MAX-ACCESS read-only
			STATUS current
			DESCRIPTION
				"802.11 radio-type
				
				Values:
				2.4GHz-wlan
				5GHz-wlan
				sensor
				
				XPath: /extremeWing-stats/device[mac=key1]/wireless/radio[radio_id=key2]/radio_type"
			::= { extremeWingStatsDevWlRadioEntry 5 }

		
		-- 1.3.6.1.4.1.1916.2.131.50.1.4.2.25.9.1.1.6
		extremeWingStatsDevWlRadioHostname OBJECT-TYPE
			SYNTAX DisplayString (SIZE (0..64))
			MAX-ACCESS read-only
			STATUS current
			DESCRIPTION
				"Hostname of the AP device
				
				XPath: /extremeWing-stats/device[mac=key1]/wireless/radio[radio_id=key2]/hostname"
			::= { extremeWingStatsDevWlRadioEntry 6 }

		
		-- 1.3.6.1.4.1.1916.2.131.50.1.4.2.25.9.1.1.7
		extremeWingStatsDevWlRadioRfdName OBJECT-TYPE
			SYNTAX DisplayString (SIZE (0..64))
			MAX-ACCESS read-only
			STATUS current
			DESCRIPTION
				"RF Domain name of the AP device
				
				XPath: /extremeWing-stats/device[mac=key1]/wireless/radio[radio_id=key2]/rf_domain_name"
			::= { extremeWingStatsDevWlRadioEntry 7 }

		
		-- 1.3.6.1.4.1.1916.2.131.50.1.4.2.25.9.1.1.8
		extremeWingStatsDevWlRadioLocation OBJECT-TYPE
			SYNTAX DisplayString (SIZE (0..64))
			MAX-ACCESS read-only
			STATUS current
			DESCRIPTION
				"Location description of the AP device
				
				XPath: /extremeWing-stats/device[mac=key1]/wireless/radio[radio_id=key2]/location"
			::= { extremeWingStatsDevWlRadioEntry 8 }

		
		-- 1.3.6.1.4.1.1916.2.131.50.1.4.2.25.9.1.1.9
		extremeWingStatsDevWlRadioState OBJECT-TYPE
			SYNTAX DisplayString (SIZE (0..64))
			MAX-ACCESS read-only
			STATUS current
			DESCRIPTION
				"Radio state
				
				XPath: /extremeWing-stats/device[mac=key1]/wireless/radio[radio_id=key2]/state"
			::= { extremeWingStatsDevWlRadioEntry 9 }

		
		-- 1.3.6.1.4.1.1916.2.131.50.1.4.2.25.9.1.1.10
		extremeWingStatsDevWlRadioCurChannel OBJECT-TYPE
			SYNTAX DisplayString (SIZE (0..16))
			MAX-ACCESS read-only
			STATUS current
			DESCRIPTION
				"Current channel the radio is operating at
				
				XPath: /extremeWing-stats/device[mac=key1]/wireless/radio[radio_id=key2]/current_channel"
			::= { extremeWingStatsDevWlRadioEntry 10 }

		
		-- 1.3.6.1.4.1.1916.2.131.50.1.4.2.25.9.1.1.11
		extremeWingStatsDevWlRadioConfigChannel OBJECT-TYPE
			SYNTAX DisplayString (SIZE (0..64))
			MAX-ACCESS read-only
			STATUS current
			DESCRIPTION
				"Configured channel for the radio
				
				XPath: /extremeWing-stats/device[mac=key1]/wireless/radio[radio_id=key2]/config_channel"
			::= { extremeWingStatsDevWlRadioEntry 11 }

		
		-- 1.3.6.1.4.1.1916.2.131.50.1.4.2.25.9.1.1.12
		extremeWingStatsDevWlRadioCurPower OBJECT-TYPE
			SYNTAX Unsigned32
			UNITS "dBm"
			MAX-ACCESS read-only
			STATUS current
			DESCRIPTION
				"Current power the radio is operating at
				
				XPath: /extremeWing-stats/device[mac=key1]/wireless/radio[radio_id=key2]/current_power"
			::= { extremeWingStatsDevWlRadioEntry 12 }

		
		-- 1.3.6.1.4.1.1916.2.131.50.1.4.2.25.9.1.1.13
		extremeWingStatsDevWlRadioConfigPower OBJECT-TYPE
			SYNTAX DisplayString (SIZE (0..16))
			MAX-ACCESS read-only
			STATUS current
			DESCRIPTION
				"Configured power for the radio
				
				XPath: /extremeWing-stats/device[mac=key1]/wireless/radio[radio_id=key2]/config_power"
			::= { extremeWingStatsDevWlRadioEntry 13 }

		
		-- 1.3.6.1.4.1.1916.2.131.50.1.4.2.25.9.1.1.14
		extremeWingStatsDevWlRadioMaxUserRate OBJECT-TYPE
			SYNTAX Counter64
			UNITS "kbps"
			MAX-ACCESS read-only
			STATUS current
			DESCRIPTION
				"Theoretic maximum user-level data rate
				
				XPath: /extremeWing-stats/device[mac=key1]/wireless/radio[radio_id=key2]/max_user_rate"
			::= { extremeWingStatsDevWlRadioEntry 14 }

		
		-- 1.3.6.1.4.1.1916.2.131.50.1.4.2.25.9.1.1.15
		extremeWingStatsDevWlRadioNumClient OBJECT-TYPE
			SYNTAX Unsigned32
			MAX-ACCESS read-only
			STATUS current
			DESCRIPTION
				"Number of clients associated to the radio
				
				XPath: /extremeWing-stats/device[mac=key1]/wireless/radio[radio_id=key2]/num_clients"
			::= { extremeWingStatsDevWlRadioEntry 15 }

		
		-- 1.3.6.1.4.1.1916.2.131.50.1.4.2.25.9.1.1.16
		extremeWingStatsDevWlRadioProtocol OBJECT-TYPE
			SYNTAX Unsigned32
			MAX-ACCESS read-only
			STATUS current
			DESCRIPTION
				"Bit map of protocols currently enabled on the radio.
				
				Bit position:
				The Least Significant Bit corresponds to the first bit
				in the map. The next bit corresponds to the second bit
				and so on. Unused bits are ignored.
				
				bit position  meaning
				============  =======
				0             dot11a
				1             dot11b
				2             dot11g
				3             dot11an
				4             dot11gn
				
				Bit values:
				1 - enabled
				0 - disabled
				
				XPath: /extremeWing-stats/device[mac=key1]/wireless/radio[radio_id=key2]/protocol"
			::= { extremeWingStatsDevWlRadioEntry 16 }

		
-- /extremeWing-stats/device/wireless/radio-stats
		-- 1.3.6.1.4.1.1916.2.131.50.1.4.2.25.10
		extremeWingStatsDevWlRadioStat OBJECT IDENTIFIER ::= { extremeWingStatsDevWl 10 }

		
		-- 1.3.6.1.4.1.1916.2.131.50.1.4.2.25.10.1
		extremeWingStatsDevWlRadioStatTable OBJECT-TYPE
			SYNTAX SEQUENCE OF ExtremeWingStatsDevWlRadioStatEntry
			MAX-ACCESS not-accessible
			STATUS current
			DESCRIPTION
				"Traffic and RF statistics of radios on AP
				
				/extremeWing-stats/device/wireless/radio-stats"
			::= { extremeWingStatsDevWlRadioStat 1 }

		
		-- 1.3.6.1.4.1.1916.2.131.50.1.4.2.25.10.1.1
		extremeWingStatsDevWlRadioStatEntry OBJECT-TYPE
			SYNTAX ExtremeWingStatsDevWlRadioStatEntry
			MAX-ACCESS not-accessible
			STATUS current
			DESCRIPTION
				"An entry in the table."
			INDEX { extremeWingStatsDevMac, extremeWingStatsDevWlRadioStatId }
			::= { extremeWingStatsDevWlRadioStatTable 1 }

		
		ExtremeWingStatsDevWlRadioStatEntry ::=
			SEQUENCE { 
				extremeWingStatsDevWlRadioStatId
					ExtremeWingIdentifier,
				extremeWingStatsDevWlRadioStatDeviceMac
					MacAddress,
				extremeWingStatsDevWlRadioStatAlias
					ExtremeWingIdentifier,
				extremeWingStatsDevWlRadioStatMac
					MacAddress,
				extremeWingStatsDevWlRadioStatType
					DisplayString,
				extremeWingStatsDevWlRadioStatTxBytes
					Counter64,
				extremeWingStatsDevWlRadioStatRxBytes
					Counter64,
				extremeWingStatsDevWlRadioStatTxPkts
					Counter64,
				extremeWingStatsDevWlRadioStatRxPkts
					Counter64,
				extremeWingStatsDevWlRadioStatTxDropped
					Counter64,
				extremeWingStatsDevWlRadioStatRxErrors
					Counter64,
				extremeWingStatsDevWlRadioStatTIndex
					Integer32,
				extremeWingStatsDevWlRadioStatTxBps
					Unsigned32,
				extremeWingStatsDevWlRadioStatRxBps
					Unsigned32,
				extremeWingStatsDevWlRadioStatSignal
					Integer32,
				extremeWingStatsDevWlRadioStatNoise
					Integer32,
				extremeWingStatsDevWlRadioStatSnr
					Integer32,
				extremeWingStatsDevWlRadioStatTxRate
					Unsigned32,
				extremeWingStatsDevWlRadioStatRxRate
					Unsigned32,
				extremeWingStatsDevWlRadioStatErrorRate
					Unsigned32,
				extremeWingStatsDevWlRadioStatQIndex
					Integer32,
				extremeWingStatsDevWlRadioStatNumClients
					Unsigned32,
				extremeWingStatsDevWlRadioStatNumBClients
					Unsigned32,
				extremeWingStatsDevWlRadioStatNumBgClients
					Unsigned32,
				extremeWingStatsDevWlRadioStatNumBgnClients
					Unsigned32,
				extremeWingStatsDevWlRadioStatNumAClients
					Unsigned32,
				extremeWingStatsDevWlRadioStatNumAnClients
					Unsigned32,
				extremeWingStatsDevWlRadioStatMediumErrorRate
					Unsigned32,
				extremeWingStatsDevWlRadioStatTxRetries
					Counter64,
				extremeWingStatsDevWlRadioStatTxRetriedBytes
					Counter64
			 }

		-- 1.3.6.1.4.1.1916.2.131.50.1.4.2.25.10.1.1.1
		extremeWingStatsDevWlRadioStatId OBJECT-TYPE
			SYNTAX ExtremeWingIdentifier
			MAX-ACCESS read-only
			STATUS current
			DESCRIPTION
				"Unique ID for each radio interface in the form of
				AP-MAC:R%d. E.g., 00-A0-F8-00-00-00:R1
				
				XPath: /extremeWing-stats/device[mac=key1]/wireless/radio-stats[radio_id=key2]/radio_id"
			::= { extremeWingStatsDevWlRadioStatEntry 1 }

		
		-- 1.3.6.1.4.1.1916.2.131.50.1.4.2.25.10.1.1.2
		extremeWingStatsDevWlRadioStatDeviceMac OBJECT-TYPE
			SYNTAX MacAddress
			MAX-ACCESS read-only
			STATUS current
			DESCRIPTION
				"MAC address of AP the radio belongs to
				
				XPath: /extremeWing-stats/device[mac=key1]/wireless/radio-stats[radio_id=key2]/device_mac"
			::= { extremeWingStatsDevWlRadioStatEntry 2 }

		
		-- 1.3.6.1.4.1.1916.2.131.50.1.4.2.25.10.1.1.3
		extremeWingStatsDevWlRadioStatAlias OBJECT-TYPE
			SYNTAX ExtremeWingIdentifier
			MAX-ACCESS read-only
			STATUS current
			DESCRIPTION
				"An alias to radio id in the form of hostname:R%d.
				E.g., wm3400-22A24E:R1
				
				XPath: /extremeWing-stats/device[mac=key1]/wireless/radio-stats[radio_id=key2]/radio_alias"
			::= { extremeWingStatsDevWlRadioStatEntry 3 }

		
		-- 1.3.6.1.4.1.1916.2.131.50.1.4.2.25.10.1.1.4
		extremeWingStatsDevWlRadioStatMac OBJECT-TYPE
			SYNTAX MacAddress
			MAX-ACCESS read-only
			STATUS current
			DESCRIPTION
				"MAC address of the radio
				
				XPath: /extremeWing-stats/device[mac=key1]/wireless/radio-stats[radio_id=key2]/radio_mac"
			::= { extremeWingStatsDevWlRadioStatEntry 4 }

		
		-- 1.3.6.1.4.1.1916.2.131.50.1.4.2.25.10.1.1.5
		extremeWingStatsDevWlRadioStatType OBJECT-TYPE
			SYNTAX DisplayString
			MAX-ACCESS read-only
			STATUS current
			DESCRIPTION
				"802.11 radio-type
				
				Values:
				2.4GHz-wlan
				5GHz-wlan
				sensor
				
				XPath: /extremeWing-stats/device[mac=key1]/wireless/radio-stats[radio_id=key2]/radio_type"
			::= { extremeWingStatsDevWlRadioStatEntry 5 }

		
		-- 1.3.6.1.4.1.1916.2.131.50.1.4.2.25.10.1.1.6
		extremeWingStatsDevWlRadioStatTxBytes OBJECT-TYPE
			SYNTAX Counter64
			MAX-ACCESS read-only
			STATUS current
			DESCRIPTION
				"Number of data bytes transmitted from radio to clients
				
				XPath: /extremeWing-stats/device[mac=key1]/wireless/radio-stats[radio_id=key2]/tx_bytes"
			::= { extremeWingStatsDevWlRadioStatEntry 6 }

		
		-- 1.3.6.1.4.1.1916.2.131.50.1.4.2.25.10.1.1.7
		extremeWingStatsDevWlRadioStatRxBytes OBJECT-TYPE
			SYNTAX Counter64
			MAX-ACCESS read-only
			STATUS current
			DESCRIPTION
				"Number of data bytes received from clients to radio
				
				XPath: /extremeWing-stats/device[mac=key1]/wireless/radio-stats[radio_id=key2]/rx_bytes"
			::= { extremeWingStatsDevWlRadioStatEntry 7 }

		
		-- 1.3.6.1.4.1.1916.2.131.50.1.4.2.25.10.1.1.8
		extremeWingStatsDevWlRadioStatTxPkts OBJECT-TYPE
			SYNTAX Counter64
			MAX-ACCESS read-only
			STATUS current
			DESCRIPTION
				"Number of packets of data transmitted from radio to clients
				
				XPath: /extremeWing-stats/device[mac=key1]/wireless/radio-stats[radio_id=key2]/tx_pkts"
			::= { extremeWingStatsDevWlRadioStatEntry 8 }

		
		-- 1.3.6.1.4.1.1916.2.131.50.1.4.2.25.10.1.1.9
		extremeWingStatsDevWlRadioStatRxPkts OBJECT-TYPE
			SYNTAX Counter64
			MAX-ACCESS read-only
			STATUS current
			DESCRIPTION
				"Number of packets of data received from clients to radio
				
				XPath: /extremeWing-stats/device[mac=key1]/wireless/radio-stats[radio_id=key2]/rx_pkts"
			::= { extremeWingStatsDevWlRadioStatEntry 9 }

		
		-- 1.3.6.1.4.1.1916.2.131.50.1.4.2.25.10.1.1.10
		extremeWingStatsDevWlRadioStatTxDropped OBJECT-TYPE
			SYNTAX Counter64
			MAX-ACCESS read-only
			STATUS current
			DESCRIPTION
				"Number of packets of data dropped on transmission
				
				XPath: /extremeWing-stats/device[mac=key1]/wireless/radio-stats[radio_id=key2]/tx_dropped"
			::= { extremeWingStatsDevWlRadioStatEntry 10 }

		
		-- 1.3.6.1.4.1.1916.2.131.50.1.4.2.25.10.1.1.11
		extremeWingStatsDevWlRadioStatRxErrors OBJECT-TYPE
			SYNTAX Counter64
			MAX-ACCESS read-only
			STATUS current
			DESCRIPTION
				"Number of packets of data received with errors
				
				XPath: /extremeWing-stats/device[mac=key1]/wireless/radio-stats[radio_id=key2]/rx_errors"
			::= { extremeWingStatsDevWlRadioStatEntry 11 }

		
		-- 1.3.6.1.4.1.1916.2.131.50.1.4.2.25.10.1.1.12
		extremeWingStatsDevWlRadioStatTIndex OBJECT-TYPE
			SYNTAX Integer32
			MAX-ACCESS read-only
			STATUS current
			DESCRIPTION
				"Traffic Utilization Index
				
				Measures the efficiency the medium under consideration
				is used. It is the percentage of the current data throughput
				over the theoretical data rate limit, which is derived
				the current maximum physical rate configured over the medium
				based on past empirical data. This index could assist end user
				in site planning and expansion. The numerical value might be
				further classified as:
				  -1: no data available ( e.g. radio is not in wlan operation
				                          mode )
				  0-20 : very low utilization
				  20-40: low utilization
				  40-60: moderate utilization
				  60 and above: high utilization
				
				XPath: /extremeWing-stats/device[mac=key1]/wireless/radio-stats[radio_id=key2]/t_index"
			::= { extremeWingStatsDevWlRadioStatEntry 12 }

		
		-- 1.3.6.1.4.1.1916.2.131.50.1.4.2.25.10.1.1.13
		extremeWingStatsDevWlRadioStatTxBps OBJECT-TYPE
			SYNTAX Unsigned32
			UNITS "kbps"
			MAX-ACCESS read-only
			STATUS current
			DESCRIPTION
				"User data transmit rate
				
				XPath: /extremeWing-stats/device[mac=key1]/wireless/radio-stats[radio_id=key2]/tx_bps"
			::= { extremeWingStatsDevWlRadioStatEntry 13 }

		
		-- 1.3.6.1.4.1.1916.2.131.50.1.4.2.25.10.1.1.14
		extremeWingStatsDevWlRadioStatRxBps OBJECT-TYPE
			SYNTAX Unsigned32
			UNITS "kbps"
			MAX-ACCESS read-only
			STATUS current
			DESCRIPTION
				"User data receive rate
				
				XPath: /extremeWing-stats/device[mac=key1]/wireless/radio-stats[radio_id=key2]/rx_bps"
			::= { extremeWingStatsDevWlRadioStatEntry 14 }

		
		-- 1.3.6.1.4.1.1916.2.131.50.1.4.2.25.10.1.1.15
		extremeWingStatsDevWlRadioStatSignal OBJECT-TYPE
			SYNTAX Integer32
			UNITS "dbm"
			MAX-ACCESS read-only
			STATUS current
			DESCRIPTION
				"Signal strength in units of dbm
				
				XPath: /extremeWing-stats/device[mac=key1]/wireless/radio-stats[radio_id=key2]/signal"
			::= { extremeWingStatsDevWlRadioStatEntry 15 }

		
		-- 1.3.6.1.4.1.1916.2.131.50.1.4.2.25.10.1.1.16
		extremeWingStatsDevWlRadioStatNoise OBJECT-TYPE
			SYNTAX Integer32
			UNITS "dbm"
			MAX-ACCESS read-only
			STATUS current
			DESCRIPTION
				"Noise level in units of dbm
				
				XPath: /extremeWing-stats/device[mac=key1]/wireless/radio-stats[radio_id=key2]/noise"
			::= { extremeWingStatsDevWlRadioStatEntry 16 }

		
		-- 1.3.6.1.4.1.1916.2.131.50.1.4.2.25.10.1.1.17
		extremeWingStatsDevWlRadioStatSnr OBJECT-TYPE
			SYNTAX Integer32
			UNITS "db"
			MAX-ACCESS read-only
			STATUS current
			DESCRIPTION
				"Signal to noise ratio in units of db
				
				XPath: /extremeWing-stats/device[mac=key1]/wireless/radio-stats[radio_id=key2]/snr"
			::= { extremeWingStatsDevWlRadioStatEntry 17 }

		
		-- 1.3.6.1.4.1.1916.2.131.50.1.4.2.25.10.1.1.18
		extremeWingStatsDevWlRadioStatTxRate OBJECT-TYPE
			SYNTAX Unsigned32
			UNITS "Mbps"
			MAX-ACCESS read-only
			STATUS current
			DESCRIPTION
				"The effective phy-layer transmit rate
				
				XPath: /extremeWing-stats/device[mac=key1]/wireless/radio-stats[radio_id=key2]/tx_rate"
			::= { extremeWingStatsDevWlRadioStatEntry 18 }

		
		-- 1.3.6.1.4.1.1916.2.131.50.1.4.2.25.10.1.1.19
		extremeWingStatsDevWlRadioStatRxRate OBJECT-TYPE
			SYNTAX Unsigned32
			UNITS "Mbps"
			MAX-ACCESS read-only
			STATUS current
			DESCRIPTION
				"The effective phy-layer receive rate
				
				XPath: /extremeWing-stats/device[mac=key1]/wireless/radio-stats[radio_id=key2]/rx_rate"
			::= { extremeWingStatsDevWlRadioStatEntry 19 }

		
		-- 1.3.6.1.4.1.1916.2.131.50.1.4.2.25.10.1.1.20
		extremeWingStatsDevWlRadioStatErrorRate OBJECT-TYPE
			SYNTAX Unsigned32
			MAX-ACCESS read-only
			STATUS current
			DESCRIPTION
				"Ratio of errors to rx-packets in percentage
				
				XPath: /extremeWing-stats/device[mac=key1]/wireless/radio-stats[radio_id=key2]/error_rate"
			::= { extremeWingStatsDevWlRadioStatEntry 20 }

		
		-- 1.3.6.1.4.1.1916.2.131.50.1.4.2.25.10.1.1.21
		extremeWingStatsDevWlRadioStatQIndex OBJECT-TYPE
			SYNTAX Integer32
			MAX-ACCESS read-only
			STATUS current
			DESCRIPTION
				"RF quality Index
				
				Measure the quality of the medium in percentage. It is a
				function of average retries and error rate. Its range is from
				0-100. Typically:
				  -1: no data available ( e.g. radio is not in wlan operation
				                          mode )
				  0-20: very poor quality
				  20-40: poor quality
				  40-60: average quality
				  60-100: good quality
				
				XPath: /extremeWing-stats/device[mac=key1]/wireless/radio-stats[radio_id=key2]/q_index"
			::= { extremeWingStatsDevWlRadioStatEntry 21 }

		
		-- 1.3.6.1.4.1.1916.2.131.50.1.4.2.25.10.1.1.22
		extremeWingStatsDevWlRadioStatNumClients OBJECT-TYPE
			SYNTAX Unsigned32
			MAX-ACCESS read-only
			STATUS current
			DESCRIPTION
				"Total number of clients
				
				XPath: /extremeWing-stats/device[mac=key1]/wireless/radio-stats[radio_id=key2]/num_clients"
			::= { extremeWingStatsDevWlRadioStatEntry 22 }

		
		-- 1.3.6.1.4.1.1916.2.131.50.1.4.2.25.10.1.1.23
		extremeWingStatsDevWlRadioStatNumBClients OBJECT-TYPE
			SYNTAX Unsigned32
			MAX-ACCESS read-only
			STATUS current
			DESCRIPTION
				"Number of 11b clients
				
				XPath: /extremeWing-stats/device[mac=key1]/wireless/radio-stats[radio_id=key2]/num_b_clients"
			::= { extremeWingStatsDevWlRadioStatEntry 23 }

		
		-- 1.3.6.1.4.1.1916.2.131.50.1.4.2.25.10.1.1.24
		extremeWingStatsDevWlRadioStatNumBgClients OBJECT-TYPE
			SYNTAX Unsigned32
			MAX-ACCESS read-only
			STATUS current
			DESCRIPTION
				"Number of 11bg clients
				
				XPath: /extremeWing-stats/device[mac=key1]/wireless/radio-stats[radio_id=key2]/num_bg_clients"
			::= { extremeWingStatsDevWlRadioStatEntry 24 }

		
		-- 1.3.6.1.4.1.1916.2.131.50.1.4.2.25.10.1.1.25
		extremeWingStatsDevWlRadioStatNumBgnClients OBJECT-TYPE
			SYNTAX Unsigned32
			MAX-ACCESS read-only
			STATUS current
			DESCRIPTION
				"Number of 11bgn clients
				
				XPath: /extremeWing-stats/device[mac=key1]/wireless/radio-stats[radio_id=key2]/num_bgn_clients"
			::= { extremeWingStatsDevWlRadioStatEntry 25 }

		
		-- 1.3.6.1.4.1.1916.2.131.50.1.4.2.25.10.1.1.26
		extremeWingStatsDevWlRadioStatNumAClients OBJECT-TYPE
			SYNTAX Unsigned32
			MAX-ACCESS read-only
			STATUS current
			DESCRIPTION
				"Number of 11a clients
				
				XPath: /extremeWing-stats/device[mac=key1]/wireless/radio-stats[radio_id=key2]/num_a_clients"
			::= { extremeWingStatsDevWlRadioStatEntry 26 }

		
		-- 1.3.6.1.4.1.1916.2.131.50.1.4.2.25.10.1.1.27
		extremeWingStatsDevWlRadioStatNumAnClients OBJECT-TYPE
			SYNTAX Unsigned32
			MAX-ACCESS read-only
			STATUS current
			DESCRIPTION
				"Number of 11an clients
				
				XPath: /extremeWing-stats/device[mac=key1]/wireless/radio-stats[radio_id=key2]/num_an_clients"
			::= { extremeWingStatsDevWlRadioStatEntry 27 }

		
		-- 1.3.6.1.4.1.1916.2.131.50.1.4.2.25.10.1.1.28
		extremeWingStatsDevWlRadioStatMediumErrorRate OBJECT-TYPE
			SYNTAX Unsigned32
			MAX-ACCESS read-only
			STATUS current
			DESCRIPTION
				"Ratio of medium errors and rx-retries to rx-packets
				in percentage
				
				XPath: /extremeWing-stats/device[mac=key1]/wireless/radio-stats[radio_id=key2]/medium_error_rate"
			::= { extremeWingStatsDevWlRadioStatEntry 28 }

		
		-- 1.3.6.1.4.1.1916.2.131.50.1.4.2.25.10.1.1.29
		extremeWingStatsDevWlRadioStatTxRetries OBJECT-TYPE
			SYNTAX Counter64
			MAX-ACCESS read-only
			STATUS current
			DESCRIPTION
				"Total number of retries
				
				XPath: /extremeWing-stats/device[mac=key1]/wireless/radio-stats[radio_id=key2]/tx_retries"
			::= { extremeWingStatsDevWlRadioStatEntry 29 }

		
		-- 1.3.6.1.4.1.1916.2.131.50.1.4.2.25.10.1.1.30
		extremeWingStatsDevWlRadioStatTxRetriedBytes OBJECT-TYPE
			SYNTAX Counter64
			MAX-ACCESS read-only
			STATUS current
			DESCRIPTION
				"Total retried bytes excluding bytes sent
				
				XPath: /extremeWing-stats/device[mac=key1]/wireless/radio-stats[radio_id=key2]/tx_retried_bytes"
			::= { extremeWingStatsDevWlRadioStatEntry 30 }

		
		-- 1.3.6.1.4.1.1916.2.131.50.1.4.2.25.20
		extremeWingStatsDevWlApDetectTable OBJECT-TYPE
			SYNTAX SEQUENCE OF ExtremeWingStatsDevWlApDetectEntry
			MAX-ACCESS not-accessible
			STATUS current
			DESCRIPTION
				"Unsanctioned APs seen
				
				/extremeWing-stats/device/wireless/apdetection-aptable"
			::= { extremeWingStatsDevWl 20 }

		
		-- 1.3.6.1.4.1.1916.2.131.50.1.4.2.25.20.1
		extremeWingStatsDevWlApDetectEntry OBJECT-TYPE
			SYNTAX ExtremeWingStatsDevWlApDetectEntry
			MAX-ACCESS not-accessible
			STATUS current
			DESCRIPTION
				"An entry in the table."
			INDEX { extremeWingStatsDevMac, extremeWingStatsDevWlApDetectMac }
			::= { extremeWingStatsDevWlApDetectTable 1 }

		
		ExtremeWingStatsDevWlApDetectEntry ::=
			SEQUENCE { 
				extremeWingStatsDevWlApDetectMac
					MacAddress,
				extremeWingStatsDevWlApDetectVendor
					DisplayString,
				extremeWingStatsDevWlApDetectChannel
					DisplayString,
				extremeWingStatsDevWlApDetectRadioType
					DisplayString,
				extremeWingStatsDevWlApDetectApMode
					DisplayString,
				extremeWingStatsDevWlApDetectSsid
					DisplayString,
				extremeWingStatsDevWlApDetectRssi
					Integer32,
				extremeWingStatsDevWlApDetectLastSeen
					Unsigned32,
				extremeWingStatsDevWlApDetectFirstSeen
					Unsigned32,
				extremeWingStatsDevWlApDetectEncryption
					TruthValue,
				extremeWingStatsDevWlApDetectReportingApMac
					MacAddress,
				extremeWingStatsDevWlApDetectReportingApRadioNum
					Unsigned32
			 }

		-- 1.3.6.1.4.1.1916.2.131.50.1.4.2.25.20.1.1
		extremeWingStatsDevWlApDetectMac OBJECT-TYPE
			SYNTAX MacAddress
			MAX-ACCESS read-only
			STATUS current
			DESCRIPTION
				"Bssid address of the unsanctioned AP.
				
				XPath: /extremeWing-stats/device[mac=key1]/wireless/apdetection-aptable[mac=key2]/mac"
			::= { extremeWingStatsDevWlApDetectEntry 1 }

		
		-- 1.3.6.1.4.1.1916.2.131.50.1.4.2.25.20.1.2
		extremeWingStatsDevWlApDetectVendor OBJECT-TYPE
			SYNTAX DisplayString (SIZE (0..64))
			MAX-ACCESS read-only
			STATUS current
			DESCRIPTION
				"Vendor name based on mac OUI lookup for the unsanctioned AP.
				
				XPath: /extremeWing-stats/device[mac=key1]/wireless/apdetection-aptable[mac=key2]/vendor"
			::= { extremeWingStatsDevWlApDetectEntry 2 }

		
		-- 1.3.6.1.4.1.1916.2.131.50.1.4.2.25.20.1.3
		extremeWingStatsDevWlApDetectChannel OBJECT-TYPE
			SYNTAX DisplayString (SIZE (1..16))
			MAX-ACCESS read-only
			STATUS current
			DESCRIPTION
				"Channel information of the unsanctioned AP.
				
				XPath: /extremeWing-stats/device[mac=key1]/wireless/apdetection-aptable[mac=key2]/channel"
			::= { extremeWingStatsDevWlApDetectEntry 3 }

		
		-- 1.3.6.1.4.1.1916.2.131.50.1.4.2.25.20.1.4
		extremeWingStatsDevWlApDetectRadioType OBJECT-TYPE
			SYNTAX DisplayString
			MAX-ACCESS read-only
			STATUS current
			DESCRIPTION
				"Radio type of the unsanctioned AP.
				
				Values:
				11a
				11b
				11g
				11bg
				11an
				11bgn
				
				XPath: /extremeWing-stats/device[mac=key1]/wireless/apdetection-aptable[mac=key2]/dot11_radio_type"
			::= { extremeWingStatsDevWlApDetectEntry 4 }

		
		-- 1.3.6.1.4.1.1916.2.131.50.1.4.2.25.20.1.5
		extremeWingStatsDevWlApDetectApMode OBJECT-TYPE
			SYNTAX DisplayString
			MAX-ACCESS read-only
			STATUS current
			DESCRIPTION
				"Operating mode of the unsanctioned AP.
				
				Values:
				ap
				adhoc
				
				XPath: /extremeWing-stats/device[mac=key1]/wireless/apdetection-aptable[mac=key2]/ap_mode"
			::= { extremeWingStatsDevWlApDetectEntry 5 }

		
		-- 1.3.6.1.4.1.1916.2.131.50.1.4.2.25.20.1.6
		extremeWingStatsDevWlApDetectSsid OBJECT-TYPE
			SYNTAX DisplayString (SIZE (1..255))
			MAX-ACCESS read-only
			STATUS current
			DESCRIPTION
				"ssid of the unsanctioned AP.
				
				XPath: /extremeWing-stats/device[mac=key1]/wireless/apdetection-aptable[mac=key2]/ssid"
			::= { extremeWingStatsDevWlApDetectEntry 6 }

		
		-- 1.3.6.1.4.1.1916.2.131.50.1.4.2.25.20.1.7
		extremeWingStatsDevWlApDetectRssi OBJECT-TYPE
			SYNTAX Integer32
			UNITS "dBm"
			MAX-ACCESS read-only
			STATUS current
			DESCRIPTION
				"Signal strength of the unsanctioned AP.
				
				XPath: /extremeWing-stats/device[mac=key1]/wireless/apdetection-aptable[mac=key2]/rssi"
			::= { extremeWingStatsDevWlApDetectEntry 7 }

		
		-- 1.3.6.1.4.1.1916.2.131.50.1.4.2.25.20.1.8
		extremeWingStatsDevWlApDetectLastSeen OBJECT-TYPE
			SYNTAX Unsigned32
			UNITS "seconds"
			MAX-ACCESS read-only
			STATUS current
			DESCRIPTION
				"Seconds ago from the current time the unsanctioned AP was
				last seen.
				
				XPath: /extremeWing-stats/device[mac=key1]/wireless/apdetection-aptable[mac=key2]/last_seen"
			::= { extremeWingStatsDevWlApDetectEntry 8 }

		
		-- 1.3.6.1.4.1.1916.2.131.50.1.4.2.25.20.1.9
		extremeWingStatsDevWlApDetectFirstSeen OBJECT-TYPE
			SYNTAX Unsigned32
			UNITS "seconds"
			MAX-ACCESS read-only
			STATUS current
			DESCRIPTION
				"Seconds ago from the current time the unsanctioned AP was
				first seen.
				
				XPath: /extremeWing-stats/device[mac=key1]/wireless/apdetection-aptable[mac=key2]/first_seen"
			::= { extremeWingStatsDevWlApDetectEntry 9 }

		
		-- 1.3.6.1.4.1.1916.2.131.50.1.4.2.25.20.1.10
		extremeWingStatsDevWlApDetectEncryption OBJECT-TYPE
			SYNTAX TruthValue
			MAX-ACCESS read-only
			STATUS current
			DESCRIPTION
				"Whether the unsanctioned AP supports data encryption.
				
				XPath: /extremeWing-stats/device[mac=key1]/wireless/apdetection-aptable[mac=key2]/encryption"
			::= { extremeWingStatsDevWlApDetectEntry 10 }

		
		-- 1.3.6.1.4.1.1916.2.131.50.1.4.2.25.20.1.11
		extremeWingStatsDevWlApDetectReportingApMac OBJECT-TYPE
			SYNTAX MacAddress
			MAX-ACCESS read-only
			STATUS current
			DESCRIPTION
				"Mac address of the AP reporting this unsanctioned AP entry.
				
				XPath: /extremeWing-stats/device[mac=key1]/wireless/apdetection-aptable[mac=key2]/reporting_ap_mac"
			::= { extremeWingStatsDevWlApDetectEntry 11 }

		
		-- 1.3.6.1.4.1.1916.2.131.50.1.4.2.25.20.1.12
		extremeWingStatsDevWlApDetectReportingApRadioNum OBJECT-TYPE
			SYNTAX Unsigned32
			MAX-ACCESS read-only
			STATUS current
			DESCRIPTION
				"Radio number on the AP reporting this unsanctioned AP entry.
				
				XPath: /extremeWing-stats/device[mac=key1]/wireless/apdetection-aptable[mac=key2]/reporting_ap_radio_num"
			::= { extremeWingStatsDevWlApDetectEntry 12 }

		
		-- 1.3.6.1.4.1.1916.2.131.50.1.4.2.25.21
		extremeWingStatsDevWlMcx OBJECT IDENTIFIER ::= { extremeWingStatsDevWl 21 }

		
		-- 1.3.6.1.4.1.1916.2.131.50.1.4.2.25.21.1
		extremeWingStatsDevWlMcxMeshpointTable OBJECT-TYPE
			SYNTAX SEQUENCE OF ExtremeWingStatsDevWlMcxMeshpointEntry
			MAX-ACCESS not-accessible
			STATUS current
			DESCRIPTION
				"
				
				/extremeWing-stats/device/wireless/meshpoint"
			::= { extremeWingStatsDevWlMcx 1 }

		
		-- 1.3.6.1.4.1.1916.2.131.50.1.4.2.25.21.1.1
		extremeWingStatsDevWlMcxMeshpointEntry OBJECT-TYPE
			SYNTAX ExtremeWingStatsDevWlMcxMeshpointEntry
			MAX-ACCESS not-accessible
			STATUS current
			DESCRIPTION
				"An entry in the table."
			INDEX { extremeWingStatsDevMac, extremeWingStatsDevWlMcxMeshpointMpid }
			::= { extremeWingStatsDevWlMcxMeshpointTable 1 }

		
		ExtremeWingStatsDevWlMcxMeshpointEntry ::=
			SEQUENCE { 
				extremeWingStatsDevWlMcxMeshpointMpid
					ExtremeWingIdentifier,
				extremeWingStatsDevWlMcxMeshpointName
					ExtremeWingIdentifier,
				extremeWingStatsDevWlMcxMeshpointHostname
					DisplayString,
				extremeWingStatsDevWlMcxMeshpointDeviceMac
					DisplayString,
				extremeWingStatsDevWlMcxMeshpointIsRoot
					TruthValue,
				extremeWingStatsDevWlMcxMeshpointIsCfgRoot
					TruthValue,
				extremeWingStatsDevWlMcxMeshpointRootMpid
					DisplayString,
				extremeWingStatsDevWlMcxMeshpointNextHop
					DisplayString,
				extremeWingStatsDevWlMcxMeshpointRootHops
					Unsigned32,
				extremeWingStatsDevWlMcxMeshpointIfidCnt
					Unsigned32
			 }

		-- 1.3.6.1.4.1.1916.2.131.50.1.4.2.25.21.1.1.1
		extremeWingStatsDevWlMcxMeshpointMpid OBJECT-TYPE
			SYNTAX ExtremeWingIdentifier
			MAX-ACCESS read-only
			STATUS current
			DESCRIPTION
				"Mesh Point MAC address
				
				XPath: /extremeWing-stats/device[mac=key1]/wireless/meshpoint[mpid=key2]/mpid"
			::= { extremeWingStatsDevWlMcxMeshpointEntry 1 }

		
		-- 1.3.6.1.4.1.1916.2.131.50.1.4.2.25.21.1.1.3
		extremeWingStatsDevWlMcxMeshpointName OBJECT-TYPE
			SYNTAX ExtremeWingIdentifier
			MAX-ACCESS read-only
			STATUS current
			DESCRIPTION
				"
				
				XPath: /extremeWing-stats/device[mac=key1]/wireless/meshpoint[mpid=key2]/name"
			::= { extremeWingStatsDevWlMcxMeshpointEntry 3 }

		
		-- 1.3.6.1.4.1.1916.2.131.50.1.4.2.25.21.1.1.4
		extremeWingStatsDevWlMcxMeshpointHostname OBJECT-TYPE
			SYNTAX DisplayString (SIZE (64))
			MAX-ACCESS read-only
			STATUS current
			DESCRIPTION
				"hostname of the AP device
				
				XPath: /extremeWing-stats/device[mac=key1]/wireless/meshpoint[mpid=key2]/hostname"
			::= { extremeWingStatsDevWlMcxMeshpointEntry 4 }

		
		-- 1.3.6.1.4.1.1916.2.131.50.1.4.2.25.21.1.1.5
		extremeWingStatsDevWlMcxMeshpointDeviceMac OBJECT-TYPE
			SYNTAX DisplayString
			MAX-ACCESS read-only
			STATUS current
			DESCRIPTION
				"Device MAC address
				
				XPath: /extremeWing-stats/device[mac=key1]/wireless/meshpoint[mpid=key2]/device_mac"
			::= { extremeWingStatsDevWlMcxMeshpointEntry 5 }

		
		-- 1.3.6.1.4.1.1916.2.131.50.1.4.2.25.21.1.1.6
		extremeWingStatsDevWlMcxMeshpointIsRoot OBJECT-TYPE
			SYNTAX TruthValue
			MAX-ACCESS read-only
			STATUS current
			DESCRIPTION
				"Acting as root or non-root
				
				XPath: /extremeWing-stats/device[mac=key1]/wireless/meshpoint[mpid=key2]/is_root"
			::= { extremeWingStatsDevWlMcxMeshpointEntry 6 }

		
		-- 1.3.6.1.4.1.1916.2.131.50.1.4.2.25.21.1.1.7
		extremeWingStatsDevWlMcxMeshpointIsCfgRoot OBJECT-TYPE
			SYNTAX TruthValue
			MAX-ACCESS read-only
			STATUS current
			DESCRIPTION
				"Configured as root device, is_root can be false due to dynamic factors
				
				XPath: /extremeWing-stats/device[mac=key1]/wireless/meshpoint[mpid=key2]/is_cfg_root"
			::= { extremeWingStatsDevWlMcxMeshpointEntry 7 }

		
		-- 1.3.6.1.4.1.1916.2.131.50.1.4.2.25.21.1.1.8
		extremeWingStatsDevWlMcxMeshpointRootMpid OBJECT-TYPE
			SYNTAX DisplayString
			MAX-ACCESS read-only
			STATUS current
			DESCRIPTION
				"Root mesh point MAC address
				
				XPath: /extremeWing-stats/device[mac=key1]/wireless/meshpoint[mpid=key2]/root_mpid"
			::= { extremeWingStatsDevWlMcxMeshpointEntry 8 }

		
		-- 1.3.6.1.4.1.1916.2.131.50.1.4.2.25.21.1.1.9
		extremeWingStatsDevWlMcxMeshpointNextHop OBJECT-TYPE
			SYNTAX DisplayString
			MAX-ACCESS read-only
			STATUS current
			DESCRIPTION
				"Next IFID hop to root
				
				XPath: /extremeWing-stats/device[mac=key1]/wireless/meshpoint[mpid=key2]/next_hop"
			::= { extremeWingStatsDevWlMcxMeshpointEntry 9 }

		
		-- 1.3.6.1.4.1.1916.2.131.50.1.4.2.25.21.1.1.10
		extremeWingStatsDevWlMcxMeshpointRootHops OBJECT-TYPE
			SYNTAX Unsigned32
			MAX-ACCESS read-only
			STATUS current
			DESCRIPTION
				"Hops to root
				
				XPath: /extremeWing-stats/device[mac=key1]/wireless/meshpoint[mpid=key2]/root_hops"
			::= { extremeWingStatsDevWlMcxMeshpointEntry 10 }

		
		-- 1.3.6.1.4.1.1916.2.131.50.1.4.2.25.21.1.1.11
		extremeWingStatsDevWlMcxMeshpointIfidCnt OBJECT-TYPE
			SYNTAX Unsigned32
			MAX-ACCESS read-only
			STATUS current
			DESCRIPTION
				"Number of IFID entries
				
				XPath: /extremeWing-stats/device[mac=key1]/wireless/meshpoint[mpid=key2]/ifid_cnt"
			::= { extremeWingStatsDevWlMcxMeshpointEntry 11 }

		
		-- 1.3.6.1.4.1.1916.2.131.50.1.4.2.25.21.2
		extremeWingStatsDevWlMcxMeshpointIfidDataTable OBJECT-TYPE
			SYNTAX SEQUENCE OF ExtremeWingStatsDevWlMcxMeshpointIfidDataEntry
			MAX-ACCESS not-accessible
			STATUS current
			DESCRIPTION
				"
				
				/extremeWing-stats/device/wireless/meshpoint/ifid_data"
			::= { extremeWingStatsDevWlMcx 2 }

		
		-- 1.3.6.1.4.1.1916.2.131.50.1.4.2.25.21.2.1
		extremeWingStatsDevWlMcxMeshpointIfidDataEntry OBJECT-TYPE
			SYNTAX ExtremeWingStatsDevWlMcxMeshpointIfidDataEntry
			MAX-ACCESS not-accessible
			STATUS current
			DESCRIPTION
				"An entry in the table."
			INDEX { extremeWingStatsDevMac, extremeWingStatsDevWlMcxMeshpointMpid, extremeWingStatsDevWlMcxMeshpointIfid }
			::= { extremeWingStatsDevWlMcxMeshpointIfidDataTable 1 }

		
		ExtremeWingStatsDevWlMcxMeshpointIfidDataEntry ::=
			SEQUENCE { 
				extremeWingStatsDevWlMcxMeshpointIfid
					ExtremeWingIdentifier,
				extremeWingStatsDevWlMcxMeshpointIfidDataDesc
					DisplayString
			 }

		-- 1.3.6.1.4.1.1916.2.131.50.1.4.2.25.21.2.1.1
		extremeWingStatsDevWlMcxMeshpointIfid OBJECT-TYPE
			SYNTAX ExtremeWingIdentifier
			MAX-ACCESS read-only
			STATUS current
			DESCRIPTION
				"
				
				XPath: /extremeWing-stats/device[mac=key1]/wireless/meshpoint[mpid=key2]/ifid_data[ifid=key3]/ifid"
			::= { extremeWingStatsDevWlMcxMeshpointIfidDataEntry 1 }

		
		-- 1.3.6.1.4.1.1916.2.131.50.1.4.2.25.21.2.1.3
		extremeWingStatsDevWlMcxMeshpointIfidDataDesc OBJECT-TYPE
			SYNTAX DisplayString (SIZE (24))
			MAX-ACCESS read-only
			STATUS current
			DESCRIPTION
				"Description of interface
				
				XPath: /extremeWing-stats/device[mac=key1]/wireless/meshpoint[mpid=key2]/ifid_data[ifid=key3]/desc"
			::= { extremeWingStatsDevWlMcxMeshpointIfidDataEntry 3 }

		
		-- 1.3.6.1.4.1.1916.2.131.50.1.4.2.25.21.3
		extremeWingStatsDevWlMcxMeshpointStatsTable OBJECT-TYPE
			SYNTAX SEQUENCE OF ExtremeWingStatsDevWlMcxMeshpointStatsEntry
			MAX-ACCESS not-accessible
			STATUS current
			DESCRIPTION
				"
				
				/extremeWing-stats/device/wireless/meshpoint-stats"
			::= { extremeWingStatsDevWlMcx 3 }

		
		-- 1.3.6.1.4.1.1916.2.131.50.1.4.2.25.21.3.1
		extremeWingStatsDevWlMcxMeshpointStatsEntry OBJECT-TYPE
			SYNTAX ExtremeWingStatsDevWlMcxMeshpointStatsEntry
			MAX-ACCESS not-accessible
			STATUS current
			DESCRIPTION
				"An entry in the table."
			INDEX { extremeWingStatsDevMac, extremeWingStatsDevWlMcxMeshpointStatsName }
			::= { extremeWingStatsDevWlMcxMeshpointStatsTable 1 }

		
		ExtremeWingStatsDevWlMcxMeshpointStatsEntry ::=
			SEQUENCE { 
				extremeWingStatsDevWlMcxMeshpointStatsName
					ExtremeWingIdentifier,
				extremeWingStatsDevWlMcxMeshpointStatsMeshid
					DisplayString,
				extremeWingStatsDevWlMcxMeshpointStatsNumRadios
					Unsigned32,
				extremeWingStatsDevWlMcxMeshpointStatsNumNeighbors
					Unsigned32,
				extremeWingStatsDevWlMcxMeshpointStatsTxBytes
					Counter64,
				extremeWingStatsDevWlMcxMeshpointStatsRxBytes
					Counter64,
				extremeWingStatsDevWlMcxMeshpointStatsTxPkts
					Unsigned32,
				extremeWingStatsDevWlMcxMeshpointStatsRxPkts
					Unsigned32,
				extremeWingStatsDevWlMcxMeshpointStatsTxDropped
					Unsigned32,
				extremeWingStatsDevWlMcxMeshpointStatsRxErrors
					Unsigned32,
				extremeWingStatsDevWlMcxMeshpointStatsTIndex
					Unsigned32,
				extremeWingStatsDevWlMcxMeshpointStatsTotalBytes
					Counter64,
				extremeWingStatsDevWlMcxMeshpointStatsTotalPkts
					Unsigned32,
				extremeWingStatsDevWlMcxMeshpointStatsTxBps
					Unsigned32,
				extremeWingStatsDevWlMcxMeshpointStatsRxBps
					Unsigned32,
				extremeWingStatsDevWlMcxMeshpointStatsTotalBps
					Unsigned32,
				extremeWingStatsDevWlMcxMeshpointStatsTxPps
					Unsigned32,
				extremeWingStatsDevWlMcxMeshpointStatsRxPps
					Unsigned32,
				extremeWingStatsDevWlMcxMeshpointStatsTotalPps
					Unsigned32,
				extremeWingStatsDevWlMcxMeshpointStatsTxBcmcPkts
					Counter64,
				extremeWingStatsDevWlMcxMeshpointStatsRxBcmcPkts
					Counter64,
				extremeWingStatsDevWlMcxMeshpointStatsTotalBcmcPkts
					Counter64,
				extremeWingStatsDevWlMcxMeshpointStatsTxMgmtPkts
					Counter64,
				extremeWingStatsDevWlMcxMeshpointStatsRxMgmtPkts
					Counter64,
				extremeWingStatsDevWlMcxMeshpointStatsTotalMgmtPkts
					Counter64,
				extremeWingStatsDevWlMcxMeshpointStatsMaxUserRate
					Unsigned32
			 }

		-- 1.3.6.1.4.1.1916.2.131.50.1.4.2.25.21.3.1.1
		extremeWingStatsDevWlMcxMeshpointStatsName OBJECT-TYPE
			SYNTAX ExtremeWingIdentifier
			MAX-ACCESS read-only
			STATUS current
			DESCRIPTION
				"
				
				XPath: /extremeWing-stats/device[mac=key1]/wireless/meshpoint-stats[name=key2]/name"
			::= { extremeWingStatsDevWlMcxMeshpointStatsEntry 1 }

		
		-- 1.3.6.1.4.1.1916.2.131.50.1.4.2.25.21.3.1.3
		extremeWingStatsDevWlMcxMeshpointStatsMeshid OBJECT-TYPE
			SYNTAX DisplayString (SIZE (32))
			MAX-ACCESS read-only
			STATUS current
			DESCRIPTION
				"Mesh Point Identifier for this MP.
				
				XPath: /extremeWing-stats/device[mac=key1]/wireless/meshpoint-stats[name=key2]/meshid"
			::= { extremeWingStatsDevWlMcxMeshpointStatsEntry 3 }

		
		-- 1.3.6.1.4.1.1916.2.131.50.1.4.2.25.21.3.1.4
		extremeWingStatsDevWlMcxMeshpointStatsNumRadios OBJECT-TYPE
			SYNTAX Unsigned32
			MAX-ACCESS read-only
			STATUS current
			DESCRIPTION
				"
				
				XPath: /extremeWing-stats/device[mac=key1]/wireless/meshpoint-stats[name=key2]/num_radios"
			::= { extremeWingStatsDevWlMcxMeshpointStatsEntry 4 }

		
		-- 1.3.6.1.4.1.1916.2.131.50.1.4.2.25.21.3.1.5
		extremeWingStatsDevWlMcxMeshpointStatsNumNeighbors OBJECT-TYPE
			SYNTAX Unsigned32
			MAX-ACCESS read-only
			STATUS current
			DESCRIPTION
				"number of neighbors resourced to this meshpoint
				
				XPath: /extremeWing-stats/device[mac=key1]/wireless/meshpoint-stats[name=key2]/num_neighbors"
			::= { extremeWingStatsDevWlMcxMeshpointStatsEntry 5 }

		
		-- 1.3.6.1.4.1.1916.2.131.50.1.4.2.25.21.3.1.6
		extremeWingStatsDevWlMcxMeshpointStatsTxBytes OBJECT-TYPE
			SYNTAX Counter64
			MAX-ACCESS read-only
			STATUS current
			DESCRIPTION
				"Number of data bytes transmitted - from AP to client
				
				XPath: /extremeWing-stats/device[mac=key1]/wireless/meshpoint-stats[name=key2]/tx_bytes"
			::= { extremeWingStatsDevWlMcxMeshpointStatsEntry 6 }

		
		-- 1.3.6.1.4.1.1916.2.131.50.1.4.2.25.21.3.1.7
		extremeWingStatsDevWlMcxMeshpointStatsRxBytes OBJECT-TYPE
			SYNTAX Counter64
			MAX-ACCESS read-only
			STATUS current
			DESCRIPTION
				"Number of data bytes received - from client to AP
				
				XPath: /extremeWing-stats/device[mac=key1]/wireless/meshpoint-stats[name=key2]/rx_bytes"
			::= { extremeWingStatsDevWlMcxMeshpointStatsEntry 7 }

		
		-- 1.3.6.1.4.1.1916.2.131.50.1.4.2.25.21.3.1.8
		extremeWingStatsDevWlMcxMeshpointStatsTxPkts OBJECT-TYPE
			SYNTAX Unsigned32
			MAX-ACCESS read-only
			STATUS current
			DESCRIPTION
				"Number of packets of data transmitted - from AP to node
				
				XPath: /extremeWing-stats/device[mac=key1]/wireless/meshpoint-stats[name=key2]/tx_pkts"
			::= { extremeWingStatsDevWlMcxMeshpointStatsEntry 8 }

		
		-- 1.3.6.1.4.1.1916.2.131.50.1.4.2.25.21.3.1.9
		extremeWingStatsDevWlMcxMeshpointStatsRxPkts OBJECT-TYPE
			SYNTAX Unsigned32
			MAX-ACCESS read-only
			STATUS current
			DESCRIPTION
				"Number of packets of data received - from client to AP
				
				XPath: /extremeWing-stats/device[mac=key1]/wireless/meshpoint-stats[name=key2]/rx_pkts"
			::= { extremeWingStatsDevWlMcxMeshpointStatsEntry 9 }

		
		-- 1.3.6.1.4.1.1916.2.131.50.1.4.2.25.21.3.1.10
		extremeWingStatsDevWlMcxMeshpointStatsTxDropped OBJECT-TYPE
			SYNTAX Unsigned32
			MAX-ACCESS read-only
			STATUS current
			DESCRIPTION
				"Number of packets of data dropped on transmission
				
				XPath: /extremeWing-stats/device[mac=key1]/wireless/meshpoint-stats[name=key2]/tx_dropped"
			::= { extremeWingStatsDevWlMcxMeshpointStatsEntry 10 }

		
		-- 1.3.6.1.4.1.1916.2.131.50.1.4.2.25.21.3.1.11
		extremeWingStatsDevWlMcxMeshpointStatsRxErrors OBJECT-TYPE
			SYNTAX Unsigned32
			MAX-ACCESS read-only
			STATUS current
			DESCRIPTION
				"Number of packets of data received with errors 
				
				XPath: /extremeWing-stats/device[mac=key1]/wireless/meshpoint-stats[name=key2]/rx_errors"
			::= { extremeWingStatsDevWlMcxMeshpointStatsEntry 11 }

		
		-- 1.3.6.1.4.1.1916.2.131.50.1.4.2.25.21.3.1.12
		extremeWingStatsDevWlMcxMeshpointStatsTIndex OBJECT-TYPE
			SYNTAX Unsigned32
			MAX-ACCESS read-only
			STATUS current
			DESCRIPTION
				"
				
				XPath: /extremeWing-stats/device[mac=key1]/wireless/meshpoint-stats[name=key2]/t_index"
			::= { extremeWingStatsDevWlMcxMeshpointStatsEntry 12 }

		
		-- 1.3.6.1.4.1.1916.2.131.50.1.4.2.25.21.3.1.13
		extremeWingStatsDevWlMcxMeshpointStatsTotalBytes OBJECT-TYPE
			SYNTAX Counter64
			MAX-ACCESS read-only
			STATUS current
			DESCRIPTION
				"Total mumber of data bytes through this node
				
				XPath: /extremeWing-stats/device[mac=key1]/wireless/meshpoint-stats[name=key2]/total_bytes"
			::= { extremeWingStatsDevWlMcxMeshpointStatsEntry 13 }

		
		-- 1.3.6.1.4.1.1916.2.131.50.1.4.2.25.21.3.1.14
		extremeWingStatsDevWlMcxMeshpointStatsTotalPkts OBJECT-TYPE
			SYNTAX Unsigned32
			MAX-ACCESS read-only
			STATUS current
			DESCRIPTION
				"Total mumber of packets through this node
				
				XPath: /extremeWing-stats/device[mac=key1]/wireless/meshpoint-stats[name=key2]/total_pkts"
			::= { extremeWingStatsDevWlMcxMeshpointStatsEntry 14 }

		
		-- 1.3.6.1.4.1.1916.2.131.50.1.4.2.25.21.3.1.15
		extremeWingStatsDevWlMcxMeshpointStatsTxBps OBJECT-TYPE
			SYNTAX Unsigned32
			UNITS "kbps"
			MAX-ACCESS read-only
			STATUS current
			DESCRIPTION
				"user data transmit rate
				
				XPath: /extremeWing-stats/device[mac=key1]/wireless/meshpoint-stats[name=key2]/tx_bps"
			::= { extremeWingStatsDevWlMcxMeshpointStatsEntry 15 }

		
		-- 1.3.6.1.4.1.1916.2.131.50.1.4.2.25.21.3.1.16
		extremeWingStatsDevWlMcxMeshpointStatsRxBps OBJECT-TYPE
			SYNTAX Unsigned32
			UNITS "kbps"
			MAX-ACCESS read-only
			STATUS current
			DESCRIPTION
				"user data receive rate
				
				XPath: /extremeWing-stats/device[mac=key1]/wireless/meshpoint-stats[name=key2]/rx_bps"
			::= { extremeWingStatsDevWlMcxMeshpointStatsEntry 16 }

		
		-- 1.3.6.1.4.1.1916.2.131.50.1.4.2.25.21.3.1.17
		extremeWingStatsDevWlMcxMeshpointStatsTotalBps OBJECT-TYPE
			SYNTAX Unsigned32
			UNITS "kbps"
			MAX-ACCESS read-only
			STATUS current
			DESCRIPTION
				"total user data rate
				
				XPath: /extremeWing-stats/device[mac=key1]/wireless/meshpoint-stats[name=key2]/total_bps"
			::= { extremeWingStatsDevWlMcxMeshpointStatsEntry 17 }

		
		-- 1.3.6.1.4.1.1916.2.131.50.1.4.2.25.21.3.1.18
		extremeWingStatsDevWlMcxMeshpointStatsTxPps OBJECT-TYPE
			SYNTAX Unsigned32
			MAX-ACCESS read-only
			STATUS current
			DESCRIPTION
				"transmitting packet rate - AP to client
				
				XPath: /extremeWing-stats/device[mac=key1]/wireless/meshpoint-stats[name=key2]/tx_pps"
			::= { extremeWingStatsDevWlMcxMeshpointStatsEntry 18 }

		
		-- 1.3.6.1.4.1.1916.2.131.50.1.4.2.25.21.3.1.19
		extremeWingStatsDevWlMcxMeshpointStatsRxPps OBJECT-TYPE
			SYNTAX Unsigned32
			MAX-ACCESS read-only
			STATUS current
			DESCRIPTION
				"receiving packet rate - client to AP
				
				XPath: /extremeWing-stats/device[mac=key1]/wireless/meshpoint-stats[name=key2]/rx_pps"
			::= { extremeWingStatsDevWlMcxMeshpointStatsEntry 19 }

		
		-- 1.3.6.1.4.1.1916.2.131.50.1.4.2.25.21.3.1.20
		extremeWingStatsDevWlMcxMeshpointStatsTotalPps OBJECT-TYPE
			SYNTAX Unsigned32
			MAX-ACCESS read-only
			STATUS current
			DESCRIPTION
				"total packet rate
				
				XPath: /extremeWing-stats/device[mac=key1]/wireless/meshpoint-stats[name=key2]/total_pps"
			::= { extremeWingStatsDevWlMcxMeshpointStatsEntry 20 }

		
		-- 1.3.6.1.4.1.1916.2.131.50.1.4.2.25.21.3.1.21
		extremeWingStatsDevWlMcxMeshpointStatsTxBcmcPkts OBJECT-TYPE
			SYNTAX Counter64
			MAX-ACCESS read-only
			STATUS current
			DESCRIPTION
				"Number of broadcast packets transmitted by the node
				
				XPath: /extremeWing-stats/device[mac=key1]/wireless/meshpoint-stats[name=key2]/tx_bcmc_pkts"
			::= { extremeWingStatsDevWlMcxMeshpointStatsEntry 21 }

		
		-- 1.3.6.1.4.1.1916.2.131.50.1.4.2.25.21.3.1.22
		extremeWingStatsDevWlMcxMeshpointStatsRxBcmcPkts OBJECT-TYPE
			SYNTAX Counter64
			MAX-ACCESS read-only
			STATUS current
			DESCRIPTION
				"Number of broadcast packets of received by the node
				
				XPath: /extremeWing-stats/device[mac=key1]/wireless/meshpoint-stats[name=key2]/rx_bcmc_pkts"
			::= { extremeWingStatsDevWlMcxMeshpointStatsEntry 22 }

		
		-- 1.3.6.1.4.1.1916.2.131.50.1.4.2.25.21.3.1.23
		extremeWingStatsDevWlMcxMeshpointStatsTotalBcmcPkts OBJECT-TYPE
			SYNTAX Counter64
			MAX-ACCESS read-only
			STATUS current
			DESCRIPTION
				"Total number of broadcast packets through this node
				
				XPath: /extremeWing-stats/device[mac=key1]/wireless/meshpoint-stats[name=key2]/total_bcmc_pkts"
			::= { extremeWingStatsDevWlMcxMeshpointStatsEntry 23 }

		
		-- 1.3.6.1.4.1.1916.2.131.50.1.4.2.25.21.3.1.24
		extremeWingStatsDevWlMcxMeshpointStatsTxMgmtPkts OBJECT-TYPE
			SYNTAX Counter64
			MAX-ACCESS read-only
			STATUS current
			DESCRIPTION
				"Number of management packets of transmitted by the node
				
				XPath: /extremeWing-stats/device[mac=key1]/wireless/meshpoint-stats[name=key2]/tx_mgmt_pkts"
			::= { extremeWingStatsDevWlMcxMeshpointStatsEntry 24 }

		
		-- 1.3.6.1.4.1.1916.2.131.50.1.4.2.25.21.3.1.25
		extremeWingStatsDevWlMcxMeshpointStatsRxMgmtPkts OBJECT-TYPE
			SYNTAX Counter64
			MAX-ACCESS read-only
			STATUS current
			DESCRIPTION
				"Number of management packets of received by the node
				
				XPath: /extremeWing-stats/device[mac=key1]/wireless/meshpoint-stats[name=key2]/rx_mgmt_pkts"
			::= { extremeWingStatsDevWlMcxMeshpointStatsEntry 25 }

		
		-- 1.3.6.1.4.1.1916.2.131.50.1.4.2.25.21.3.1.26
		extremeWingStatsDevWlMcxMeshpointStatsTotalMgmtPkts OBJECT-TYPE
			SYNTAX Counter64
			MAX-ACCESS read-only
			STATUS current
			DESCRIPTION
				"Total Number of management packets Through the domain
				
				XPath: /extremeWing-stats/device[mac=key1]/wireless/meshpoint-stats[name=key2]/total_mgmt_pkts"
			::= { extremeWingStatsDevWlMcxMeshpointStatsEntry 26 }

		
		-- 1.3.6.1.4.1.1916.2.131.50.1.4.2.25.21.3.1.27
		extremeWingStatsDevWlMcxMeshpointStatsMaxUserRate OBJECT-TYPE
			SYNTAX Unsigned32
			UNITS "kbps"
			MAX-ACCESS read-only
			STATUS current
			DESCRIPTION
				"Theoretic maximum user-level data rate
				
				XPath: /extremeWing-stats/device[mac=key1]/wireless/meshpoint-stats[name=key2]/max_user_rate"
			::= { extremeWingStatsDevWlMcxMeshpointStatsEntry 27 }

		
		-- 1.3.6.1.4.1.1916.2.131.50.1.4.2.25.21.4
		extremeWingStatsDevWlMcxMeshpointNeighborsTable OBJECT-TYPE
			SYNTAX SEQUENCE OF ExtremeWingStatsDevWlMcxMeshpointNeighborsEntry
			MAX-ACCESS not-accessible
			STATUS current
			DESCRIPTION
				"
				
				/extremeWing-stats/device/wireless/meshpoint-neighbors"
			::= { extremeWingStatsDevWlMcx 4 }

		
		-- 1.3.6.1.4.1.1916.2.131.50.1.4.2.25.21.4.1
		extremeWingStatsDevWlMcxMeshpointNeighborsEntry OBJECT-TYPE
			SYNTAX ExtremeWingStatsDevWlMcxMeshpointNeighborsEntry
			MAX-ACCESS not-accessible
			STATUS current
			DESCRIPTION
				"An entry in the table."
			INDEX { extremeWingStatsDevMac, extremeWingStatsDevWlMcxMeshpointNeighborsMpid }
			::= { extremeWingStatsDevWlMcxMeshpointNeighborsTable 1 }

		
		ExtremeWingStatsDevWlMcxMeshpointNeighborsEntry ::=
			SEQUENCE { 
				extremeWingStatsDevWlMcxMeshpointNeighborsMpid
					ExtremeWingIdentifier,
				extremeWingStatsDevWlMcxMeshpointNeighborsName
					ExtremeWingIdentifier,
				extremeWingStatsDevWlMcxMeshpointNeighborsHostname
					DisplayString,
				extremeWingStatsDevWlMcxMeshpointNeighborsDeviceMac
					DisplayString,
				extremeWingStatsDevWlMcxMeshpointNeighborsNumEntries
					Unsigned32
			 }

		-- 1.3.6.1.4.1.1916.2.131.50.1.4.2.25.21.4.1.1
		extremeWingStatsDevWlMcxMeshpointNeighborsMpid OBJECT-TYPE
			SYNTAX ExtremeWingIdentifier
			MAX-ACCESS read-only
			STATUS current
			DESCRIPTION
				"Mesh Point MAC address
				
				XPath: /extremeWing-stats/device[mac=key1]/wireless/meshpoint-neighbors[mpid=key2]/mpid"
			::= { extremeWingStatsDevWlMcxMeshpointNeighborsEntry 1 }

		
		-- 1.3.6.1.4.1.1916.2.131.50.1.4.2.25.21.4.1.3
		extremeWingStatsDevWlMcxMeshpointNeighborsName OBJECT-TYPE
			SYNTAX ExtremeWingIdentifier
			MAX-ACCESS read-only
			STATUS current
			DESCRIPTION
				"
				
				XPath: /extremeWing-stats/device[mac=key1]/wireless/meshpoint-neighbors[mpid=key2]/name"
			::= { extremeWingStatsDevWlMcxMeshpointNeighborsEntry 3 }

		
		-- 1.3.6.1.4.1.1916.2.131.50.1.4.2.25.21.4.1.4
		extremeWingStatsDevWlMcxMeshpointNeighborsHostname OBJECT-TYPE
			SYNTAX DisplayString (SIZE (64))
			MAX-ACCESS read-only
			STATUS current
			DESCRIPTION
				"hostname of the AP device
				
				XPath: /extremeWing-stats/device[mac=key1]/wireless/meshpoint-neighbors[mpid=key2]/hostname"
			::= { extremeWingStatsDevWlMcxMeshpointNeighborsEntry 4 }

		
		-- 1.3.6.1.4.1.1916.2.131.50.1.4.2.25.21.4.1.5
		extremeWingStatsDevWlMcxMeshpointNeighborsDeviceMac OBJECT-TYPE
			SYNTAX DisplayString
			MAX-ACCESS read-only
			STATUS current
			DESCRIPTION
				"Device MAC address
				
				XPath: /extremeWing-stats/device[mac=key1]/wireless/meshpoint-neighbors[mpid=key2]/device_mac"
			::= { extremeWingStatsDevWlMcxMeshpointNeighborsEntry 5 }

		
		-- 1.3.6.1.4.1.1916.2.131.50.1.4.2.25.21.4.1.6
		extremeWingStatsDevWlMcxMeshpointNeighborsNumEntries OBJECT-TYPE
			SYNTAX Unsigned32
			MAX-ACCESS read-only
			STATUS current
			DESCRIPTION
				"Number of entries on for this table
				
				XPath: /extremeWing-stats/device[mac=key1]/wireless/meshpoint-neighbors[mpid=key2]/num_entries"
			::= { extremeWingStatsDevWlMcxMeshpointNeighborsEntry 6 }

		
		-- 1.3.6.1.4.1.1916.2.131.50.1.4.2.25.21.5
		extremeWingStatsDevWlMcxMeshpointNeighborsEntriesTable OBJECT-TYPE
			SYNTAX SEQUENCE OF ExtremeWingStatsDevWlMcxMeshpointNeighborsEntriesEntry
			MAX-ACCESS not-accessible
			STATUS current
			DESCRIPTION
				"
				
				/extremeWing-stats/device/wireless/meshpoint-neighbors/entries"
			::= { extremeWingStatsDevWlMcx 5 }

		
		-- 1.3.6.1.4.1.1916.2.131.50.1.4.2.25.21.5.1
		extremeWingStatsDevWlMcxMeshpointNeighborsEntriesEntry OBJECT-TYPE
			SYNTAX ExtremeWingStatsDevWlMcxMeshpointNeighborsEntriesEntry
			MAX-ACCESS not-accessible
			STATUS current
			DESCRIPTION
				"An entry in the table."
			INDEX { extremeWingStatsDevMac, extremeWingStatsDevWlMcxMeshpointNeighborsMpid, extremeWingStatsDevWlMcxMeshpointNeighborsEntriesIndex }
			::= { extremeWingStatsDevWlMcxMeshpointNeighborsEntriesTable 1 }

		
		ExtremeWingStatsDevWlMcxMeshpointNeighborsEntriesEntry ::=
			SEQUENCE { 
				extremeWingStatsDevWlMcxMeshpointNeighborsEntriesIndex
					Unsigned32,
				extremeWingStatsDevWlMcxMeshpointNeighborsEntriesNeighborIfid
					DisplayString,
				extremeWingStatsDevWlMcxMeshpointNeighborsEntriesNeighborMpid
					DisplayString,
				extremeWingStatsDevWlMcxMeshpointNeighborsEntriesBoundRoot
					DisplayString,
				extremeWingStatsDevWlMcxMeshpointNeighborsEntriesRootMetric
					Unsigned32,
				extremeWingStatsDevWlMcxMeshpointNeighborsEntriesRootHops
					Unsigned32,
				extremeWingStatsDevWlMcxMeshpointNeighborsEntriesValid
					TruthValue,
				extremeWingStatsDevWlMcxMeshpointNeighborsEntriesRoot
					TruthValue,
				extremeWingStatsDevWlMcxMeshpointNeighborsEntriesProxy
					TruthValue,
				extremeWingStatsDevWlMcxMeshpointNeighborsEntriesGeoReference
					TruthValue,
				extremeWingStatsDevWlMcxMeshpointNeighborsEntriesMobile
					TruthValue,
				extremeWingStatsDevWlMcxMeshpointNeighborsEntriesInterfaceId
					ExtremeWingIdentifier,
				extremeWingStatsDevWlMcxMeshpointNeighborsEntriesAuthState
					DisplayString,
				extremeWingStatsDevWlMcxMeshpointNeighborsEntriesRank
					DisplayString,
				extremeWingStatsDevWlMcxMeshpointNeighborsEntriesResourced
					TruthValue,
				extremeWingStatsDevWlMcxMeshpointNeighborsEntriesLinkQuality
					Unsigned32,
				extremeWingStatsDevWlMcxMeshpointNeighborsEntriesLinkMetric
					Unsigned32,
				extremeWingStatsDevWlMcxMeshpointNeighborsEntriesAge
					Integer32
			 }

		-- 1.3.6.1.4.1.1916.2.131.50.1.4.2.25.21.5.1.1
		extremeWingStatsDevWlMcxMeshpointNeighborsEntriesIndex OBJECT-TYPE
			SYNTAX Unsigned32 (1..4294967295)
			MAX-ACCESS read-only
			STATUS current
			DESCRIPTION
				"Entries Index
				
				XPath: /extremeWing-stats/device[mac=key1]/wireless/meshpoint-neighbors[mpid=key2]/entries[entry_idx=key3]/entry_idx"
			::= { extremeWingStatsDevWlMcxMeshpointNeighborsEntriesEntry 1 }

		
		-- 1.3.6.1.4.1.1916.2.131.50.1.4.2.25.21.5.1.2
		extremeWingStatsDevWlMcxMeshpointNeighborsEntriesNeighborIfid OBJECT-TYPE
			SYNTAX DisplayString
			MAX-ACCESS read-only
			STATUS current
			DESCRIPTION
				"Neighbor interface MAC address
				
				XPath: /extremeWing-stats/device[mac=key1]/wireless/meshpoint-neighbors[mpid=key2]/entries[entry_idx=key3]/neighbor_ifid"
			::= { extremeWingStatsDevWlMcxMeshpointNeighborsEntriesEntry 2 }

		
		-- 1.3.6.1.4.1.1916.2.131.50.1.4.2.25.21.5.1.3
		extremeWingStatsDevWlMcxMeshpointNeighborsEntriesNeighborMpid OBJECT-TYPE
			SYNTAX DisplayString
			MAX-ACCESS read-only
			STATUS current
			DESCRIPTION
				"Neighbor mesh point MAC address
				
				XPath: /extremeWing-stats/device[mac=key1]/wireless/meshpoint-neighbors[mpid=key2]/entries[entry_idx=key3]/neighbor_mpid"
			::= { extremeWingStatsDevWlMcxMeshpointNeighborsEntriesEntry 3 }

		
		-- 1.3.6.1.4.1.1916.2.131.50.1.4.2.25.21.5.1.4
		extremeWingStatsDevWlMcxMeshpointNeighborsEntriesBoundRoot OBJECT-TYPE
			SYNTAX DisplayString
			MAX-ACCESS read-only
			STATUS current
			DESCRIPTION
				"Neighbor's bound root MAC address
				
				XPath: /extremeWing-stats/device[mac=key1]/wireless/meshpoint-neighbors[mpid=key2]/entries[entry_idx=key3]/bound_root"
			::= { extremeWingStatsDevWlMcxMeshpointNeighborsEntriesEntry 4 }

		
		-- 1.3.6.1.4.1.1916.2.131.50.1.4.2.25.21.5.1.5
		extremeWingStatsDevWlMcxMeshpointNeighborsEntriesRootMetric OBJECT-TYPE
			SYNTAX Unsigned32
			MAX-ACCESS read-only
			STATUS current
			DESCRIPTION
				"Route metric to root
				
				XPath: /extremeWing-stats/device[mac=key1]/wireless/meshpoint-neighbors[mpid=key2]/entries[entry_idx=key3]/root_metric"
			::= { extremeWingStatsDevWlMcxMeshpointNeighborsEntriesEntry 5 }

		
		-- 1.3.6.1.4.1.1916.2.131.50.1.4.2.25.21.5.1.6
		extremeWingStatsDevWlMcxMeshpointNeighborsEntriesRootHops OBJECT-TYPE
			SYNTAX Unsigned32
			MAX-ACCESS read-only
			STATUS current
			DESCRIPTION
				"Hops to root
				
				XPath: /extremeWing-stats/device[mac=key1]/wireless/meshpoint-neighbors[mpid=key2]/entries[entry_idx=key3]/root_hops"
			::= { extremeWingStatsDevWlMcxMeshpointNeighborsEntriesEntry 6 }

		
		-- 1.3.6.1.4.1.1916.2.131.50.1.4.2.25.21.5.1.7
		extremeWingStatsDevWlMcxMeshpointNeighborsEntriesValid OBJECT-TYPE
			SYNTAX TruthValue
			MAX-ACCESS read-only
			STATUS current
			DESCRIPTION
				"Mesh point services are valid
				
				XPath: /extremeWing-stats/device[mac=key1]/wireless/meshpoint-neighbors[mpid=key2]/entries[entry_idx=key3]/valid"
			::= { extremeWingStatsDevWlMcxMeshpointNeighborsEntriesEntry 7 }

		
		-- 1.3.6.1.4.1.1916.2.131.50.1.4.2.25.21.5.1.8
		extremeWingStatsDevWlMcxMeshpointNeighborsEntriesRoot OBJECT-TYPE
			SYNTAX TruthValue
			MAX-ACCESS read-only
			STATUS current
			DESCRIPTION
				"Mesh point is a root
				
				XPath: /extremeWing-stats/device[mac=key1]/wireless/meshpoint-neighbors[mpid=key2]/entries[entry_idx=key3]/root"
			::= { extremeWingStatsDevWlMcxMeshpointNeighborsEntriesEntry 8 }

		
		-- 1.3.6.1.4.1.1916.2.131.50.1.4.2.25.21.5.1.9
		extremeWingStatsDevWlMcxMeshpointNeighborsEntriesProxy OBJECT-TYPE
			SYNTAX TruthValue
			MAX-ACCESS read-only
			STATUS current
			DESCRIPTION
				"Mesh point can proxy for others
				
				XPath: /extremeWing-stats/device[mac=key1]/wireless/meshpoint-neighbors[mpid=key2]/entries[entry_idx=key3]/proxy"
			::= { extremeWingStatsDevWlMcxMeshpointNeighborsEntriesEntry 9 }

		
		-- 1.3.6.1.4.1.1916.2.131.50.1.4.2.25.21.5.1.10
		extremeWingStatsDevWlMcxMeshpointNeighborsEntriesGeoReference OBJECT-TYPE
			SYNTAX TruthValue
			MAX-ACCESS read-only
			STATUS current
			DESCRIPTION
				"Mesh point can provide a geo reference
				
				XPath: /extremeWing-stats/device[mac=key1]/wireless/meshpoint-neighbors[mpid=key2]/entries[entry_idx=key3]/geo_reference"
			::= { extremeWingStatsDevWlMcxMeshpointNeighborsEntriesEntry 10 }

		
		-- 1.3.6.1.4.1.1916.2.131.50.1.4.2.25.21.5.1.11
		extremeWingStatsDevWlMcxMeshpointNeighborsEntriesMobile OBJECT-TYPE
			SYNTAX TruthValue
			MAX-ACCESS read-only
			STATUS current
			DESCRIPTION
				"Mesh point is mobile
				
				XPath: /extremeWing-stats/device[mac=key1]/wireless/meshpoint-neighbors[mpid=key2]/entries[entry_idx=key3]/mobile"
			::= { extremeWingStatsDevWlMcxMeshpointNeighborsEntriesEntry 11 }

		
		-- 1.3.6.1.4.1.1916.2.131.50.1.4.2.25.21.5.1.12
		extremeWingStatsDevWlMcxMeshpointNeighborsEntriesInterfaceId OBJECT-TYPE
			SYNTAX ExtremeWingIdentifier
			MAX-ACCESS read-only
			STATUS current
			DESCRIPTION
				"Unique ID for each interfacce in the form of AP-MAC:%c%d. E.g., 00-A0-F8-00-00-00:R1
				
				XPath: /extremeWing-stats/device[mac=key1]/wireless/meshpoint-neighbors[mpid=key2]/entries[entry_idx=key3]/interface_id"
			::= { extremeWingStatsDevWlMcxMeshpointNeighborsEntriesEntry 12 }

		
		-- 1.3.6.1.4.1.1916.2.131.50.1.4.2.25.21.5.1.13
		extremeWingStatsDevWlMcxMeshpointNeighborsEntriesAuthState OBJECT-TYPE
			SYNTAX DisplayString
			MAX-ACCESS read-only
			STATUS current
			DESCRIPTION
				"Authorization state
				
				Values:
				Init,
				Enabled,
				Failed,
				In
				Progress,
				N/A
				
				XPath: /extremeWing-stats/device[mac=key1]/wireless/meshpoint-neighbors[mpid=key2]/entries[entry_idx=key3]/auth_state"
			::= { extremeWingStatsDevWlMcxMeshpointNeighborsEntriesEntry 13 }

		
		-- 1.3.6.1.4.1.1916.2.131.50.1.4.2.25.21.5.1.14
		extremeWingStatsDevWlMcxMeshpointNeighborsEntriesRank OBJECT-TYPE
			SYNTAX DisplayString
			MAX-ACCESS read-only
			STATUS current
			DESCRIPTION
				"Ranking
				
				Values:
				8,
				7,
				6,
				5,
				4,
				3,
				2,
				1,
				0,
				-1
				
				XPath: /extremeWing-stats/device[mac=key1]/wireless/meshpoint-neighbors[mpid=key2]/entries[entry_idx=key3]/rank"
			::= { extremeWingStatsDevWlMcxMeshpointNeighborsEntriesEntry 14 }

		
		-- 1.3.6.1.4.1.1916.2.131.50.1.4.2.25.21.5.1.15
		extremeWingStatsDevWlMcxMeshpointNeighborsEntriesResourced OBJECT-TYPE
			SYNTAX TruthValue
			MAX-ACCESS read-only
			STATUS current
			DESCRIPTION
				"Neighbor has an Client resource
				
				XPath: /extremeWing-stats/device[mac=key1]/wireless/meshpoint-neighbors[mpid=key2]/entries[entry_idx=key3]/resourced"
			::= { extremeWingStatsDevWlMcxMeshpointNeighborsEntriesEntry 15 }

		
		-- 1.3.6.1.4.1.1916.2.131.50.1.4.2.25.21.5.1.16
		extremeWingStatsDevWlMcxMeshpointNeighborsEntriesLinkQuality OBJECT-TYPE
			SYNTAX Unsigned32
			MAX-ACCESS read-only
			STATUS current
			DESCRIPTION
				"Link Quality
				
				XPath: /extremeWing-stats/device[mac=key1]/wireless/meshpoint-neighbors[mpid=key2]/entries[entry_idx=key3]/link_quality"
			::= { extremeWingStatsDevWlMcxMeshpointNeighborsEntriesEntry 16 }

		
		-- 1.3.6.1.4.1.1916.2.131.50.1.4.2.25.21.5.1.17
		extremeWingStatsDevWlMcxMeshpointNeighborsEntriesLinkMetric OBJECT-TYPE
			SYNTAX Unsigned32
			MAX-ACCESS read-only
			STATUS current
			DESCRIPTION
				"Route metric to neighbor
				
				XPath: /extremeWing-stats/device[mac=key1]/wireless/meshpoint-neighbors[mpid=key2]/entries[entry_idx=key3]/link_metric"
			::= { extremeWingStatsDevWlMcxMeshpointNeighborsEntriesEntry 17 }

		
		-- 1.3.6.1.4.1.1916.2.131.50.1.4.2.25.21.5.1.18
		extremeWingStatsDevWlMcxMeshpointNeighborsEntriesAge OBJECT-TYPE
			SYNTAX Integer32
			MAX-ACCESS read-only
			STATUS current
			DESCRIPTION
				"Last time used
				
				XPath: /extremeWing-stats/device[mac=key1]/wireless/meshpoint-neighbors[mpid=key2]/entries[entry_idx=key3]/age"
			::= { extremeWingStatsDevWlMcxMeshpointNeighborsEntriesEntry 18 }

		
		-- 1.3.6.1.4.1.1916.2.131.50.1.4.2.25.21.6
		extremeWingStatsDevWlMcxMeshpointPathsTable OBJECT-TYPE
			SYNTAX SEQUENCE OF ExtremeWingStatsDevWlMcxMeshpointPathsEntry
			MAX-ACCESS not-accessible
			STATUS current
			DESCRIPTION
				"
				
				/extremeWing-stats/device/wireless/meshpoint-paths"
			::= { extremeWingStatsDevWlMcx 6 }

		
		-- 1.3.6.1.4.1.1916.2.131.50.1.4.2.25.21.6.1
		extremeWingStatsDevWlMcxMeshpointPathsEntry OBJECT-TYPE
			SYNTAX ExtremeWingStatsDevWlMcxMeshpointPathsEntry
			MAX-ACCESS not-accessible
			STATUS current
			DESCRIPTION
				"An entry in the table."
			INDEX { extremeWingStatsDevMac, extremeWingStatsDevWlMcxMeshpointPathsMpid }
			::= { extremeWingStatsDevWlMcxMeshpointPathsTable 1 }

		
		ExtremeWingStatsDevWlMcxMeshpointPathsEntry ::=
			SEQUENCE { 
				extremeWingStatsDevWlMcxMeshpointPathsMpid
					ExtremeWingIdentifier,
				extremeWingStatsDevWlMcxMeshpointPathsName
					ExtremeWingIdentifier,
				extremeWingStatsDevWlMcxMeshpointPathsHostname
					DisplayString,
				extremeWingStatsDevWlMcxMeshpointPathsDeviceMac
					DisplayString,
				extremeWingStatsDevWlMcxMeshpointPathsNumEntries
					Unsigned32
			 }

		-- 1.3.6.1.4.1.1916.2.131.50.1.4.2.25.21.6.1.1
		extremeWingStatsDevWlMcxMeshpointPathsMpid OBJECT-TYPE
			SYNTAX ExtremeWingIdentifier
			MAX-ACCESS read-only
			STATUS current
			DESCRIPTION
				"Mesh Point MAC address
				
				XPath: /extremeWing-stats/device[mac=key1]/wireless/meshpoint-paths[mpid=key2]/mpid"
			::= { extremeWingStatsDevWlMcxMeshpointPathsEntry 1 }

		
		-- 1.3.6.1.4.1.1916.2.131.50.1.4.2.25.21.6.1.3
		extremeWingStatsDevWlMcxMeshpointPathsName OBJECT-TYPE
			SYNTAX ExtremeWingIdentifier
			MAX-ACCESS read-only
			STATUS current
			DESCRIPTION
				"
				
				XPath: /extremeWing-stats/device[mac=key1]/wireless/meshpoint-paths[mpid=key2]/name"
			::= { extremeWingStatsDevWlMcxMeshpointPathsEntry 3 }

		
		-- 1.3.6.1.4.1.1916.2.131.50.1.4.2.25.21.6.1.4
		extremeWingStatsDevWlMcxMeshpointPathsHostname OBJECT-TYPE
			SYNTAX DisplayString (SIZE (64))
			MAX-ACCESS read-only
			STATUS current
			DESCRIPTION
				"hostname of the AP device
				
				XPath: /extremeWing-stats/device[mac=key1]/wireless/meshpoint-paths[mpid=key2]/hostname"
			::= { extremeWingStatsDevWlMcxMeshpointPathsEntry 4 }

		
		-- 1.3.6.1.4.1.1916.2.131.50.1.4.2.25.21.6.1.5
		extremeWingStatsDevWlMcxMeshpointPathsDeviceMac OBJECT-TYPE
			SYNTAX DisplayString
			MAX-ACCESS read-only
			STATUS current
			DESCRIPTION
				"Device MAC address
				
				XPath: /extremeWing-stats/device[mac=key1]/wireless/meshpoint-paths[mpid=key2]/device_mac"
			::= { extremeWingStatsDevWlMcxMeshpointPathsEntry 5 }

		
		-- 1.3.6.1.4.1.1916.2.131.50.1.4.2.25.21.6.1.6
		extremeWingStatsDevWlMcxMeshpointPathsNumEntries OBJECT-TYPE
			SYNTAX Unsigned32
			MAX-ACCESS read-only
			STATUS current
			DESCRIPTION
				"Number of entries on for this table
				
				XPath: /extremeWing-stats/device[mac=key1]/wireless/meshpoint-paths[mpid=key2]/num_entries"
			::= { extremeWingStatsDevWlMcxMeshpointPathsEntry 6 }

		
		-- 1.3.6.1.4.1.1916.2.131.50.1.4.2.25.21.7
		extremeWingStatsDevWlMcxMeshpointPathsEntriesTable OBJECT-TYPE
			SYNTAX SEQUENCE OF ExtremeWingStatsDevWlMcxMeshpointPathsEntriesEntry
			MAX-ACCESS not-accessible
			STATUS current
			DESCRIPTION
				"
				
				/extremeWing-stats/device/wireless/meshpoint-paths/entries"
			::= { extremeWingStatsDevWlMcx 7 }

		
		-- 1.3.6.1.4.1.1916.2.131.50.1.4.2.25.21.7.1
		extremeWingStatsDevWlMcxMeshpointPathsEntriesEntry OBJECT-TYPE
			SYNTAX ExtremeWingStatsDevWlMcxMeshpointPathsEntriesEntry
			MAX-ACCESS not-accessible
			STATUS current
			DESCRIPTION
				"An entry in the table."
			INDEX { extremeWingStatsDevMac, extremeWingStatsDevWlMcxMeshpointPathsMpid, extremeWingStatsDevWlMcxMeshpointPathsEntriesIndex }
			::= { extremeWingStatsDevWlMcxMeshpointPathsEntriesTable 1 }

		
		ExtremeWingStatsDevWlMcxMeshpointPathsEntriesEntry ::=
			SEQUENCE { 
				extremeWingStatsDevWlMcxMeshpointPathsEntriesIndex
					Unsigned32,
				extremeWingStatsDevWlMcxMeshpointPathsEntriesDestMpid
					DisplayString,
				extremeWingStatsDevWlMcxMeshpointPathsEntriesNextHopIfid
					DisplayString,
				extremeWingStatsDevWlMcxMeshpointPathsEntriesPathMetric
					Unsigned32,
				extremeWingStatsDevWlMcxMeshpointPathsEntriesHops
					Unsigned32,
				extremeWingStatsDevWlMcxMeshpointPathsEntriesPathState
					DisplayString,
				extremeWingStatsDevWlMcxMeshpointPathsEntriesBindState
					DisplayString,
				extremeWingStatsDevWlMcxMeshpointPathsEntriesValid
					TruthValue,
				extremeWingStatsDevWlMcxMeshpointPathsEntriesRoot
					TruthValue,
				extremeWingStatsDevWlMcxMeshpointPathsEntriesProxy
					TruthValue,
				extremeWingStatsDevWlMcxMeshpointPathsEntriesGeoReference
					TruthValue,
				extremeWingStatsDevWlMcxMeshpointPathsEntriesMobile
					TruthValue,
				extremeWingStatsDevWlMcxMeshpointPathsEntriesDestinationSequence
					Unsigned32,
				extremeWingStatsDevWlMcxMeshpointPathsEntriesPathTimeout
					Integer32,
				extremeWingStatsDevWlMcxMeshpointPathsEntriesNewRouteTimeout
					Integer32,
				extremeWingStatsDevWlMcxMeshpointPathsEntriesDestMintId
					DisplayString
			 }

		-- 1.3.6.1.4.1.1916.2.131.50.1.4.2.25.21.7.1.1
		extremeWingStatsDevWlMcxMeshpointPathsEntriesIndex OBJECT-TYPE
			SYNTAX Unsigned32 (1..4294967295)
			MAX-ACCESS read-only
			STATUS current
			DESCRIPTION
				"Entries Index
				
				XPath: /extremeWing-stats/device[mac=key1]/wireless/meshpoint-paths[mpid=key2]/entries[entry_idx=key3]/entry_idx"
			::= { extremeWingStatsDevWlMcxMeshpointPathsEntriesEntry 1 }

		
		-- 1.3.6.1.4.1.1916.2.131.50.1.4.2.25.21.7.1.2
		extremeWingStatsDevWlMcxMeshpointPathsEntriesDestMpid OBJECT-TYPE
			SYNTAX DisplayString
			MAX-ACCESS read-only
			STATUS current
			DESCRIPTION
				"Destination mesh point MAC address
				
				XPath: /extremeWing-stats/device[mac=key1]/wireless/meshpoint-paths[mpid=key2]/entries[entry_idx=key3]/dest_mpid"
			::= { extremeWingStatsDevWlMcxMeshpointPathsEntriesEntry 2 }

		
		-- 1.3.6.1.4.1.1916.2.131.50.1.4.2.25.21.7.1.3
		extremeWingStatsDevWlMcxMeshpointPathsEntriesNextHopIfid OBJECT-TYPE
			SYNTAX DisplayString
			MAX-ACCESS read-only
			STATUS current
			DESCRIPTION
				"Next hop interface MAC address
				
				XPath: /extremeWing-stats/device[mac=key1]/wireless/meshpoint-paths[mpid=key2]/entries[entry_idx=key3]/next_hop_ifid"
			::= { extremeWingStatsDevWlMcxMeshpointPathsEntriesEntry 3 }

		
		-- 1.3.6.1.4.1.1916.2.131.50.1.4.2.25.21.7.1.4
		extremeWingStatsDevWlMcxMeshpointPathsEntriesPathMetric OBJECT-TYPE
			SYNTAX Unsigned32
			MAX-ACCESS read-only
			STATUS current
			DESCRIPTION
				"Route metric to destination
				
				XPath: /extremeWing-stats/device[mac=key1]/wireless/meshpoint-paths[mpid=key2]/entries[entry_idx=key3]/path_metric"
			::= { extremeWingStatsDevWlMcxMeshpointPathsEntriesEntry 4 }

		
		-- 1.3.6.1.4.1.1916.2.131.50.1.4.2.25.21.7.1.5
		extremeWingStatsDevWlMcxMeshpointPathsEntriesHops OBJECT-TYPE
			SYNTAX Unsigned32
			MAX-ACCESS read-only
			STATUS current
			DESCRIPTION
				"Hops to destination
				
				XPath: /extremeWing-stats/device[mac=key1]/wireless/meshpoint-paths[mpid=key2]/entries[entry_idx=key3]/hops"
			::= { extremeWingStatsDevWlMcxMeshpointPathsEntriesEntry 5 }

		
		-- 1.3.6.1.4.1.1916.2.131.50.1.4.2.25.21.7.1.6
		extremeWingStatsDevWlMcxMeshpointPathsEntriesPathState OBJECT-TYPE
			SYNTAX DisplayString
			MAX-ACCESS read-only
			STATUS current
			DESCRIPTION
				"Path state
				
				Values:
				Valid,
				Req-Timeout,
				Expired,
				In
				Progress,
				Fwd-To-Root,
				Invalid
				
				XPath: /extremeWing-stats/device[mac=key1]/wireless/meshpoint-paths[mpid=key2]/entries[entry_idx=key3]/path_state"
			::= { extremeWingStatsDevWlMcxMeshpointPathsEntriesEntry 6 }

		
		-- 1.3.6.1.4.1.1916.2.131.50.1.4.2.25.21.7.1.7
		extremeWingStatsDevWlMcxMeshpointPathsEntriesBindState OBJECT-TYPE
			SYNTAX DisplayString
			MAX-ACCESS read-only
			STATUS current
			DESCRIPTION
				"Bind state
				
				Values:
				Bound,
				Unbound,
				Proxy-Upd,
				Disfavored,
				Removed,
				Invalid
				
				XPath: /extremeWing-stats/device[mac=key1]/wireless/meshpoint-paths[mpid=key2]/entries[entry_idx=key3]/bind_state"
			::= { extremeWingStatsDevWlMcxMeshpointPathsEntriesEntry 7 }

		
		-- 1.3.6.1.4.1.1916.2.131.50.1.4.2.25.21.7.1.8
		extremeWingStatsDevWlMcxMeshpointPathsEntriesValid OBJECT-TYPE
			SYNTAX TruthValue
			MAX-ACCESS read-only
			STATUS current
			DESCRIPTION
				"Mesh point services are valid
				
				XPath: /extremeWing-stats/device[mac=key1]/wireless/meshpoint-paths[mpid=key2]/entries[entry_idx=key3]/valid"
			::= { extremeWingStatsDevWlMcxMeshpointPathsEntriesEntry 8 }

		
		-- 1.3.6.1.4.1.1916.2.131.50.1.4.2.25.21.7.1.9
		extremeWingStatsDevWlMcxMeshpointPathsEntriesRoot OBJECT-TYPE
			SYNTAX TruthValue
			MAX-ACCESS read-only
			STATUS current
			DESCRIPTION
				"Mesh point is a root
				
				XPath: /extremeWing-stats/device[mac=key1]/wireless/meshpoint-paths[mpid=key2]/entries[entry_idx=key3]/root"
			::= { extremeWingStatsDevWlMcxMeshpointPathsEntriesEntry 9 }

		
		-- 1.3.6.1.4.1.1916.2.131.50.1.4.2.25.21.7.1.10
		extremeWingStatsDevWlMcxMeshpointPathsEntriesProxy OBJECT-TYPE
			SYNTAX TruthValue
			MAX-ACCESS read-only
			STATUS current
			DESCRIPTION
				"Mesh point can proxy for others
				
				XPath: /extremeWing-stats/device[mac=key1]/wireless/meshpoint-paths[mpid=key2]/entries[entry_idx=key3]/proxy"
			::= { extremeWingStatsDevWlMcxMeshpointPathsEntriesEntry 10 }

		
		-- 1.3.6.1.4.1.1916.2.131.50.1.4.2.25.21.7.1.11
		extremeWingStatsDevWlMcxMeshpointPathsEntriesGeoReference OBJECT-TYPE
			SYNTAX TruthValue
			MAX-ACCESS read-only
			STATUS current
			DESCRIPTION
				"Mesh point can provide a geo reference
				
				XPath: /extremeWing-stats/device[mac=key1]/wireless/meshpoint-paths[mpid=key2]/entries[entry_idx=key3]/geo_reference"
			::= { extremeWingStatsDevWlMcxMeshpointPathsEntriesEntry 11 }

		
		-- 1.3.6.1.4.1.1916.2.131.50.1.4.2.25.21.7.1.12
		extremeWingStatsDevWlMcxMeshpointPathsEntriesMobile OBJECT-TYPE
			SYNTAX TruthValue
			MAX-ACCESS read-only
			STATUS current
			DESCRIPTION
				"Mesh point is mobile
				
				XPath: /extremeWing-stats/device[mac=key1]/wireless/meshpoint-paths[mpid=key2]/entries[entry_idx=key3]/mobile"
			::= { extremeWingStatsDevWlMcxMeshpointPathsEntriesEntry 12 }

		
		-- 1.3.6.1.4.1.1916.2.131.50.1.4.2.25.21.7.1.13
		extremeWingStatsDevWlMcxMeshpointPathsEntriesDestinationSequence OBJECT-TYPE
			SYNTAX Unsigned32
			MAX-ACCESS read-only
			STATUS current
			DESCRIPTION
				"Destination sequence number
				
				XPath: /extremeWing-stats/device[mac=key1]/wireless/meshpoint-paths[mpid=key2]/entries[entry_idx=key3]/destination_sequence"
			::= { extremeWingStatsDevWlMcxMeshpointPathsEntriesEntry 13 }

		
		-- 1.3.6.1.4.1.1916.2.131.50.1.4.2.25.21.7.1.14
		extremeWingStatsDevWlMcxMeshpointPathsEntriesPathTimeout OBJECT-TYPE
			SYNTAX Integer32
			MAX-ACCESS read-only
			STATUS current
			DESCRIPTION
				"Path timeout
				
				XPath: /extremeWing-stats/device[mac=key1]/wireless/meshpoint-paths[mpid=key2]/entries[entry_idx=key3]/path_timeout"
			::= { extremeWingStatsDevWlMcxMeshpointPathsEntriesEntry 14 }

		
		-- 1.3.6.1.4.1.1916.2.131.50.1.4.2.25.21.7.1.15
		extremeWingStatsDevWlMcxMeshpointPathsEntriesNewRouteTimeout OBJECT-TYPE
			SYNTAX Integer32
			MAX-ACCESS read-only
			STATUS current
			DESCRIPTION
				"New route timeout
				
				XPath: /extremeWing-stats/device[mac=key1]/wireless/meshpoint-paths[mpid=key2]/entries[entry_idx=key3]/new_route_timeout"
			::= { extremeWingStatsDevWlMcxMeshpointPathsEntriesEntry 15 }

		
		-- 1.3.6.1.4.1.1916.2.131.50.1.4.2.25.21.7.1.16
		extremeWingStatsDevWlMcxMeshpointPathsEntriesDestMintId OBJECT-TYPE
			SYNTAX DisplayString
			MAX-ACCESS read-only
			STATUS current
			DESCRIPTION
				"Destination MiNT address
				
				XPath: /extremeWing-stats/device[mac=key1]/wireless/meshpoint-paths[mpid=key2]/entries[entry_idx=key3]/dest_mint_id"
			::= { extremeWingStatsDevWlMcxMeshpointPathsEntriesEntry 16 }

		
		-- 1.3.6.1.4.1.1916.2.131.50.1.4.2.25.21.8
		extremeWingStatsDevWlMcxMeshpointRootsTable OBJECT-TYPE
			SYNTAX SEQUENCE OF ExtremeWingStatsDevWlMcxMeshpointRootsEntry
			MAX-ACCESS not-accessible
			STATUS current
			DESCRIPTION
				"
				
				/extremeWing-stats/device/wireless/meshpoint-roots"
			::= { extremeWingStatsDevWlMcx 8 }

		
		-- 1.3.6.1.4.1.1916.2.131.50.1.4.2.25.21.8.1
		extremeWingStatsDevWlMcxMeshpointRootsEntry OBJECT-TYPE
			SYNTAX ExtremeWingStatsDevWlMcxMeshpointRootsEntry
			MAX-ACCESS not-accessible
			STATUS current
			DESCRIPTION
				"An entry in the table."
			INDEX { extremeWingStatsDevMac, extremeWingStatsDevWlMcxMeshpointRootsMpid }
			::= { extremeWingStatsDevWlMcxMeshpointRootsTable 1 }

		
		ExtremeWingStatsDevWlMcxMeshpointRootsEntry ::=
			SEQUENCE { 
				extremeWingStatsDevWlMcxMeshpointRootsMpid
					ExtremeWingIdentifier,
				extremeWingStatsDevWlMcxMeshpointRootsName
					ExtremeWingIdentifier,
				extremeWingStatsDevWlMcxMeshpointRootsHostname
					DisplayString,
				extremeWingStatsDevWlMcxMeshpointRootsDeviceMac
					DisplayString,
				extremeWingStatsDevWlMcxMeshpointRootsNumEntries
					Unsigned32
			 }

		-- 1.3.6.1.4.1.1916.2.131.50.1.4.2.25.21.8.1.1
		extremeWingStatsDevWlMcxMeshpointRootsMpid OBJECT-TYPE
			SYNTAX ExtremeWingIdentifier
			MAX-ACCESS read-only
			STATUS current
			DESCRIPTION
				"Mesh Point MAC address
				
				XPath: /extremeWing-stats/device[mac=key1]/wireless/meshpoint-roots[mpid=key2]/mpid"
			::= { extremeWingStatsDevWlMcxMeshpointRootsEntry 1 }

		
		-- 1.3.6.1.4.1.1916.2.131.50.1.4.2.25.21.8.1.3
		extremeWingStatsDevWlMcxMeshpointRootsName OBJECT-TYPE
			SYNTAX ExtremeWingIdentifier
			MAX-ACCESS read-only
			STATUS current
			DESCRIPTION
				"
				
				XPath: /extremeWing-stats/device[mac=key1]/wireless/meshpoint-roots[mpid=key2]/name"
			::= { extremeWingStatsDevWlMcxMeshpointRootsEntry 3 }

		
		-- 1.3.6.1.4.1.1916.2.131.50.1.4.2.25.21.8.1.4
		extremeWingStatsDevWlMcxMeshpointRootsHostname OBJECT-TYPE
			SYNTAX DisplayString (SIZE (64))
			MAX-ACCESS read-only
			STATUS current
			DESCRIPTION
				"hostname of the AP device
				
				XPath: /extremeWing-stats/device[mac=key1]/wireless/meshpoint-roots[mpid=key2]/hostname"
			::= { extremeWingStatsDevWlMcxMeshpointRootsEntry 4 }

		
		-- 1.3.6.1.4.1.1916.2.131.50.1.4.2.25.21.8.1.5
		extremeWingStatsDevWlMcxMeshpointRootsDeviceMac OBJECT-TYPE
			SYNTAX DisplayString
			MAX-ACCESS read-only
			STATUS current
			DESCRIPTION
				"Device MAC address
				
				XPath: /extremeWing-stats/device[mac=key1]/wireless/meshpoint-roots[mpid=key2]/device_mac"
			::= { extremeWingStatsDevWlMcxMeshpointRootsEntry 5 }

		
		-- 1.3.6.1.4.1.1916.2.131.50.1.4.2.25.21.8.1.6
		extremeWingStatsDevWlMcxMeshpointRootsNumEntries OBJECT-TYPE
			SYNTAX Unsigned32
			MAX-ACCESS read-only
			STATUS current
			DESCRIPTION
				"Number of entries on for this table
				
				XPath: /extremeWing-stats/device[mac=key1]/wireless/meshpoint-roots[mpid=key2]/num_entries"
			::= { extremeWingStatsDevWlMcxMeshpointRootsEntry 6 }

		
		-- 1.3.6.1.4.1.1916.2.131.50.1.4.2.25.21.9
		extremeWingStatsDevWlMcxMeshpointRootsEntriesTable OBJECT-TYPE
			SYNTAX SEQUENCE OF ExtremeWingStatsDevWlMcxMeshpointRootsEntriesEntry
			MAX-ACCESS not-accessible
			STATUS current
			DESCRIPTION
				"
				
				/extremeWing-stats/device/wireless/meshpoint-roots/entries"
			::= { extremeWingStatsDevWlMcx 9 }

		
		-- 1.3.6.1.4.1.1916.2.131.50.1.4.2.25.21.9.1
		extremeWingStatsDevWlMcxMeshpointRootsEntriesEntry OBJECT-TYPE
			SYNTAX ExtremeWingStatsDevWlMcxMeshpointRootsEntriesEntry
			MAX-ACCESS not-accessible
			STATUS current
			DESCRIPTION
				"An entry in the table."
			INDEX { extremeWingStatsDevMac, extremeWingStatsDevWlMcxMeshpointRootsMpid, extremeWingStatsDevWlMcxMeshpointRootsEntriesIndex }
			::= { extremeWingStatsDevWlMcxMeshpointRootsEntriesTable 1 }

		
		ExtremeWingStatsDevWlMcxMeshpointRootsEntriesEntry ::=
			SEQUENCE { 
				extremeWingStatsDevWlMcxMeshpointRootsEntriesIndex
					Unsigned32,
				extremeWingStatsDevWlMcxMeshpointRootsEntriesRootMpid
					DisplayString,
				extremeWingStatsDevWlMcxMeshpointRootsEntriesNextHopIfid
					DisplayString,
				extremeWingStatsDevWlMcxMeshpointRootsEntriesInterfaceId
					ExtremeWingIdentifier,
				extremeWingStatsDevWlMcxMeshpointRootsEntriesRecommended
					TruthValue,
				extremeWingStatsDevWlMcxMeshpointRootsEntriesBindFailed
					TruthValue,
				extremeWingStatsDevWlMcxMeshpointRootsEntriesPathFailed
					TruthValue,
				extremeWingStatsDevWlMcxMeshpointRootsEntriesPathMetric
					Unsigned32,
				extremeWingStatsDevWlMcxMeshpointRootsEntriesIfBias
					Integer32,
				extremeWingStatsDevWlMcxMeshpointRootsEntriesNeighborBias
					Integer32,
				extremeWingStatsDevWlMcxMeshpointRootsEntriesRootBias
					Integer32
			 }

		-- 1.3.6.1.4.1.1916.2.131.50.1.4.2.25.21.9.1.1
		extremeWingStatsDevWlMcxMeshpointRootsEntriesIndex OBJECT-TYPE
			SYNTAX Unsigned32 (1..4294967295)
			MAX-ACCESS read-write
			STATUS current
			DESCRIPTION
				"Entries Index
				
				XPath: /extremeWing-stats/device[mac=key1]/wireless/meshpoint-roots[mpid=key2]/entries[entry_idx=key3]/entry_idx"
			::= { extremeWingStatsDevWlMcxMeshpointRootsEntriesEntry 1 }

		
		-- 1.3.6.1.4.1.1916.2.131.50.1.4.2.25.21.9.1.2
		extremeWingStatsDevWlMcxMeshpointRootsEntriesRootMpid OBJECT-TYPE
			SYNTAX DisplayString
			MAX-ACCESS read-only
			STATUS current
			DESCRIPTION
				"Root mesh point MAC address
				
				XPath: /extremeWing-stats/device[mac=key1]/wireless/meshpoint-roots[mpid=key2]/entries[entry_idx=key3]/root_mpid"
			::= { extremeWingStatsDevWlMcxMeshpointRootsEntriesEntry 2 }

		
		-- 1.3.6.1.4.1.1916.2.131.50.1.4.2.25.21.9.1.3
		extremeWingStatsDevWlMcxMeshpointRootsEntriesNextHopIfid OBJECT-TYPE
			SYNTAX DisplayString
			MAX-ACCESS read-only
			STATUS current
			DESCRIPTION
				"Next hop interface MAC address
				
				XPath: /extremeWing-stats/device[mac=key1]/wireless/meshpoint-roots[mpid=key2]/entries[entry_idx=key3]/next_hop_ifid"
			::= { extremeWingStatsDevWlMcxMeshpointRootsEntriesEntry 3 }

		
		-- 1.3.6.1.4.1.1916.2.131.50.1.4.2.25.21.9.1.4
		extremeWingStatsDevWlMcxMeshpointRootsEntriesInterfaceId OBJECT-TYPE
			SYNTAX ExtremeWingIdentifier
			MAX-ACCESS read-only
			STATUS current
			DESCRIPTION
				"Unique ID for each interfacce in the form of AP-MAC:%c%d. E.g., 00-A0-F8-00-00-00:R1
				
				XPath: /extremeWing-stats/device[mac=key1]/wireless/meshpoint-roots[mpid=key2]/entries[entry_idx=key3]/interface_id"
			::= { extremeWingStatsDevWlMcxMeshpointRootsEntriesEntry 4 }

		
		-- 1.3.6.1.4.1.1916.2.131.50.1.4.2.25.21.9.1.5
		extremeWingStatsDevWlMcxMeshpointRootsEntriesRecommended OBJECT-TYPE
			SYNTAX TruthValue
			MAX-ACCESS read-only
			STATUS current
			DESCRIPTION
				"Recommended root
				
				XPath: /extremeWing-stats/device[mac=key1]/wireless/meshpoint-roots[mpid=key2]/entries[entry_idx=key3]/recommended"
			::= { extremeWingStatsDevWlMcxMeshpointRootsEntriesEntry 5 }

		
		-- 1.3.6.1.4.1.1916.2.131.50.1.4.2.25.21.9.1.6
		extremeWingStatsDevWlMcxMeshpointRootsEntriesBindFailed OBJECT-TYPE
			SYNTAX TruthValue
			MAX-ACCESS read-only
			STATUS current
			DESCRIPTION
				"Bind failure
				
				XPath: /extremeWing-stats/device[mac=key1]/wireless/meshpoint-roots[mpid=key2]/entries[entry_idx=key3]/bind_failed"
			::= { extremeWingStatsDevWlMcxMeshpointRootsEntriesEntry 6 }

		
		-- 1.3.6.1.4.1.1916.2.131.50.1.4.2.25.21.9.1.7
		extremeWingStatsDevWlMcxMeshpointRootsEntriesPathFailed OBJECT-TYPE
			SYNTAX TruthValue
			MAX-ACCESS read-only
			STATUS current
			DESCRIPTION
				"Path failure
				
				XPath: /extremeWing-stats/device[mac=key1]/wireless/meshpoint-roots[mpid=key2]/entries[entry_idx=key3]/path_failed"
			::= { extremeWingStatsDevWlMcxMeshpointRootsEntriesEntry 7 }

		
		-- 1.3.6.1.4.1.1916.2.131.50.1.4.2.25.21.9.1.8
		extremeWingStatsDevWlMcxMeshpointRootsEntriesPathMetric OBJECT-TYPE
			SYNTAX Unsigned32
			MAX-ACCESS read-only
			STATUS current
			DESCRIPTION
				"Route metric to destination
				
				XPath: /extremeWing-stats/device[mac=key1]/wireless/meshpoint-roots[mpid=key2]/entries[entry_idx=key3]/path_metric"
			::= { extremeWingStatsDevWlMcxMeshpointRootsEntriesEntry 8 }

		
		-- 1.3.6.1.4.1.1916.2.131.50.1.4.2.25.21.9.1.9
		extremeWingStatsDevWlMcxMeshpointRootsEntriesIfBias OBJECT-TYPE
			SYNTAX Integer32
			MAX-ACCESS read-only
			STATUS current
			DESCRIPTION
				"Interface bias
				
				XPath: /extremeWing-stats/device[mac=key1]/wireless/meshpoint-roots[mpid=key2]/entries[entry_idx=key3]/if_bias"
			::= { extremeWingStatsDevWlMcxMeshpointRootsEntriesEntry 9 }

		-- 1.3.6.1.4.1.1916.2.131.50.1.4.2.25.21.9.1.10
		extremeWingStatsDevWlMcxMeshpointRootsEntriesNeighborBias OBJECT-TYPE
			SYNTAX Integer32
			MAX-ACCESS read-only
			STATUS current
			DESCRIPTION
				"Neighbor bias
				
				XPath: /extremeWing-stats/device[mac=key1]/wireless/meshpoint-roots[mpid=key2]/entries[entry_idx=key3]/neighbor_bias"
			::= { extremeWingStatsDevWlMcxMeshpointRootsEntriesEntry 10 }

		
		-- 1.3.6.1.4.1.1916.2.131.50.1.4.2.25.21.9.1.11
		extremeWingStatsDevWlMcxMeshpointRootsEntriesRootBias OBJECT-TYPE
			SYNTAX Integer32
			MAX-ACCESS read-only
			STATUS current
			DESCRIPTION
				"Root bias
				
				XPath: /extremeWing-stats/device[mac=key1]/wireless/meshpoint-roots[mpid=key2]/entries[entry_idx=key3]/root_bias"
			::= { extremeWingStatsDevWlMcxMeshpointRootsEntriesEntry 11 }

		
		-- 1.3.6.1.4.1.1916.2.131.50.1.4.2.25.21.10
		extremeWingStatsDevWlMcxMeshpointProxiesTable OBJECT-TYPE
			SYNTAX SEQUENCE OF ExtremeWingStatsDevWlMcxMeshpointProxiesEntry
			MAX-ACCESS not-accessible
			STATUS current
			DESCRIPTION
				"
				
				/extremeWing-stats/device/wireless/meshpoint-proxies"
			::= { extremeWingStatsDevWlMcx 10 }

		
		-- 1.3.6.1.4.1.1916.2.131.50.1.4.2.25.21.10.1
		extremeWingStatsDevWlMcxMeshpointProxiesEntry OBJECT-TYPE
			SYNTAX ExtremeWingStatsDevWlMcxMeshpointProxiesEntry
			MAX-ACCESS not-accessible
			STATUS current
			DESCRIPTION
				"An entry in the table."
			INDEX { extremeWingStatsDevMac, extremeWingStatsDevWlMcxMeshpointProxiesMpid }
			::= { extremeWingStatsDevWlMcxMeshpointProxiesTable 1 }

		
		ExtremeWingStatsDevWlMcxMeshpointProxiesEntry ::=
			SEQUENCE { 
				extremeWingStatsDevWlMcxMeshpointProxiesMpid
					ExtremeWingIdentifier,
				extremeWingStatsDevWlMcxMeshpointProxiesName
					ExtremeWingIdentifier,
				extremeWingStatsDevWlMcxMeshpointProxiesHostname
					DisplayString,
				extremeWingStatsDevWlMcxMeshpointProxiesDeviceMac
					DisplayString,
				extremeWingStatsDevWlMcxMeshpointProxiesNumEntries
					Unsigned32
			 }

		-- 1.3.6.1.4.1.1916.2.131.50.1.4.2.25.21.10.1.1
		extremeWingStatsDevWlMcxMeshpointProxiesMpid OBJECT-TYPE
			SYNTAX ExtremeWingIdentifier
			MAX-ACCESS read-only
			STATUS current
			DESCRIPTION
				"Mesh Point MAC address
				
				XPath: /extremeWing-stats/device[mac=key1]/wireless/meshpoint-proxies[mpid=key2]/mpid"
			::= { extremeWingStatsDevWlMcxMeshpointProxiesEntry 1 }

		
		-- 1.3.6.1.4.1.1916.2.131.50.1.4.2.25.21.10.1.3
		extremeWingStatsDevWlMcxMeshpointProxiesName OBJECT-TYPE
			SYNTAX ExtremeWingIdentifier
			MAX-ACCESS read-only
			STATUS current
			DESCRIPTION
				"
				
				XPath: /extremeWing-stats/device[mac=key1]/wireless/meshpoint-proxies[mpid=key2]/name"
			::= { extremeWingStatsDevWlMcxMeshpointProxiesEntry 3 }

		
		-- 1.3.6.1.4.1.1916.2.131.50.1.4.2.25.21.10.1.4
		extremeWingStatsDevWlMcxMeshpointProxiesHostname OBJECT-TYPE
			SYNTAX DisplayString (SIZE (64))
			MAX-ACCESS read-only
			STATUS current
			DESCRIPTION
				"hostname of the AP device
				
				XPath: /extremeWing-stats/device[mac=key1]/wireless/meshpoint-proxies[mpid=key2]/hostname"
			::= { extremeWingStatsDevWlMcxMeshpointProxiesEntry 4 }

		
		-- 1.3.6.1.4.1.1916.2.131.50.1.4.2.25.21.10.1.5
		extremeWingStatsDevWlMcxMeshpointProxiesDeviceMac OBJECT-TYPE
			SYNTAX DisplayString
			MAX-ACCESS read-only
			STATUS current
			DESCRIPTION
				"Device MAC address
				
				XPath: /extremeWing-stats/device[mac=key1]/wireless/meshpoint-proxies[mpid=key2]/device_mac"
			::= { extremeWingStatsDevWlMcxMeshpointProxiesEntry 5 }

		
		-- 1.3.6.1.4.1.1916.2.131.50.1.4.2.25.21.10.1.6
		extremeWingStatsDevWlMcxMeshpointProxiesNumEntries OBJECT-TYPE
			SYNTAX Unsigned32
			MAX-ACCESS read-only
			STATUS current
			DESCRIPTION
				"Number of entries on for this table
				
				XPath: /extremeWing-stats/device[mac=key1]/wireless/meshpoint-proxies[mpid=key2]/num_entries"
			::= { extremeWingStatsDevWlMcxMeshpointProxiesEntry 6 }

		
		-- 1.3.6.1.4.1.1916.2.131.50.1.4.2.25.21.11
		extremeWingStatsDevWlMcxMeshpointProxiesEntriesTable OBJECT-TYPE
			SYNTAX SEQUENCE OF ExtremeWingStatsDevWlMcxMeshpointProxiesEntriesEntry
			MAX-ACCESS not-accessible
			STATUS current
			DESCRIPTION
				"
				
				/extremeWing-stats/device/wireless/meshpoint-proxies/entries"
			::= { extremeWingStatsDevWlMcx 11 }

		
		-- 1.3.6.1.4.1.1916.2.131.50.1.4.2.25.21.11.1
		extremeWingStatsDevWlMcxMeshpointProxiesEntriesEntry OBJECT-TYPE
			SYNTAX ExtremeWingStatsDevWlMcxMeshpointProxiesEntriesEntry
			MAX-ACCESS not-accessible
			STATUS current
			DESCRIPTION
				"An entry in the table."
			INDEX { extremeWingStatsDevMac, extremeWingStatsDevWlMcxMeshpointProxiesMpid, extremeWingStatsDevWlMcxMeshpointProxiesEntriesIndex }
			::= { extremeWingStatsDevWlMcxMeshpointProxiesEntriesTable 1 }

		
		ExtremeWingStatsDevWlMcxMeshpointProxiesEntriesEntry ::=
			SEQUENCE { 
				extremeWingStatsDevWlMcxMeshpointProxiesEntriesIndex
					Unsigned32,
				extremeWingStatsDevWlMcxMeshpointProxiesEntriesProxyAddr
					DisplayString,
				extremeWingStatsDevWlMcxMeshpointProxiesEntriesProxyOwner
					DisplayString,
				extremeWingStatsDevWlMcxMeshpointProxiesEntriesPersistence
					DisplayString,
				extremeWingStatsDevWlMcxMeshpointProxiesEntriesAge
					Integer32,
				extremeWingStatsDevWlMcxMeshpointProxiesEntriesVlan
					Unsigned32
			 }

		-- 1.3.6.1.4.1.1916.2.131.50.1.4.2.25.21.11.1.1
		extremeWingStatsDevWlMcxMeshpointProxiesEntriesIndex OBJECT-TYPE
			SYNTAX Unsigned32 (1..4294967295)
			MAX-ACCESS read-only
			STATUS current
			DESCRIPTION
				"Entries Index
				
				XPath: /extremeWing-stats/device[mac=key1]/wireless/meshpoint-proxies[mpid=key2]/entries[entry_idx=key3]/entry_idx"
			::= { extremeWingStatsDevWlMcxMeshpointProxiesEntriesEntry 1 }

		
		-- 1.3.6.1.4.1.1916.2.131.50.1.4.2.25.21.11.1.2
		extremeWingStatsDevWlMcxMeshpointProxiesEntriesProxyAddr OBJECT-TYPE
			SYNTAX DisplayString
			MAX-ACCESS read-only
			STATUS current
			DESCRIPTION
				"Proxy MAC address
				
				XPath: /extremeWing-stats/device[mac=key1]/wireless/meshpoint-proxies[mpid=key2]/entries[entry_idx=key3]/proxy_addr"
			::= { extremeWingStatsDevWlMcxMeshpointProxiesEntriesEntry 2 }

		
		-- 1.3.6.1.4.1.1916.2.131.50.1.4.2.25.21.11.1.3
		extremeWingStatsDevWlMcxMeshpointProxiesEntriesProxyOwner OBJECT-TYPE
			SYNTAX DisplayString
			MAX-ACCESS read-only
			STATUS current
			DESCRIPTION
				"Proxy owner's MAC address
				
				XPath: /extremeWing-stats/device[mac=key1]/wireless/meshpoint-proxies[mpid=key2]/entries[entry_idx=key3]/proxy_owner"
			::= { extremeWingStatsDevWlMcxMeshpointProxiesEntriesEntry 3 }

		
		-- 1.3.6.1.4.1.1916.2.131.50.1.4.2.25.21.11.1.4
		extremeWingStatsDevWlMcxMeshpointProxiesEntriesPersistence OBJECT-TYPE
			SYNTAX DisplayString
			MAX-ACCESS read-only
			STATUS current
			DESCRIPTION
				"Persistence state
				
				Values:
				Timed,
				Untimed,
				Permanent,
				Invalid
				
				XPath: /extremeWing-stats/device[mac=key1]/wireless/meshpoint-proxies[mpid=key2]/entries[entry_idx=key3]/persistence"
			::= { extremeWingStatsDevWlMcxMeshpointProxiesEntriesEntry 4 }

		
		-- 1.3.6.1.4.1.1916.2.131.50.1.4.2.25.21.11.1.5
		extremeWingStatsDevWlMcxMeshpointProxiesEntriesAge OBJECT-TYPE
			SYNTAX Integer32
			MAX-ACCESS read-only
			STATUS current
			DESCRIPTION
				"Last time used
				
				XPath: /extremeWing-stats/device[mac=key1]/wireless/meshpoint-proxies[mpid=key2]/entries[entry_idx=key3]/age"
			::= { extremeWingStatsDevWlMcxMeshpointProxiesEntriesEntry 5 }

		
		-- 1.3.6.1.4.1.1916.2.131.50.1.4.2.25.21.11.1.6
		extremeWingStatsDevWlMcxMeshpointProxiesEntriesVlan OBJECT-TYPE
			SYNTAX Unsigned32
			MAX-ACCESS read-only
			STATUS current
			DESCRIPTION
				"The VLAN assigned to the proxy
				
				XPath: /extremeWing-stats/device[mac=key1]/wireless/meshpoint-proxies[mpid=key2]/entries[entry_idx=key3]/vlan"
			::= { extremeWingStatsDevWlMcxMeshpointProxiesEntriesEntry 6 }
		
		-- 1.3.6.1.4.1.1916.2.131.50.1.4.2.25.21.12
		extremeWingStatsDevWlMcxMeshpointLsaTable OBJECT-TYPE
			SYNTAX SEQUENCE OF ExtremeWingStatsDevWlMcxMeshpointLsaEntry
			MAX-ACCESS not-accessible
			STATUS current
			DESCRIPTION
				"
				
				/extremeWing-stats/device/wireless/meshpoint-lsa"
			::= { extremeWingStatsDevWlMcx 12 }

		
		-- 1.3.6.1.4.1.1916.2.131.50.1.4.2.25.21.12.1
		extremeWingStatsDevWlMcxMeshpointLsaEntry OBJECT-TYPE
			SYNTAX ExtremeWingStatsDevWlMcxMeshpointLsaEntry
			MAX-ACCESS not-accessible
			STATUS current
			DESCRIPTION
				"An entry in the table."
			INDEX { extremeWingStatsDevMac, extremeWingStatsDevWlMcxMeshpointLsaMpid }
			::= { extremeWingStatsDevWlMcxMeshpointLsaTable 1 }

		
		ExtremeWingStatsDevWlMcxMeshpointLsaEntry ::=
			SEQUENCE { 
				extremeWingStatsDevWlMcxMeshpointLsaMpid
					ExtremeWingIdentifier,
				extremeWingStatsDevWlMcxMeshpointLsaName
					ExtremeWingIdentifier,
				extremeWingStatsDevWlMcxMeshpointLsaHostname
					DisplayString,
				extremeWingStatsDevWlMcxMeshpointLsaDeviceMac
					DisplayString,
				extremeWingStatsDevWlMcxMeshpointLsaNumEntries
					Unsigned32,
				extremeWingStatsDevWlMcxMeshpointLsaMeshid
					DisplayString,
				extremeWingStatsDevWlMcxMeshpointLsaR0Valid
					TruthValue,
				extremeWingStatsDevWlMcxMeshpointLsaR0mdid
					OCTET STRING,
				extremeWingStatsDevWlMcxMeshpointLsaR0khid
					OCTET STRING
			 }

		-- 1.3.6.1.4.1.1916.2.131.50.1.4.2.25.21.12.1.1
		extremeWingStatsDevWlMcxMeshpointLsaMpid OBJECT-TYPE
			SYNTAX ExtremeWingIdentifier
			MAX-ACCESS read-only
			STATUS current
			DESCRIPTION
				"Mesh Point MAC address
				
				XPath: /extremeWing-stats/device[mac=key1]/wireless/meshpoint-lsa[mpid=key2]/mpid"
			::= { extremeWingStatsDevWlMcxMeshpointLsaEntry 1 }

		
		-- 1.3.6.1.4.1.1916.2.131.50.1.4.2.25.21.12.1.3
		extremeWingStatsDevWlMcxMeshpointLsaName OBJECT-TYPE
			SYNTAX ExtremeWingIdentifier
			MAX-ACCESS read-only
			STATUS current
			DESCRIPTION
				"
				
				XPath: /extremeWing-stats/device[mac=key1]/wireless/meshpoint-lsa[mpid=key2]/name"
			::= { extremeWingStatsDevWlMcxMeshpointLsaEntry 3 }

		
		-- 1.3.6.1.4.1.1916.2.131.50.1.4.2.25.21.12.1.4
		extremeWingStatsDevWlMcxMeshpointLsaHostname OBJECT-TYPE
			SYNTAX DisplayString (SIZE (64))
			MAX-ACCESS read-only
			STATUS current
			DESCRIPTION
				"hostname of the AP device
				
				XPath: /extremeWing-stats/device[mac=key1]/wireless/meshpoint-lsa[mpid=key2]/hostname"
			::= { extremeWingStatsDevWlMcxMeshpointLsaEntry 4 }

		
		-- 1.3.6.1.4.1.1916.2.131.50.1.4.2.25.21.12.1.5
		extremeWingStatsDevWlMcxMeshpointLsaDeviceMac OBJECT-TYPE
			SYNTAX DisplayString
			MAX-ACCESS read-only
			STATUS current
			DESCRIPTION
				"Device MAC address
				
				XPath: /extremeWing-stats/device[mac=key1]/wireless/meshpoint-lsa[mpid=key2]/device_mac"
			::= { extremeWingStatsDevWlMcxMeshpointLsaEntry 5 }

		
		-- 1.3.6.1.4.1.1916.2.131.50.1.4.2.25.21.12.1.6
		extremeWingStatsDevWlMcxMeshpointLsaNumEntries OBJECT-TYPE
			SYNTAX Unsigned32
			MAX-ACCESS read-only
			STATUS current
			DESCRIPTION
				"Number of entries on for this table
				
				XPath: /extremeWing-stats/device[mac=key1]/wireless/meshpoint-lsa[mpid=key2]/num_entries"
			::= { extremeWingStatsDevWlMcxMeshpointLsaEntry 6 }

		
		-- 1.3.6.1.4.1.1916.2.131.50.1.4.2.25.21.12.1.7
		extremeWingStatsDevWlMcxMeshpointLsaMeshid OBJECT-TYPE
			SYNTAX DisplayString (SIZE (32))
			MAX-ACCESS read-only
			STATUS current
			DESCRIPTION
				"Mesh Point Identifier for this MP.
				
				XPath: /extremeWing-stats/device[mac=key1]/wireless/meshpoint-lsa[mpid=key2]/meshid"
			::= { extremeWingStatsDevWlMcxMeshpointLsaEntry 7 }

		
		-- 1.3.6.1.4.1.1916.2.131.50.1.4.2.25.21.12.1.8
		extremeWingStatsDevWlMcxMeshpointLsaR0Valid OBJECT-TYPE
			SYNTAX TruthValue
			MAX-ACCESS read-only
			STATUS current
			DESCRIPTION
				"R0 information is valid
				
				XPath: /extremeWing-stats/device[mac=key1]/wireless/meshpoint-lsa[mpid=key2]/r0_valid"
			::= { extremeWingStatsDevWlMcxMeshpointLsaEntry 8 }

		
		-- 1.3.6.1.4.1.1916.2.131.50.1.4.2.25.21.12.1.9
		extremeWingStatsDevWlMcxMeshpointLsaR0mdid OBJECT-TYPE
			SYNTAX OCTET STRING (SIZE (12))
			MAX-ACCESS read-only
			STATUS current
			DESCRIPTION
				"Mesh Point R0 Mesh Domain ID
				
				XPath: /extremeWing-stats/device[mac=key1]/wireless/meshpoint-lsa[mpid=key2]/r0mdid"
			::= { extremeWingStatsDevWlMcxMeshpointLsaEntry 9 }

		
		-- 1.3.6.1.4.1.1916.2.131.50.1.4.2.25.21.12.1.10
		extremeWingStatsDevWlMcxMeshpointLsaR0khid OBJECT-TYPE
			SYNTAX OCTET STRING (SIZE (32))
			MAX-ACCESS read-only
			STATUS current
			DESCRIPTION
				"Mesh Point R0 Key Holder ID
				
				XPath: /extremeWing-stats/device[mac=key1]/wireless/meshpoint-lsa[mpid=key2]/r0khid"
			::= { extremeWingStatsDevWlMcxMeshpointLsaEntry 10 }

		
		-- 1.3.6.1.4.1.1916.2.131.50.1.4.2.25.21.13
		extremeWingStatsDevWlMcxMeshpointLsaEntriesTable OBJECT-TYPE
			SYNTAX SEQUENCE OF ExtremeWingStatsDevWlMcxMeshpointLsaEntriesEntry
			MAX-ACCESS not-accessible
			STATUS current
			DESCRIPTION
				"
				
				/extremeWing-stats/device/wireless/meshpoint-lsa/entries"
			::= { extremeWingStatsDevWlMcx 13 }

		
		-- 1.3.6.1.4.1.1916.2.131.50.1.4.2.25.21.13.1
		extremeWingStatsDevWlMcxMeshpointLsaEntriesEntry OBJECT-TYPE
			SYNTAX ExtremeWingStatsDevWlMcxMeshpointLsaEntriesEntry
			MAX-ACCESS not-accessible
			STATUS current
			DESCRIPTION
				"An entry in the table."
			INDEX { extremeWingStatsDevMac, extremeWingStatsDevWlMcxMeshpointLsaMpid, extremeWingStatsDevWlMcxMeshpointLsaEntriesIndex }
			::= { extremeWingStatsDevWlMcxMeshpointLsaEntriesTable 1 }

		
		ExtremeWingStatsDevWlMcxMeshpointLsaEntriesEntry ::=
			SEQUENCE { 
				extremeWingStatsDevWlMcxMeshpointLsaEntriesIndex
					Unsigned32,
				extremeWingStatsDevWlMcxMeshpointLsaEntriesLinkAddr
					DisplayString,
				extremeWingStatsDevWlMcxMeshpointLsaEntriesInterfaceId
					ExtremeWingIdentifier,
				extremeWingStatsDevWlMcxMeshpointLsaEntriesKeepAlive
					TruthValue,
				extremeWingStatsDevWlMcxMeshpointLsaEntriesLinkState
					DisplayString,
				extremeWingStatsDevWlMcxMeshpointLsaEntriesLinkTimeout
					Integer32
			 }

		-- 1.3.6.1.4.1.1916.2.131.50.1.4.2.25.21.13.1.1
		extremeWingStatsDevWlMcxMeshpointLsaEntriesIndex OBJECT-TYPE
			SYNTAX Unsigned32 (1..4294967295)
			MAX-ACCESS read-only
			STATUS current
			DESCRIPTION
				"Entries Index
				XPath: /extremeWing-stats/device[mac=key1]/wireless/meshpoint-lsa[mpid=key2]/entries[entry_idx=key3]/entry_idx"
			::= { extremeWingStatsDevWlMcxMeshpointLsaEntriesEntry 1 }

		
		-- 1.3.6.1.4.1.1916.2.131.50.1.4.2.25.21.13.1.2
		extremeWingStatsDevWlMcxMeshpointLsaEntriesLinkAddr OBJECT-TYPE
			SYNTAX DisplayString
			MAX-ACCESS read-only
			STATUS current
			DESCRIPTION
				"Link MAC address
				
				XPath: /extremeWing-stats/device[mac=key1]/wireless/meshpoint-lsa[mpid=key2]/entries[entry_idx=key3]/link_addr"
			::= { extremeWingStatsDevWlMcxMeshpointLsaEntriesEntry 2 }

		
		-- 1.3.6.1.4.1.1916.2.131.50.1.4.2.25.21.13.1.3
		extremeWingStatsDevWlMcxMeshpointLsaEntriesInterfaceId OBJECT-TYPE
			SYNTAX ExtremeWingIdentifier
			MAX-ACCESS read-only
			STATUS current
			DESCRIPTION
				"Unique ID for each interfacce in the form of AP-MAC:%c%d. E.g., 00-A0-F8-00-00-00:R1
				
				XPath: /extremeWing-stats/device[mac=key1]/wireless/meshpoint-lsa[mpid=key2]/entries[entry_idx=key3]/interface_id"
			::= { extremeWingStatsDevWlMcxMeshpointLsaEntriesEntry 3 }

		
		-- 1.3.6.1.4.1.1916.2.131.50.1.4.2.25.21.13.1.4
		extremeWingStatsDevWlMcxMeshpointLsaEntriesKeepAlive OBJECT-TYPE
			SYNTAX TruthValue
			MAX-ACCESS read-only
			STATUS current
			DESCRIPTION
				"Keep link alive
				
				XPath: /extremeWing-stats/device[mac=key1]/wireless/meshpoint-lsa[mpid=key2]/entries[entry_idx=key3]/keep_alive"
			::= { extremeWingStatsDevWlMcxMeshpointLsaEntriesEntry 4 }

		
		-- 1.3.6.1.4.1.1916.2.131.50.1.4.2.25.21.13.1.5
		extremeWingStatsDevWlMcxMeshpointLsaEntriesLinkState OBJECT-TYPE
			SYNTAX DisplayString
			MAX-ACCESS read-only
			STATUS current
			DESCRIPTION
				"Link state
				
				Values:
				Init,
				Enabled,
				Failed,
				In
				Progress,
				Invalid
				
				XPath: /extremeWing-stats/device[mac=key1]/wireless/meshpoint-lsa[mpid=key2]/entries[entry_idx=key3]/link_state"
			::= { extremeWingStatsDevWlMcxMeshpointLsaEntriesEntry 5 }

		
		-- 1.3.6.1.4.1.1916.2.131.50.1.4.2.25.21.13.1.6
		extremeWingStatsDevWlMcxMeshpointLsaEntriesLinkTimeout OBJECT-TYPE
			SYNTAX Integer32
			MAX-ACCESS read-only
			STATUS current
			DESCRIPTION
				"Link timeout
				
				XPath: /extremeWing-stats/device[mac=key1]/wireless/meshpoint-lsa[mpid=key2]/entries[entry_idx=key3]/link_timeout"
			::= { extremeWingStatsDevWlMcxMeshpointLsaEntriesEntry 6 }
		
		-- 1.3.6.1.4.1.1916.2.131.50.1.4.2.25.21.14
		extremeWingStatsDevWlMcxMeshpointMcastPathsTable OBJECT-TYPE
			SYNTAX SEQUENCE OF ExtremeWingStatsDevWlMcxMeshpointMcastPathsEntry
			MAX-ACCESS not-accessible
			STATUS current
			DESCRIPTION
				"
				
				/extremeWing-stats/device/wireless/meshpoint-mcast-paths"
			::= { extremeWingStatsDevWlMcx 14 }

		
		-- 1.3.6.1.4.1.1916.2.131.50.1.4.2.25.21.14.1
		extremeWingStatsDevWlMcxMeshpointMcastPathsEntry OBJECT-TYPE
			SYNTAX ExtremeWingStatsDevWlMcxMeshpointMcastPathsEntry
			MAX-ACCESS not-accessible
			STATUS current
			DESCRIPTION
				"An entry in the table."
			INDEX { extremeWingStatsDevMac, extremeWingStatsDevWlMcxMeshpointMcastPathsMpid }
			::= { extremeWingStatsDevWlMcxMeshpointMcastPathsTable 1 }

		
		ExtremeWingStatsDevWlMcxMeshpointMcastPathsEntry ::=
			SEQUENCE { 
				extremeWingStatsDevWlMcxMeshpointMcastPathsMpid
					ExtremeWingIdentifier,
				extremeWingStatsDevWlMcxMeshpointMcastPathsName
					ExtremeWingIdentifier,
				extremeWingStatsDevWlMcxMeshpointMcastPathsHostname
					DisplayString,
				extremeWingStatsDevWlMcxMeshpointMcastPathsDeviceMac
					DisplayString,
				extremeWingStatsDevWlMcxMeshpointMcastPathsNumEntries
					Unsigned32
			 }

		-- 1.3.6.1.4.1.1916.2.131.50.1.4.2.25.21.14.1.1
		extremeWingStatsDevWlMcxMeshpointMcastPathsMpid OBJECT-TYPE
			SYNTAX ExtremeWingIdentifier
			MAX-ACCESS read-only
			STATUS current
			DESCRIPTION
				"Mesh Point MAC address
				
				XPath: /extremeWing-stats/device[mac=key1]/wireless/meshpoint-mcast-paths[mpid=key2]/mpid"
			::= { extremeWingStatsDevWlMcxMeshpointMcastPathsEntry 1 }

		
		-- 1.3.6.1.4.1.1916.2.131.50.1.4.2.25.21.14.1.3
		extremeWingStatsDevWlMcxMeshpointMcastPathsName OBJECT-TYPE
			SYNTAX ExtremeWingIdentifier
			MAX-ACCESS read-only
			STATUS current
			DESCRIPTION
				"
				
				XPath: /extremeWing-stats/device[mac=key1]/wireless/meshpoint-mcast-paths[mpid=key2]/name"
			::= { extremeWingStatsDevWlMcxMeshpointMcastPathsEntry 3 }

		
		-- 1.3.6.1.4.1.1916.2.131.50.1.4.2.25.21.14.1.4
		extremeWingStatsDevWlMcxMeshpointMcastPathsHostname OBJECT-TYPE
			SYNTAX DisplayString (SIZE (64))
			MAX-ACCESS read-only
			STATUS current
			DESCRIPTION
				"hostname of the AP device
				
				XPath: /extremeWing-stats/device[mac=key1]/wireless/meshpoint-mcast-paths[mpid=key2]/hostname"
			::= { extremeWingStatsDevWlMcxMeshpointMcastPathsEntry 4 }

		
		-- 1.3.6.1.4.1.1916.2.131.50.1.4.2.25.21.14.1.5
		extremeWingStatsDevWlMcxMeshpointMcastPathsDeviceMac OBJECT-TYPE
			SYNTAX DisplayString
			MAX-ACCESS read-only
			STATUS current
			DESCRIPTION
				"Device MAC address
				
				XPath: /extremeWing-stats/device[mac=key1]/wireless/meshpoint-mcast-paths[mpid=key2]/device_mac"
			::= { extremeWingStatsDevWlMcxMeshpointMcastPathsEntry 5 }

		
		-- 1.3.6.1.4.1.1916.2.131.50.1.4.2.25.21.14.1.6
		extremeWingStatsDevWlMcxMeshpointMcastPathsNumEntries OBJECT-TYPE
			SYNTAX Unsigned32
			MAX-ACCESS read-only
			STATUS current
			DESCRIPTION
				"Number of entries on for this table
				
				XPath: /extremeWing-stats/device[mac=key1]/wireless/meshpoint-mcast-paths[mpid=key2]/num_entries"
			::= { extremeWingStatsDevWlMcxMeshpointMcastPathsEntry 6 }

		
		-- 1.3.6.1.4.1.1916.2.131.50.1.4.2.25.21.15
		extremeWingStatsDevWlMcxMeshpointMcastPathsEntriesTable OBJECT-TYPE
			SYNTAX SEQUENCE OF ExtremeWingStatsDevWlMcxMeshpointMcastPathsEntriesEntry
			MAX-ACCESS not-accessible
			STATUS current
			DESCRIPTION
				"
				
				/extremeWing-stats/device/wireless/meshpoint-mcast-paths/entries"
			::= { extremeWingStatsDevWlMcx 15 }

		
		-- 1.3.6.1.4.1.1916.2.131.50.1.4.2.25.21.15.1
		extremeWingStatsDevWlMcxMeshpointMcastPathsEntriesEntry OBJECT-TYPE
			SYNTAX ExtremeWingStatsDevWlMcxMeshpointMcastPathsEntriesEntry
			MAX-ACCESS not-accessible
			STATUS current
			DESCRIPTION
				"An entry in the table."
			INDEX { extremeWingStatsDevMac, extremeWingStatsDevWlMcxMeshpointMcastPathsMpid, extremeWingStatsDevWlMcxMeshpointMcastPathsEntriesIndex }
			::= { extremeWingStatsDevWlMcxMeshpointMcastPathsEntriesTable 1 }

		
		ExtremeWingStatsDevWlMcxMeshpointMcastPathsEntriesEntry ::=
			SEQUENCE { 
				extremeWingStatsDevWlMcxMeshpointMcastPathsEntriesIndex
					Unsigned32,
				extremeWingStatsDevWlMcxMeshpointMcastPathsEntriesGroupAddr
					DisplayString,
				extremeWingStatsDevWlMcxMeshpointMcastPathsEntriesMemberAddr
					DisplayString,
				extremeWingStatsDevWlMcxMeshpointMcastPathsEntriesPathTimeout
					Integer32
			 }

		-- 1.3.6.1.4.1.1916.2.131.50.1.4.2.25.21.15.1.1
		extremeWingStatsDevWlMcxMeshpointMcastPathsEntriesIndex OBJECT-TYPE
			SYNTAX Unsigned32 (1..4294967295)
			MAX-ACCESS read-only
			STATUS current
			DESCRIPTION
				"Entries Index
				
				XPath: /extremeWing-stats/device[mac=key1]/wireless/meshpoint-mcast-paths[mpid=key2]/entries[entry_idx=key3]/entry_idx"
			::= { extremeWingStatsDevWlMcxMeshpointMcastPathsEntriesEntry 1 }

		
		-- 1.3.6.1.4.1.1916.2.131.50.1.4.2.25.21.15.1.2
		extremeWingStatsDevWlMcxMeshpointMcastPathsEntriesGroupAddr OBJECT-TYPE
			SYNTAX DisplayString
			MAX-ACCESS read-only
			STATUS current
			DESCRIPTION
				"Group MAC address
				
				XPath: /extremeWing-stats/device[mac=key1]/wireless/meshpoint-mcast-paths[mpid=key2]/entries[entry_idx=key3]/group_addr"
			::= { extremeWingStatsDevWlMcxMeshpointMcastPathsEntriesEntry 2 }

		
		-- 1.3.6.1.4.1.1916.2.131.50.1.4.2.25.21.15.1.3
		extremeWingStatsDevWlMcxMeshpointMcastPathsEntriesMemberAddr OBJECT-TYPE
			SYNTAX DisplayString
			MAX-ACCESS read-only
			STATUS current
			DESCRIPTION
				"Member mesh point MAC address
				
				XPath: /extremeWing-stats/device[mac=key1]/wireless/meshpoint-mcast-paths[mpid=key2]/entries[entry_idx=key3]/member_addr"
			::= { extremeWingStatsDevWlMcxMeshpointMcastPathsEntriesEntry 3 }

		
		-- 1.3.6.1.4.1.1916.2.131.50.1.4.2.25.21.15.1.4
		extremeWingStatsDevWlMcxMeshpointMcastPathsEntriesPathTimeout OBJECT-TYPE
			SYNTAX Integer32
			MAX-ACCESS read-only
			STATUS current
			DESCRIPTION
				"Path timeout
				
				XPath: /extremeWing-stats/device[mac=key1]/wireless/meshpoint-mcast-paths[mpid=key2]/entries[entry_idx=key3]/path_timeout"
			::= { extremeWingStatsDevWlMcxMeshpointMcastPathsEntriesEntry 4 }

                -- 1.3.6.1.4.1.1916.2.131.50.1.4.2.25.22
                extremeWingStatsDevWlGlobalRadioInfo OBJECT IDENTIFIER ::= { extremeWingStatsDevWl 22 }


                -- 1.3.6.1.4.1.1916.2.131.50.1.4.2.25.22.1
                extremeWingStatsDevWlGlobalRadioInfoNoOfAdopRadios OBJECT-TYPE
                        SYNTAX Counter32
                        MAX-ACCESS read-only
                        STATUS current
                        DESCRIPTION
                                "
                                XPath: /extremeWing-stats/device/self/global-radio-info/number_of_adopted_radios"
                        ::= { extremeWingStatsDevWlGlobalRadioInfo 1 }


                -- 1.3.6.1.4.1.1916.2.131.50.1.4.2.25.22.2
                extremeWingStatsDevWlGlobalRadioInfoNoOfOnlineRadios OBJECT-TYPE
                        SYNTAX Counter32
                        MAX-ACCESS read-only
                        STATUS current
                        DESCRIPTION
                                "
                                XPath: /extremeWing-stats/device/self/global-radio-info/number_of_online_radios"
                        ::= { extremeWingStatsDevWlGlobalRadioInfo 2 }
		
-- /extremeWing-stats/device/vrrp
		-- 1.3.6.1.4.1.1916.2.131.50.1.4.2.31
		extremeWingStatsDevVrrp OBJECT IDENTIFIER ::= { extremeWingStatsDev 31 }

		
		-- 1.3.6.1.4.1.1916.2.131.50.1.4.2.31.1
		extremeWingStatsDevVrrpGlobalErrTable OBJECT-TYPE
			SYNTAX SEQUENCE OF ExtremeWingStatsDevVrrpGlobalErrEntry
			MAX-ACCESS not-accessible
			STATUS current
			DESCRIPTION
				"
				
				/extremeWing-stats/device/vrrp/vrrp_router_global_err_stats"
			::= { extremeWingStatsDevVrrp 1 }

		
		-- 1.3.6.1.4.1.1916.2.131.50.1.4.2.31.1.1
		extremeWingStatsDevVrrpGlobalErrEntry OBJECT-TYPE
			SYNTAX ExtremeWingStatsDevVrrpGlobalErrEntry
			MAX-ACCESS not-accessible
			STATUS current
			DESCRIPTION
				"An entry in the table."
			INDEX { extremeWingStatsDevMac }
			::= { extremeWingStatsDevVrrpGlobalErrTable 1 }

		
		ExtremeWingStatsDevVrrpGlobalErrEntry ::=
			SEQUENCE { 
				extremeWingStatsDevVrrpGlobalErrIpTtlErrs
					Unsigned32,
				extremeWingStatsDevVrrpGlobalErrVersionMismatch
					Unsigned32,
				extremeWingStatsDevVrrpGlobalErrPacketLenErr
					Unsigned32,
				extremeWingStatsDevVrrpGlobalErrChecksumErr
					Unsigned32,
				extremeWingStatsDevVrrpGlobalErrInvalidVirtualRouterId
					Unsigned32,
				extremeWingStatsDevVrrpGlobalErrAuthMismatch
					Unsigned32,
				extremeWingStatsDevVrrpGlobalErrInvalidTypePackets
					Unsigned32,
				extremeWingStatsDevVrrpGlobalErrLastProtocolErrReason
					DisplayString
			 }

		-- 1.3.6.1.4.1.1916.2.131.50.1.4.2.31.1.1.1
		extremeWingStatsDevVrrpGlobalErrIpTtlErrs OBJECT-TYPE
			SYNTAX Unsigned32
			MAX-ACCESS read-only
			STATUS current
			DESCRIPTION
				"The total number of VRRP packets received by the virtual router with IPv4 TTL not equal to 255.
				
				XPath: /extremeWing-stats/device[mac=key1]/vrrp/vrrp_router_global_err_stats/ip_ttl_errors"
			::= { extremeWingStatsDevVrrpGlobalErrEntry 1 }

		
		-- 1.3.6.1.4.1.1916.2.131.50.1.4.2.31.1.1.2
		extremeWingStatsDevVrrpGlobalErrVersionMismatch OBJECT-TYPE
			SYNTAX Unsigned32
			MAX-ACCESS read-only
			STATUS current
			DESCRIPTION
				"The total number of VRRP packets received with an unknown or unsupported version number
				
				XPath: /extremeWing-stats/device[mac=key1]/vrrp/vrrp_router_global_err_stats/version_mismatch"
			::= { extremeWingStatsDevVrrpGlobalErrEntry 2 }

		
		-- 1.3.6.1.4.1.1916.2.131.50.1.4.2.31.1.1.3
		extremeWingStatsDevVrrpGlobalErrPacketLenErr OBJECT-TYPE
			SYNTAX Unsigned32
			MAX-ACCESS read-only
			STATUS current
			DESCRIPTION
				"The total number of packets received with a packet length less than the length of the VRRP header
				
				XPath: /extremeWing-stats/device[mac=key1]/vrrp/vrrp_router_global_err_stats/packet_len_error"
			::= { extremeWingStatsDevVrrpGlobalErrEntry 3 }

		
		-- 1.3.6.1.4.1.1916.2.131.50.1.4.2.31.1.1.4
		extremeWingStatsDevVrrpGlobalErrChecksumErr OBJECT-TYPE
			SYNTAX Unsigned32
			MAX-ACCESS read-only
			STATUS current
			DESCRIPTION
				"The total number of VRRP packets received with an invalid VRRP checksum value
				
				XPath: /extremeWing-stats/device[mac=key1]/vrrp/vrrp_router_global_err_stats/checksum_err"
			::= { extremeWingStatsDevVrrpGlobalErrEntry 4 }

		
		-- 1.3.6.1.4.1.1916.2.131.50.1.4.2.31.1.1.5
		extremeWingStatsDevVrrpGlobalErrInvalidVirtualRouterId OBJECT-TYPE
			SYNTAX Unsigned32
			MAX-ACCESS read-only
			STATUS current
			DESCRIPTION
				"The total number of VRRP packets received with an invalid VRID for this virtual router
				
				XPath: /extremeWing-stats/device[mac=key1]/vrrp/vrrp_router_global_err_stats/invalid_virtual_router_id"
			::= { extremeWingStatsDevVrrpGlobalErrEntry 5 }

		
		-- 1.3.6.1.4.1.1916.2.131.50.1.4.2.31.1.1.6
		extremeWingStatsDevVrrpGlobalErrAuthMismatch OBJECT-TYPE
			SYNTAX Unsigned32
			MAX-ACCESS read-only
			STATUS current
			DESCRIPTION
				"VRRP authentication mismatch
				
				XPath: /extremeWing-stats/device[mac=key1]/vrrp/vrrp_router_global_err_stats/authentication_mismatch"
			::= { extremeWingStatsDevVrrpGlobalErrEntry 6 }

		
		-- 1.3.6.1.4.1.1916.2.131.50.1.4.2.31.1.1.7
		extremeWingStatsDevVrrpGlobalErrInvalidTypePackets OBJECT-TYPE
			SYNTAX Unsigned32
			MAX-ACCESS read-only
			STATUS current
			DESCRIPTION
				"The total number of VRRP packets send by the virtual router with an invalid value in the 'type' field
				
				XPath: /extremeWing-stats/device[mac=key1]/vrrp/vrrp_router_global_err_stats/invalid_type_packets"
			::= { extremeWingStatsDevVrrpGlobalErrEntry 7 }

		
		-- 1.3.6.1.4.1.1916.2.131.50.1.4.2.31.1.1.8
		extremeWingStatsDevVrrpGlobalErrLastProtocolErrReason OBJECT-TYPE
			SYNTAX DisplayString
			MAX-ACCESS read-only
			STATUS current
			DESCRIPTION
				"This indicates the reason for the last protocol error.  This SHOULD be set to none when no protocol
				
				Values:
				none,
				ip-ttl,
				version,
				packet_len,
				checksum,
				vrid,
				auth,
				invalid_type
				
				XPath: /extremeWing-stats/device[mac=key1]/vrrp/vrrp_router_global_err_stats/last_protocol_error_reason"
			::= { extremeWingStatsDevVrrpGlobalErrEntry 8 }

		
		-- 1.3.6.1.4.1.1916.2.131.50.1.4.2.31.2
		extremeWingStatsDevVrrpOperationTable OBJECT-TYPE
			SYNTAX SEQUENCE OF ExtremeWingStatsDevVrrpOperationEntry
			MAX-ACCESS not-accessible
			STATUS current
			DESCRIPTION
				"
				
				/extremeWing-stats/device/vrrp/vrrp_operations_summary"
			::= { extremeWingStatsDevVrrp 2 }

		
		-- 1.3.6.1.4.1.1916.2.131.50.1.4.2.31.2.1
		extremeWingStatsDevVrrpOperationEntry OBJECT-TYPE
			SYNTAX ExtremeWingStatsDevVrrpOperationEntry
			MAX-ACCESS not-accessible
			STATUS current
			DESCRIPTION
				"An entry in the table."
			INDEX { extremeWingStatsDevMac, extremeWingStatsDevVrrpOperationVirtualRouterId }
			::= { extremeWingStatsDevVrrpOperationTable 1 }

		
		ExtremeWingStatsDevVrrpOperationEntry ::=
			SEQUENCE { 
				extremeWingStatsDevVrrpOperationVirtualRouterId
					Unsigned32,
				extremeWingStatsDevVrrpOperationIfName
					DisplayString,
				extremeWingStatsDevVrrpOperationVersion
					DisplayString,
				extremeWingStatsDevVrrpOperationState
					DisplayString,
				extremeWingStatsDevVrrpOperationPriority
					Unsigned32,
				extremeWingStatsDevVrrpOperationVirtualAddr
					DisplayString,
				extremeWingStatsDevVrrpOperationMasterAddr
					DisplayString,
				extremeWingStatsDevVrrpOperationExpiryTimer
					DisplayString,
				extremeWingStatsDevVrrpOperationMasterDeadTimer
					DisplayString
			 }

		-- 1.3.6.1.4.1.1916.2.131.50.1.4.2.31.2.1.1
		extremeWingStatsDevVrrpOperationVirtualRouterId OBJECT-TYPE
			SYNTAX Unsigned32 (1..255)
			MAX-ACCESS read-only
			STATUS current
			DESCRIPTION
				"Virtual router Identifier
				
				XPath: /extremeWing-stats/device[mac=key1]/vrrp/vrrp_operations_summary[virtual_router_id=key2]/virtual_router_id"
			::= { extremeWingStatsDevVrrpOperationEntry 1 }

		
		-- 1.3.6.1.4.1.1916.2.131.50.1.4.2.31.2.1.3
		extremeWingStatsDevVrrpOperationIfName OBJECT-TYPE
			SYNTAX DisplayString
			MAX-ACCESS read-only
			STATUS current
			DESCRIPTION
				"Name of the interface on which VRRP is running
				
				XPath: /extremeWing-stats/device[mac=key1]/vrrp/vrrp_operations_summary[virtual_router_id=key2]/interface_name"
			::= { extremeWingStatsDevVrrpOperationEntry 3 }

		
		-- 1.3.6.1.4.1.1916.2.131.50.1.4.2.31.2.1.4
		extremeWingStatsDevVrrpOperationVersion OBJECT-TYPE
			SYNTAX DisplayString
			MAX-ACCESS read-only
			STATUS current
			DESCRIPTION
				"VRRP version of this group
				
				Values:
				2,
				3
				
				XPath: /extremeWing-stats/device[mac=key1]/vrrp/vrrp_operations_summary[virtual_router_id=key2]/version"
			::= { extremeWingStatsDevVrrpOperationEntry 4 }

		
		-- 1.3.6.1.4.1.1916.2.131.50.1.4.2.31.2.1.5
		extremeWingStatsDevVrrpOperationState OBJECT-TYPE
			SYNTAX DisplayString
			MAX-ACCESS read-only
			STATUS current
			DESCRIPTION
				"The current state of the virtual router. This object
				
				Values:
				init,
				backup,
				master
				
				XPath: /extremeWing-stats/device[mac=key1]/vrrp/vrrp_operations_summary[virtual_router_id=key2]/state"
			::= { extremeWingStatsDevVrrpOperationEntry 5 }

		
		-- 1.3.6.1.4.1.1916.2.131.50.1.4.2.31.2.1.6
		extremeWingStatsDevVrrpOperationPriority OBJECT-TYPE
			SYNTAX Unsigned32 (0..255)
			MAX-ACCESS read-only
			STATUS current
			DESCRIPTION
				" Runtime VRRP priority for this group. In case of link monitoring this can differ from the configured priority.
				
				XPath: /extremeWing-stats/device[mac=key1]/vrrp/vrrp_operations_summary[virtual_router_id=key2]/operation_priority"
			::= { extremeWingStatsDevVrrpOperationEntry 6 }

		
		-- 1.3.6.1.4.1.1916.2.131.50.1.4.2.31.2.1.7
		extremeWingStatsDevVrrpOperationVirtualAddr OBJECT-TYPE
			SYNTAX DisplayString
			MAX-ACCESS read-only
			STATUS current
			DESCRIPTION
				"Virtual IP address, if more than one specified then the first configured one is selected
				
				XPath: /extremeWing-stats/device[mac=key1]/vrrp/vrrp_operations_summary[virtual_router_id=key2]/virtual_address"
			::= { extremeWingStatsDevVrrpOperationEntry 7 }

		
		-- 1.3.6.1.4.1.1916.2.131.50.1.4.2.31.2.1.8
		extremeWingStatsDevVrrpOperationMasterAddr OBJECT-TYPE
			SYNTAX DisplayString
			MAX-ACCESS read-only
			STATUS current
			DESCRIPTION
				"current master IP address
				
				XPath: /extremeWing-stats/device[mac=key1]/vrrp/vrrp_operations_summary[virtual_router_id=key2]/master_address"
			::= { extremeWingStatsDevVrrpOperationEntry 8 }

		
		-- 1.3.6.1.4.1.1916.2.131.50.1.4.2.31.2.1.9
		extremeWingStatsDevVrrpOperationExpiryTimer OBJECT-TYPE
			SYNTAX DisplayString
			MAX-ACCESS read-only
			STATUS current
			DESCRIPTION
				"How long until the advertisement timer expires
				
				XPath: /extremeWing-stats/device[mac=key1]/vrrp/vrrp_operations_summary[virtual_router_id=key2]/expiry_timer"
			::= { extremeWingStatsDevVrrpOperationEntry 9 }

		
		-- 1.3.6.1.4.1.1916.2.131.50.1.4.2.31.2.1.10
		extremeWingStatsDevVrrpOperationMasterDeadTimer OBJECT-TYPE
			SYNTAX DisplayString
			MAX-ACCESS read-only
			STATUS current
			DESCRIPTION
				"How long until the master is detected as dead timer expires
				
				XPath: /extremeWing-stats/device[mac=key1]/vrrp/vrrp_operations_summary[virtual_router_id=key2]/master_dead_timer"
			::= { extremeWingStatsDevVrrpOperationEntry 10 }

		
		-- 1.3.6.1.4.1.1916.2.131.50.1.4.2.31.3
		extremeWingStatsDevVrrpDetailTable OBJECT-TYPE
			SYNTAX SEQUENCE OF ExtremeWingStatsDevVrrpDetailEntry
			MAX-ACCESS not-accessible
			STATUS current
			DESCRIPTION
				"
				
				/extremeWing-stats/device/vrrp/vrrp_operations_detail"
			::= { extremeWingStatsDevVrrp 3 }

		
		-- 1.3.6.1.4.1.1916.2.131.50.1.4.2.31.3.1
		extremeWingStatsDevVrrpDetailEntry OBJECT-TYPE
			SYNTAX ExtremeWingStatsDevVrrpDetailEntry
			MAX-ACCESS not-accessible
			STATUS current
			DESCRIPTION
				"An entry in the table."
			INDEX { extremeWingStatsDevMac, extremeWingStatsDevVrrpDetailVirtualRouterId }
			::= { extremeWingStatsDevVrrpDetailTable 1 }

		
		ExtremeWingStatsDevVrrpDetailEntry ::=
			SEQUENCE { 
				extremeWingStatsDevVrrpDetailVirtualRouterId
					Unsigned32,
				extremeWingStatsDevVrrpDetailIfName
					DisplayString,
				extremeWingStatsDevVrrpDetailVersion
					DisplayString,
				extremeWingStatsDevVrrpDetailConfiguredPriority
					Unsigned32,
				extremeWingStatsDevVrrpDetailAdvertisementInterval
					DisplayString,
				extremeWingStatsDevVrrpDetailLocalIpAddress
					DisplayString,
				extremeWingStatsDevVrrpDetailIfStatusAdmin
					DisplayString,
				extremeWingStatsDevVrrpDetailVirtualAddressCount
					Unsigned32,
				extremeWingStatsDevVrrpDetailPreempt
					TruthValue,
				extremeWingStatsDevVrrpDetailPreemptDelay
					Unsigned32,
				extremeWingStatsDevVrrpDetailCrmDownAction
					DisplayString,
				extremeWingStatsDevVrrpDetailCrmStatus
					DisplayString,
				extremeWingStatsDevVrrpDetailCfgedDeltaPriority
					Unsigned32,
				extremeWingStatsDevVrrpDetailVirtualMacAddr
					MacAddress,
				extremeWingStatsDevVrrpDetailSyncGroup
					TruthValue,
				extremeWingStatsDevVrrpDetailFailoverSyncGroup
					DisplayString
			 }

		-- 1.3.6.1.4.1.1916.2.131.50.1.4.2.31.3.1.1
		extremeWingStatsDevVrrpDetailVirtualRouterId OBJECT-TYPE
			SYNTAX Unsigned32 (1..255)
			MAX-ACCESS read-only
			STATUS current
			DESCRIPTION
				"Virtual router Identifier
				
				XPath: /extremeWing-stats/device[mac=key1]/vrrp/vrrp_operations_detail[virtual_router_id=key2]/virtual_router_id"
			::= { extremeWingStatsDevVrrpDetailEntry 1 }

		
		-- 1.3.6.1.4.1.1916.2.131.50.1.4.2.31.3.1.3
		extremeWingStatsDevVrrpDetailIfName OBJECT-TYPE
			SYNTAX DisplayString
			MAX-ACCESS read-only
			STATUS current
			DESCRIPTION
				"Name of the interface on which VRRP is running
				
				XPath: /extremeWing-stats/device[mac=key1]/vrrp/vrrp_operations_detail[virtual_router_id=key2]/interface_name"
			::= { extremeWingStatsDevVrrpDetailEntry 3 }

		
		-- 1.3.6.1.4.1.1916.2.131.50.1.4.2.31.3.1.4
		extremeWingStatsDevVrrpDetailVersion OBJECT-TYPE
			SYNTAX DisplayString
			MAX-ACCESS read-only
			STATUS current
			DESCRIPTION
				"VRRP version of this group
				
				Values:
				2,
				3
				
				XPath: /extremeWing-stats/device[mac=key1]/vrrp/vrrp_operations_detail[virtual_router_id=key2]/version"
			::= { extremeWingStatsDevVrrpDetailEntry 4 }

		
		-- 1.3.6.1.4.1.1916.2.131.50.1.4.2.31.3.1.5
		extremeWingStatsDevVrrpDetailConfiguredPriority OBJECT-TYPE
			SYNTAX Unsigned32 (1..254)
			MAX-ACCESS read-only
			STATUS current
			DESCRIPTION
				"the priority to be used for the virtual router master election process.  Higher values imply higher priority.
				
				XPath: /extremeWing-stats/device[mac=key1]/vrrp/vrrp_operations_detail[virtual_router_id=key2]/configured_priority"
			::= { extremeWingStatsDevVrrpDetailEntry 5 }

		
		-- 1.3.6.1.4.1.1916.2.131.50.1.4.2.31.3.1.6
		extremeWingStatsDevVrrpDetailAdvertisementInterval OBJECT-TYPE
			SYNTAX DisplayString
			MAX-ACCESS read-only
			STATUS current
			DESCRIPTION
				"Time interval between sending advertisement messages. Only the master router sends VRRP advertisements
				
				XPath: /extremeWing-stats/device[mac=key1]/vrrp/vrrp_operations_detail[virtual_router_id=key2]/advertisement_interval"
			::= { extremeWingStatsDevVrrpDetailEntry 6 }

		
		-- 1.3.6.1.4.1.1916.2.131.50.1.4.2.31.3.1.7
		extremeWingStatsDevVrrpDetailLocalIpAddress OBJECT-TYPE
			SYNTAX DisplayString
			MAX-ACCESS read-only
			STATUS current
			DESCRIPTION
				"In the case where there are more than one IP Address (associated IP addresses) for a given interface, this will the IP address with highest prefix
				
				XPath: /extremeWing-stats/device[mac=key1]/vrrp/vrrp_operations_detail[virtual_router_id=key2]/local_ip_address"
			::= { extremeWingStatsDevVrrpDetailEntry 7 }

		
		-- 1.3.6.1.4.1.1916.2.131.50.1.4.2.31.3.1.8
		extremeWingStatsDevVrrpDetailIfStatusAdmin OBJECT-TYPE
			SYNTAX DisplayString
			MAX-ACCESS read-only
			STATUS current
			DESCRIPTION
				"Administrative status of interface (up/down)
				
				Values:
				up,
				down,
				up_and_running
				
				XPath: /extremeWing-stats/device[mac=key1]/vrrp/vrrp_operations_detail[virtual_router_id=key2]/interface_status_admin"
			::= { extremeWingStatsDevVrrpDetailEntry 8 }

		
		-- 1.3.6.1.4.1.1916.2.131.50.1.4.2.31.3.1.9
		extremeWingStatsDevVrrpDetailVirtualAddressCount OBJECT-TYPE
			SYNTAX Unsigned32
			MAX-ACCESS read-only
			STATUS current
			DESCRIPTION
				"Number of virtual address(es) configured
				
				XPath: /extremeWing-stats/device[mac=key1]/vrrp/vrrp_operations_detail[virtual_router_id=key2]/virtual_address_count"
			::= { extremeWingStatsDevVrrpDetailEntry 9 }

		
		-- 1.3.6.1.4.1.1916.2.131.50.1.4.2.31.3.1.10
		extremeWingStatsDevVrrpDetailPreempt OBJECT-TYPE
			SYNTAX TruthValue
			MAX-ACCESS read-only
			STATUS current
			DESCRIPTION
				"Controls whether a higher priority backup router will preempt a lower priority master.
				
				XPath: /extremeWing-stats/device[mac=key1]/vrrp/vrrp_operations_detail[virtual_router_id=key2]/preempt"
			::= { extremeWingStatsDevVrrpDetailEntry 10 }

		
		-- 1.3.6.1.4.1.1916.2.131.50.1.4.2.31.3.1.11
		extremeWingStatsDevVrrpDetailPreemptDelay OBJECT-TYPE
			SYNTAX Unsigned32 (0..65535)
			UNITS "seconds"
			MAX-ACCESS read-only
			STATUS current
			DESCRIPTION
				"Delay after which preemption will get triggered
				
				XPath: /extremeWing-stats/device[mac=key1]/vrrp/vrrp_operations_detail[virtual_router_id=key2]/preempt_delay"
			::= { extremeWingStatsDevVrrpDetailEntry 11 }

		
		-- 1.3.6.1.4.1.1916.2.131.50.1.4.2.31.3.1.12
		extremeWingStatsDevVrrpDetailCrmDownAction OBJECT-TYPE
			SYNTAX DisplayString
			MAX-ACCESS read-only
			STATUS current
			DESCRIPTION
				"
				
				Values:
				increment-priority,
				decrement-priority,
				none
				
				XPath: /extremeWing-stats/device[mac=key1]/vrrp/vrrp_operations_detail[virtual_router_id=key2]/crm_down_action"
			::= { extremeWingStatsDevVrrpDetailEntry 12 }

		
		-- 1.3.6.1.4.1.1916.2.131.50.1.4.2.31.3.1.13
		extremeWingStatsDevVrrpDetailCrmStatus OBJECT-TYPE
			SYNTAX DisplayString
			MAX-ACCESS read-only
			STATUS current
			DESCRIPTION
				"
				
				Values:
				up,
				down
				
				XPath: /extremeWing-stats/device[mac=key1]/vrrp/vrrp_operations_detail[virtual_router_id=key2]/crm_status"
			::= { extremeWingStatsDevVrrpDetailEntry 13 }

		
		-- 1.3.6.1.4.1.1916.2.131.50.1.4.2.31.3.1.14
		extremeWingStatsDevVrrpDetailCfgedDeltaPriority OBJECT-TYPE
			SYNTAX Unsigned32
			MAX-ACCESS read-only
			STATUS current
			DESCRIPTION
				"The configured priority will be increment/decremented by this value. Also see description for type field above.
				
				XPath: /extremeWing-stats/device[mac=key1]/vrrp/vrrp_operations_detail[virtual_router_id=key2]/configured_delta_priority"
			::= { extremeWingStatsDevVrrpDetailEntry 14 }

		
		-- 1.3.6.1.4.1.1916.2.131.50.1.4.2.31.3.1.15
		extremeWingStatsDevVrrpDetailVirtualMacAddr OBJECT-TYPE
			SYNTAX MacAddress
			MAX-ACCESS read-only
			STATUS current
			DESCRIPTION
				"virtual mac addresses that is derived from the virtual router id
				
				XPath: /extremeWing-stats/device[mac=key1]/vrrp/vrrp_operations_detail[virtual_router_id=key2]/virtual_mac_address"
			::= { extremeWingStatsDevVrrpDetailEntry 15 }

		
		-- 1.3.6.1.4.1.1916.2.131.50.1.4.2.31.3.1.16
		extremeWingStatsDevVrrpDetailSyncGroup OBJECT-TYPE
			SYNTAX TruthValue
			MAX-ACCESS read-only
			STATUS current
			DESCRIPTION
				"Specifies whether this group is part of vrrp sync group. If it is, then vrrp failover happens when all masters that are part of this group is detected as dead
				
				XPath: /extremeWing-stats/device[mac=key1]/vrrp/vrrp_operations_detail[virtual_router_id=key2]/sync_group"
			::= { extremeWingStatsDevVrrpDetailEntry 16 }

		
		-- 1.3.6.1.4.1.1916.2.131.50.1.4.2.31.3.1.17
		extremeWingStatsDevVrrpDetailFailoverSyncGroup OBJECT-TYPE
			SYNTAX DisplayString
			MAX-ACCESS read-only
			STATUS current
			DESCRIPTION
				"Specifies the operational state of this group
				
				XPath: /extremeWing-stats/device[mac=key1]/vrrp/vrrp_operations_detail[virtual_router_id=key2]/failover_sync_group"
			::= { extremeWingStatsDevVrrpDetailEntry 17 }

		
		-- 1.3.6.1.4.1.1916.2.131.50.1.4.2.31.4
		extremeWingStatsDevVrrpDetailMonitorTable OBJECT-TYPE
			SYNTAX SEQUENCE OF ExtremeWingStatsDevVrrpDetailMonitorEntry
			MAX-ACCESS not-accessible
			STATUS current
			DESCRIPTION
				"
				
				/extremeWing-stats/device/vrrp/vrrp_operations_detail/monitor"
			::= { extremeWingStatsDevVrrp 4 }

		
		-- 1.3.6.1.4.1.1916.2.131.50.1.4.2.31.4.1
		extremeWingStatsDevVrrpDetailMonitorEntry OBJECT-TYPE
			SYNTAX ExtremeWingStatsDevVrrpDetailMonitorEntry
			MAX-ACCESS not-accessible
			STATUS current
			DESCRIPTION
				"An entry in the table."
			INDEX { extremeWingStatsDevMac, extremeWingStatsDevVrrpDetailVirtualRouterId, extremeWingStatsDevVrrpDetailMonitorIf }
			::= { extremeWingStatsDevVrrpDetailMonitorTable 1 }

		
		ExtremeWingStatsDevVrrpDetailMonitorEntry ::=
			SEQUENCE { 
				extremeWingStatsDevVrrpDetailMonitorIf
					ExtremeWingIdentifier,
				extremeWingStatsDevVrrpDetailMonitorIfStatusAdmin
					DisplayString
			 }

		-- 1.3.6.1.4.1.1916.2.131.50.1.4.2.31.4.1.1
		extremeWingStatsDevVrrpDetailMonitorIf OBJECT-TYPE
			SYNTAX ExtremeWingIdentifier
			MAX-ACCESS read-only
			STATUS current
			DESCRIPTION
				"Name of the local interface being monitored
				
				XPath: /extremeWing-stats/device[mac=key1]/vrrp/vrrp_operations_detail[virtual_router_id=key2]/monitor[monitor_interface=key3]/monitor_interface"
			::= { extremeWingStatsDevVrrpDetailMonitorEntry 1 }

		
		-- 1.3.6.1.4.1.1916.2.131.50.1.4.2.31.4.1.3
		extremeWingStatsDevVrrpDetailMonitorIfStatusAdmin OBJECT-TYPE
			SYNTAX DisplayString
			MAX-ACCESS read-only
			STATUS current
			DESCRIPTION
				"Administrative status of locally monitored interface
				
				Values:
				up,
				down,
				up_and_running
				
				XPath: /extremeWing-stats/device[mac=key1]/vrrp/vrrp_operations_detail[virtual_router_id=key2]/monitor[monitor_interface=key3]/interface_status_admin"
			::= { extremeWingStatsDevVrrpDetailMonitorEntry 3 }

		
		-- 1.3.6.1.4.1.1916.2.131.50.1.4.2.31.5
		extremeWingStatsDevVrrpRouterStatsTable OBJECT-TYPE
			SYNTAX SEQUENCE OF ExtremeWingStatsDevVrrpRouterStatsEntry
			MAX-ACCESS not-accessible
			STATUS current
			DESCRIPTION
				"
				
				/extremeWing-stats/device/vrrp/vrrp_router_statistics"
			::= { extremeWingStatsDevVrrp 5 }

		
		-- 1.3.6.1.4.1.1916.2.131.50.1.4.2.31.5.1
		extremeWingStatsDevVrrpRouterStatsEntry OBJECT-TYPE
			SYNTAX ExtremeWingStatsDevVrrpRouterStatsEntry
			MAX-ACCESS not-accessible
			STATUS current
			DESCRIPTION
				"An entry in the table."
			INDEX { extremeWingStatsDevMac, extremeWingStatsDevVrrpRouterStatsVirtualRouterId }
			::= { extremeWingStatsDevVrrpRouterStatsTable 1 }

		
		ExtremeWingStatsDevVrrpRouterStatsEntry ::=
			SEQUENCE { 
				extremeWingStatsDevVrrpRouterStatsVirtualRouterId
					Unsigned32,
				extremeWingStatsDevVrrpRouterStatsMasterTransitions
					Unsigned32,
				extremeWingStatsDevVrrpRouterStatsNewMasterReason
					DisplayString,
				extremeWingStatsDevVrrpRouterStatsNumReceivedAdvertisement
					Unsigned32,
				extremeWingStatsDevVrrpRouterStatsAdvertisementIntervalErrs
					Unsigned32,
				extremeWingStatsDevVrrpRouterStatsNumSendAdvertisement
					Unsigned32,
				extremeWingStatsDevVrrpRouterStatsReceivedAdvtInitState
					Unsigned32,
				extremeWingStatsDevVrrpRouterStatsReceivedPriorityZeroPackets
					Unsigned32,
				extremeWingStatsDevVrrpRouterStatsSendPriorityZeroPackets
					Unsigned32,
				extremeWingStatsDevVrrpRouterStatsAddressListErrors
					Unsigned32
			 }

		-- 1.3.6.1.4.1.1916.2.131.50.1.4.2.31.5.1.1
		extremeWingStatsDevVrrpRouterStatsVirtualRouterId OBJECT-TYPE
			SYNTAX Unsigned32 (1..255)
			MAX-ACCESS read-only
			STATUS current
			DESCRIPTION
				"Virtual router Identifier
				
				XPath: /extremeWing-stats/device[mac=key1]/vrrp/vrrp_router_statistics[virtual_router_id=key2]/virtual_router_id"
			::= { extremeWingStatsDevVrrpRouterStatsEntry 1 }

		
		-- 1.3.6.1.4.1.1916.2.131.50.1.4.2.31.5.1.3
		extremeWingStatsDevVrrpRouterStatsMasterTransitions OBJECT-TYPE
			SYNTAX Unsigned32
			MAX-ACCESS read-only
			STATUS current
			DESCRIPTION
				"The total number of times that this virtual router's state has transitioned to MASTER
				
				XPath: /extremeWing-stats/device[mac=key1]/vrrp/vrrp_router_statistics[virtual_router_id=key2]/master_transitions"
			::= { extremeWingStatsDevVrrpRouterStatsEntry 3 }

		
		-- 1.3.6.1.4.1.1916.2.131.50.1.4.2.31.5.1.4
		extremeWingStatsDevVrrpRouterStatsNewMasterReason OBJECT-TYPE
			SYNTAX DisplayString
			MAX-ACCESS read-only
			STATUS current
			DESCRIPTION
				"Reason for becoming a master. This object
				
				Values:
				not-master,
				priority,
				preempted,
				master-no-response,
				critical-resource-monitoring
				
				XPath: /extremeWing-stats/device[mac=key1]/vrrp/vrrp_router_statistics[virtual_router_id=key2]/new_master_reason"
			::= { extremeWingStatsDevVrrpRouterStatsEntry 4 }

		
		-- 1.3.6.1.4.1.1916.2.131.50.1.4.2.31.5.1.5
		extremeWingStatsDevVrrpRouterStatsNumReceivedAdvertisement OBJECT-TYPE
			SYNTAX Unsigned32
			MAX-ACCESS read-only
			STATUS current
			DESCRIPTION
				"Number of advertisement packets received
				
				XPath: /extremeWing-stats/device[mac=key1]/vrrp/vrrp_router_statistics[virtual_router_id=key2]/num_received_advertisement"
			::= { extremeWingStatsDevVrrpRouterStatsEntry 5 }

		
		-- 1.3.6.1.4.1.1916.2.131.50.1.4.2.31.5.1.6
		extremeWingStatsDevVrrpRouterStatsAdvertisementIntervalErrs OBJECT-TYPE
			SYNTAX Unsigned32
			MAX-ACCESS read-only
			STATUS current
			DESCRIPTION
				"The total number of VRRP advertisement packets received for which the advertisement interval is different than the one configured for the local virtual
				
				XPath: /extremeWing-stats/device[mac=key1]/vrrp/vrrp_router_statistics[virtual_router_id=key2]/advertisement_interval_errors"
			::= { extremeWingStatsDevVrrpRouterStatsEntry 6 }

		
		-- 1.3.6.1.4.1.1916.2.131.50.1.4.2.31.5.1.7
		extremeWingStatsDevVrrpRouterStatsNumSendAdvertisement OBJECT-TYPE
			SYNTAX Unsigned32
			MAX-ACCESS read-only
			STATUS current
			DESCRIPTION
				"Number of advertisement packets send
				
				XPath: /extremeWing-stats/device[mac=key1]/vrrp/vrrp_router_statistics[virtual_router_id=key2]/num_send_advertisement"
			::= { extremeWingStatsDevVrrpRouterStatsEntry 7 }

		
		-- 1.3.6.1.4.1.1916.2.131.50.1.4.2.31.5.1.8
		extremeWingStatsDevVrrpRouterStatsReceivedAdvtInitState OBJECT-TYPE
			SYNTAX Unsigned32
			MAX-ACCESS read-only
			STATUS current
			DESCRIPTION
				"The total number of VRRP packets received when the virtual router is in init state
				
				XPath: /extremeWing-stats/device[mac=key1]/vrrp/vrrp_router_statistics[virtual_router_id=key2]/received_advt_init_state"
			::= { extremeWingStatsDevVrrpRouterStatsEntry 8 }

		
		-- 1.3.6.1.4.1.1916.2.131.50.1.4.2.31.5.1.9
		extremeWingStatsDevVrrpRouterStatsReceivedPriorityZeroPackets OBJECT-TYPE
			SYNTAX Unsigned32
			MAX-ACCESS read-only
			STATUS current
			DESCRIPTION
				"The total number of VRRP packets received by the virtual router with priority of '0'
				
				XPath: /extremeWing-stats/device[mac=key1]/vrrp/vrrp_router_statistics[virtual_router_id=key2]/received_priority_zero_packets"
			::= { extremeWingStatsDevVrrpRouterStatsEntry 9 }

		
		-- 1.3.6.1.4.1.1916.2.131.50.1.4.2.31.5.1.10
		extremeWingStatsDevVrrpRouterStatsSendPriorityZeroPackets OBJECT-TYPE
			SYNTAX Unsigned32
			MAX-ACCESS read-only
			STATUS current
			DESCRIPTION
				"The total number of VRRP packets send by the virtual router with priority of '0'
				
				XPath: /extremeWing-stats/device[mac=key1]/vrrp/vrrp_router_statistics[virtual_router_id=key2]/send_priority_zero_packets"
			::= { extremeWingStatsDevVrrpRouterStatsEntry 10 }

		
		-- 1.3.6.1.4.1.1916.2.131.50.1.4.2.31.5.1.11
		extremeWingStatsDevVrrpRouterStatsAddressListErrors OBJECT-TYPE
			SYNTAX Unsigned32
			MAX-ACCESS read-only
			STATUS current
			DESCRIPTION
				"The total number of packets received for which the address list does not match the locally configured list for the virtual router
				
				XPath: /extremeWing-stats/device[mac=key1]/vrrp/vrrp_router_statistics[virtual_router_id=key2]/address_list_errors"
			::= { extremeWingStatsDevVrrpRouterStatsEntry 11 }

		
-- /extremeWing-stats/device/crm
		-- 1.3.6.1.4.1.1916.2.131.50.1.4.2.32
		extremeWingStatsDevCrm OBJECT IDENTIFIER ::= { extremeWingStatsDev 32 }

		
		-- 1.3.6.1.4.1.1916.2.131.50.1.4.2.32.1
		extremeWingStatsDevCrmTable OBJECT-TYPE
			SYNTAX SEQUENCE OF ExtremeWingStatsDevCrmEntry
			MAX-ACCESS not-accessible
			STATUS current
			DESCRIPTION
				"
				
				/extremeWing-stats/device/crm"
			::= { extremeWingStatsDevCrm 1 }

		
		-- 1.3.6.1.4.1.1916.2.131.50.1.4.2.32.1.1
		extremeWingStatsDevCrmEntry OBJECT-TYPE
			SYNTAX ExtremeWingStatsDevCrmEntry
			MAX-ACCESS not-accessible
			STATUS current
			DESCRIPTION
				"An entry in the table."
			INDEX { extremeWingStatsDevMac }
			::= { extremeWingStatsDevCrmTable 1 }

		
		ExtremeWingStatsDevCrmEntry ::=
			SEQUENCE { 
				extremeWingStatsDevCrmMonitorInterval
					Unsigned32
			 }

		-- 1.3.6.1.4.1.1916.2.131.50.1.4.2.32.1.1.1
		extremeWingStatsDevCrmMonitorInterval OBJECT-TYPE
			SYNTAX Unsigned32
			UNITS "seconds"
			MAX-ACCESS read-only
			STATUS current
			DESCRIPTION
				"
				
				XPath: /extremeWing-stats/device[mac=key1]/crm/monitor_interval"
			::= { extremeWingStatsDevCrmEntry 1 }

		
		-- 1.3.6.1.4.1.1916.2.131.50.1.4.2.32.2
		extremeWingStatsDevCrmCriticalResTable OBJECT-TYPE
			SYNTAX SEQUENCE OF ExtremeWingStatsDevCrmCriticalResEntry
			MAX-ACCESS not-accessible
			STATUS current
			DESCRIPTION
				"
				
				/extremeWing-stats/device/crm/critical_resources"
			::= { extremeWingStatsDevCrm 2 }

		
		-- 1.3.6.1.4.1.1916.2.131.50.1.4.2.32.2.1
		extremeWingStatsDevCrmCriticalResEntry OBJECT-TYPE
			SYNTAX ExtremeWingStatsDevCrmCriticalResEntry
			MAX-ACCESS not-accessible
			STATUS current
			DESCRIPTION
				"An entry in the table."
			INDEX { extremeWingStatsDevMac, extremeWingStatsDevCrmCriticalResVia }
			::= { extremeWingStatsDevCrmCriticalResTable 1 }

		
		ExtremeWingStatsDevCrmCriticalResEntry ::=
			SEQUENCE { 
				extremeWingStatsDevCrmCriticalResVia
					ExtremeWingIdentifier,
				extremeWingStatsDevCrmCriticalResStatus
					DisplayString,
				extremeWingStatsDevCrmCriticalResErrorReason
					DisplayString,
				extremeWingStatsDevCrmCriticalResMode
					DisplayString
			 }

		-- 1.3.6.1.4.1.1916.2.131.50.1.4.2.32.2.1.1
		extremeWingStatsDevCrmCriticalResVia OBJECT-TYPE
			SYNTAX ExtremeWingIdentifier
			MAX-ACCESS read-only
			STATUS current
			DESCRIPTION
				"
				
				XPath: /extremeWing-stats/device[mac=key1]/crm/critical_resources[via=key2]/via"
			::= { extremeWingStatsDevCrmCriticalResEntry 1 }

		
		-- 1.3.6.1.4.1.1916.2.131.50.1.4.2.32.2.1.3
		extremeWingStatsDevCrmCriticalResStatus OBJECT-TYPE
			SYNTAX DisplayString
			MAX-ACCESS read-only
			STATUS current
			DESCRIPTION
				"
				
				Values:
				up,
				down,
				checking
				
				XPath: /extremeWing-stats/device[mac=key1]/crm/critical_resources[via=key2]/status"
			::= { extremeWingStatsDevCrmCriticalResEntry 3 }

		
		-- 1.3.6.1.4.1.1916.2.131.50.1.4.2.32.2.1.4
		extremeWingStatsDevCrmCriticalResErrorReason OBJECT-TYPE
			SYNTAX DisplayString
			MAX-ACCESS read-only
			STATUS current
			DESCRIPTION
				"
				
				XPath: /extremeWing-stats/device[mac=key1]/crm/critical_resources[via=key2]/error_reason"
			::= { extremeWingStatsDevCrmCriticalResEntry 4 }

		
		-- 1.3.6.1.4.1.1916.2.131.50.1.4.2.32.2.1.5
		extremeWingStatsDevCrmCriticalResMode OBJECT-TYPE
			SYNTAX DisplayString
			MAX-ACCESS read-only
			STATUS current
			DESCRIPTION
				"
				
				XPath: /extremeWing-stats/device[mac=key1]/crm/critical_resources[via=key2]/mode"
			::= { extremeWingStatsDevCrmCriticalResEntry 5 }

		
		-- 1.3.6.1.4.1.1916.2.131.50.1.4.2.32.3
		extremeWingStatsDevCrmCriticalResResTable OBJECT-TYPE
			SYNTAX SEQUENCE OF ExtremeWingStatsDevCrmCriticalResResEntry
			MAX-ACCESS not-accessible
			STATUS current
			DESCRIPTION
				"
				
				/extremeWing-stats/device/crm/critical_resources/resources"
			::= { extremeWingStatsDevCrm 3 }

		
		-- 1.3.6.1.4.1.1916.2.131.50.1.4.2.32.3.1
		extremeWingStatsDevCrmCriticalResResEntry OBJECT-TYPE
			SYNTAX ExtremeWingStatsDevCrmCriticalResResEntry
			MAX-ACCESS not-accessible
			STATUS current
			DESCRIPTION
				"An entry in the table."
			INDEX { extremeWingStatsDevMac, extremeWingStatsDevCrmCriticalResVia, extremeWingStatsDevCrmCriticalResResAddr }
			::= { extremeWingStatsDevCrmCriticalResResTable 1 }

		
		ExtremeWingStatsDevCrmCriticalResResEntry ::=
			SEQUENCE { 
				extremeWingStatsDevCrmCriticalResResAddr
					ExtremeWingIdentifier,
				extremeWingStatsDevCrmCriticalResResMonitorMode
					DisplayString,
				extremeWingStatsDevCrmCriticalResResArpVlan
					Unsigned32,
				extremeWingStatsDevCrmCriticalResResStatus
					DisplayString,
				extremeWingStatsDevCrmCriticalResResArpPort
					DisplayString
			 }

		-- 1.3.6.1.4.1.1916.2.131.50.1.4.2.32.3.1.1
		extremeWingStatsDevCrmCriticalResResAddr OBJECT-TYPE
			SYNTAX ExtremeWingIdentifier
			MAX-ACCESS read-only
			STATUS current
			DESCRIPTION
				"
				
				XPath: /extremeWing-stats/device[mac=key1]/crm/critical_resources[via=key2]/resources[addr=key3]/addr"
			::= { extremeWingStatsDevCrmCriticalResResEntry 1 }

		
		-- 1.3.6.1.4.1.1916.2.131.50.1.4.2.32.3.1.3
		extremeWingStatsDevCrmCriticalResResMonitorMode OBJECT-TYPE
			SYNTAX DisplayString
			MAX-ACCESS read-only
			STATUS current
			DESCRIPTION
				"
				
				Values:
				arp-only,
				arp-and-ping
				
				XPath: /extremeWing-stats/device[mac=key1]/crm/critical_resources[via=key2]/resources[addr=key3]/monitor_mode"
			::= { extremeWingStatsDevCrmCriticalResResEntry 3 }

		
		-- 1.3.6.1.4.1.1916.2.131.50.1.4.2.32.3.1.4
		extremeWingStatsDevCrmCriticalResResArpVlan OBJECT-TYPE
			SYNTAX Unsigned32
			MAX-ACCESS read-only
			STATUS current
			DESCRIPTION
				"
				
				XPath: /extremeWing-stats/device[mac=key1]/crm/critical_resources[via=key2]/resources[addr=key3]/arp_vlan"
			::= { extremeWingStatsDevCrmCriticalResResEntry 4 }

		
		-- 1.3.6.1.4.1.1916.2.131.50.1.4.2.32.3.1.5
		extremeWingStatsDevCrmCriticalResResStatus OBJECT-TYPE
			SYNTAX DisplayString
			MAX-ACCESS read-only
			STATUS current
			DESCRIPTION
				"
				
				Values:
				up,
				down,
				unresolved
				
				XPath: /extremeWing-stats/device[mac=key1]/crm/critical_resources[via=key2]/resources[addr=key3]/status"
			::= { extremeWingStatsDevCrmCriticalResResEntry 5 }

		
		-- 1.3.6.1.4.1.1916.2.131.50.1.4.2.32.3.1.6
		extremeWingStatsDevCrmCriticalResResArpPort OBJECT-TYPE
			SYNTAX DisplayString
			MAX-ACCESS read-only
			STATUS current
			DESCRIPTION
				"
				
				XPath: /extremeWing-stats/device[mac=key1]/crm/critical_resources[via=key2]/resources[addr=key3]/arp_port"
			::= { extremeWingStatsDevCrmCriticalResResEntry 6 }

		
-- /extremeWing-stats/device/pbr_stats
		-- 1.3.6.1.4.1.1916.2.131.50.1.4.2.33
		extremeWingStatsDevPbr OBJECT IDENTIFIER ::= { extremeWingStatsDev 33 }

		
		-- 1.3.6.1.4.1.1916.2.131.50.1.4.2.33.1
		extremeWingStatsDevPbrTable OBJECT-TYPE
			SYNTAX SEQUENCE OF ExtremeWingStatsDevPbrEntry
			MAX-ACCESS not-accessible
			STATUS current
			DESCRIPTION
				"
				
				/extremeWing-stats/device/pbr_stats"
			::= { extremeWingStatsDevPbr 1 }

		
		-- 1.3.6.1.4.1.1916.2.131.50.1.4.2.33.1.1
		extremeWingStatsDevPbrEntry OBJECT-TYPE
			SYNTAX ExtremeWingStatsDevPbrEntry
			MAX-ACCESS not-accessible
			STATUS current
			DESCRIPTION
				"An entry in the table."
			INDEX { extremeWingStatsDevMac, extremeWingStatsDevPbrRouteMapPrecedence }
			::= { extremeWingStatsDevPbrTable 1 }

		
		ExtremeWingStatsDevPbrEntry ::=
			SEQUENCE { 
				extremeWingStatsDevPbrRouteMapPrecedence
					Unsigned32,
				extremeWingStatsDevPbrPrimaryNextHopIfName
					DisplayString,
				extremeWingStatsDevPbrPrimaryNextHopIpAddr
					DisplayString,
				extremeWingStatsDevPbrPrimaryNextHopState
					DisplayString,
				extremeWingStatsDevPbrPrimaryNextHopMonitorMode
					DisplayString,
				extremeWingStatsDevPbrSecondaryNextHopIfName
					DisplayString,
				extremeWingStatsDevPbrSecondaryNextHopIpAddr
					DisplayString,
				extremeWingStatsDevPbrSecondaryNextHopState
					DisplayString,
				extremeWingStatsDevPbrSecondaryNextHopMonitorMode
					DisplayString,
				extremeWingStatsDevPbrDefaultNextHopIfName
					DisplayString,
				extremeWingStatsDevPbrDefaultNextHopIpAddr
					DisplayString,
				extremeWingStatsDevPbrDefaultNextHopState
					DisplayString,
				extremeWingStatsDevPbrDefaultNextHopMonitorMode
					DisplayString,
				extremeWingStatsDevPbrWlan
					DisplayString,
				extremeWingStatsDevPbrWirelessClientRole
					DisplayString,
				extremeWingStatsDevPbrInInterface
					DisplayString,
				extremeWingStatsDevPbrIpDscp
					DisplayString
			 }

		-- 1.3.6.1.4.1.1916.2.131.50.1.4.2.33.1.1.1
		extremeWingStatsDevPbrRouteMapPrecedence OBJECT-TYPE
			SYNTAX Unsigned32 (1..100)
			MAX-ACCESS read-only
			STATUS current
			DESCRIPTION
				"
				
				XPath: /extremeWing-stats/device[mac=key1]/pbr_stats[route_map_precedence=key2]/route_map_precedence"
			::= { extremeWingStatsDevPbrEntry 1 }

		
		-- 1.3.6.1.4.1.1916.2.131.50.1.4.2.33.1.1.3
		extremeWingStatsDevPbrPrimaryNextHopIfName OBJECT-TYPE
			SYNTAX DisplayString
			MAX-ACCESS read-only
			STATUS current
			DESCRIPTION
				"
				
				XPath: /extremeWing-stats/device[mac=key1]/pbr_stats[route_map_precedence=key2]/primary_next_hop/interface_name"
			::= { extremeWingStatsDevPbrEntry 3 }

		
		-- 1.3.6.1.4.1.1916.2.131.50.1.4.2.33.1.1.4
		extremeWingStatsDevPbrPrimaryNextHopIpAddr OBJECT-TYPE
			SYNTAX DisplayString
			MAX-ACCESS read-only
			STATUS current
			DESCRIPTION
				"
				
				XPath: /extremeWing-stats/device[mac=key1]/pbr_stats[route_map_precedence=key2]/primary_next_hop/ip_address"
			::= { extremeWingStatsDevPbrEntry 4 }

		
		-- 1.3.6.1.4.1.1916.2.131.50.1.4.2.33.1.1.5
		extremeWingStatsDevPbrPrimaryNextHopState OBJECT-TYPE
			SYNTAX DisplayString
			MAX-ACCESS read-only
			STATUS current
			DESCRIPTION
				"UP: next-hop is up and traffic is being routed through it, UNREACHABLE: next-hop has been reported down by critical-resource monitoring, UNKNOWN: an interface was configured as next-hop but the gateway has not been determined, INVALID: configured next-hop is not a neighbor
				
				XPath: /extremeWing-stats/device[mac=key1]/pbr_stats[route_map_precedence=key2]/primary_next_hop/state"
			::= { extremeWingStatsDevPbrEntry 5 }

		
		-- 1.3.6.1.4.1.1916.2.131.50.1.4.2.33.1.1.6
		extremeWingStatsDevPbrPrimaryNextHopMonitorMode OBJECT-TYPE
			SYNTAX DisplayString
			MAX-ACCESS read-only
			STATUS current
			DESCRIPTION
				"
				
				XPath: /extremeWing-stats/device[mac=key1]/pbr_stats[route_map_precedence=key2]/primary_next_hop/monitor_mode"
			::= { extremeWingStatsDevPbrEntry 6 }

		
		-- 1.3.6.1.4.1.1916.2.131.50.1.4.2.33.1.1.7
		extremeWingStatsDevPbrSecondaryNextHopIfName OBJECT-TYPE
			SYNTAX DisplayString
			MAX-ACCESS read-only
			STATUS current
			DESCRIPTION
				"
				
				XPath: /extremeWing-stats/device[mac=key1]/pbr_stats[route_map_precedence=key2]/secondary_next_hop/interface_name"
			::= { extremeWingStatsDevPbrEntry 7 }

		
		-- 1.3.6.1.4.1.1916.2.131.50.1.4.2.33.1.1.8
		extremeWingStatsDevPbrSecondaryNextHopIpAddr OBJECT-TYPE
			SYNTAX DisplayString
			MAX-ACCESS read-only
			STATUS current
			DESCRIPTION
				"
				
				XPath: /extremeWing-stats/device[mac=key1]/pbr_stats[route_map_precedence=key2]/secondary_next_hop/ip_address"
			::= { extremeWingStatsDevPbrEntry 8 }

		
		-- 1.3.6.1.4.1.1916.2.131.50.1.4.2.33.1.1.9
		extremeWingStatsDevPbrSecondaryNextHopState OBJECT-TYPE
			SYNTAX DisplayString
			MAX-ACCESS read-only
			STATUS current
			DESCRIPTION
				"UP: next-hop is up and traffic is being routed through it, UNREACHABLE: next-hop has been reported down by critical-resource monitoring, UNKNOWN: an interface was configured as next-hop but the gateway has not been determined, INVALID: configured next-hop is not a neighbor
				
				XPath: /extremeWing-stats/device[mac=key1]/pbr_stats[route_map_precedence=key2]/secondary_next_hop/state"
			::= { extremeWingStatsDevPbrEntry 9 }

		
		-- 1.3.6.1.4.1.1916.2.131.50.1.4.2.33.1.1.10
		extremeWingStatsDevPbrSecondaryNextHopMonitorMode OBJECT-TYPE
			SYNTAX DisplayString
			MAX-ACCESS read-only
			STATUS current
			DESCRIPTION
				"
				
				XPath: /extremeWing-stats/device[mac=key1]/pbr_stats[route_map_precedence=key2]/secondary_next_hop/monitor_mode"
			::= { extremeWingStatsDevPbrEntry 10 }

		
		-- 1.3.6.1.4.1.1916.2.131.50.1.4.2.33.1.1.11
		extremeWingStatsDevPbrDefaultNextHopIfName OBJECT-TYPE
			SYNTAX DisplayString
			MAX-ACCESS read-only
			STATUS current
			DESCRIPTION
				"
				
				XPath: /extremeWing-stats/device[mac=key1]/pbr_stats[route_map_precedence=key2]/default_next_hop/interface_name"
			::= { extremeWingStatsDevPbrEntry 11 }

		
		-- 1.3.6.1.4.1.1916.2.131.50.1.4.2.33.1.1.12
		extremeWingStatsDevPbrDefaultNextHopIpAddr OBJECT-TYPE
			SYNTAX DisplayString
			MAX-ACCESS read-only
			STATUS current
			DESCRIPTION
				"
				
				XPath: /extremeWing-stats/device[mac=key1]/pbr_stats[route_map_precedence=key2]/default_next_hop/ip_address"
			::= { extremeWingStatsDevPbrEntry 12 }

		
		-- 1.3.6.1.4.1.1916.2.131.50.1.4.2.33.1.1.13
		extremeWingStatsDevPbrDefaultNextHopState OBJECT-TYPE
			SYNTAX DisplayString
			MAX-ACCESS read-only
			STATUS current
			DESCRIPTION
				"UP: next-hop is up and traffic is being routed through it, UNREACHABLE: next-hop has been reported down by critical-resource monitoring, UNKNOWN: an interface was configured as next-hop but the gateway has not been determined, INVALID: configured next-hop is not a neighbor
				
				XPath: /extremeWing-stats/device[mac=key1]/pbr_stats[route_map_precedence=key2]/default_next_hop/state"
			::= { extremeWingStatsDevPbrEntry 13 }

		
		-- 1.3.6.1.4.1.1916.2.131.50.1.4.2.33.1.1.14
		extremeWingStatsDevPbrDefaultNextHopMonitorMode OBJECT-TYPE
			SYNTAX DisplayString
			MAX-ACCESS read-only
			STATUS current
			DESCRIPTION
				"
				
				XPath: /extremeWing-stats/device[mac=key1]/pbr_stats[route_map_precedence=key2]/default_next_hop/monitor_mode"
			::= { extremeWingStatsDevPbrEntry 14 }

		
		-- 1.3.6.1.4.1.1916.2.131.50.1.4.2.33.1.1.15
		extremeWingStatsDevPbrWlan OBJECT-TYPE
			SYNTAX DisplayString
			MAX-ACCESS read-only
			STATUS current
			DESCRIPTION
				"
				
				XPath: /extremeWing-stats/device[mac=key1]/pbr_stats[route_map_precedence=key2]/wlan"
			::= { extremeWingStatsDevPbrEntry 15 }

		
		-- 1.3.6.1.4.1.1916.2.131.50.1.4.2.33.1.1.16
		extremeWingStatsDevPbrWirelessClientRole OBJECT-TYPE
			SYNTAX DisplayString
			MAX-ACCESS read-only
			STATUS current
			DESCRIPTION
				"
				
				XPath: /extremeWing-stats/device[mac=key1]/pbr_stats[route_map_precedence=key2]/wireless_client_role"
			::= { extremeWingStatsDevPbrEntry 16 }

		
		-- 1.3.6.1.4.1.1916.2.131.50.1.4.2.33.1.1.17
		extremeWingStatsDevPbrInInterface OBJECT-TYPE
			SYNTAX DisplayString
			MAX-ACCESS read-only
			STATUS current
			DESCRIPTION
				"
				
				XPath: /extremeWing-stats/device[mac=key1]/pbr_stats[route_map_precedence=key2]/in_interface"
			::= { extremeWingStatsDevPbrEntry 17 }

		
		-- 1.3.6.1.4.1.1916.2.131.50.1.4.2.33.1.1.18
		extremeWingStatsDevPbrIpDscp OBJECT-TYPE
			SYNTAX DisplayString
			MAX-ACCESS read-only
			STATUS current
			DESCRIPTION
				"
				
				XPath: /extremeWing-stats/device[mac=key1]/pbr_stats[route_map_precedence=key2]/ip_dscp"
			::= { extremeWingStatsDevPbrEntry 18 }

		
		-- 1.3.6.1.4.1.1916.2.131.50.1.4.2.33.2
		extremeWingStatsDevPbrRulesTable OBJECT-TYPE
			SYNTAX SEQUENCE OF ExtremeWingStatsDevPbrRulesEntry
			MAX-ACCESS not-accessible
			STATUS current
			DESCRIPTION
				"
				
				/extremeWing-stats/device/pbr_stats/rules"
			::= { extremeWingStatsDevPbr 2 }

		
		-- 1.3.6.1.4.1.1916.2.131.50.1.4.2.33.2.1
		extremeWingStatsDevPbrRulesEntry OBJECT-TYPE
			SYNTAX ExtremeWingStatsDevPbrRulesEntry
			MAX-ACCESS not-accessible
			STATUS current
			DESCRIPTION
				"An entry in the table."
			INDEX { extremeWingStatsDevMac, extremeWingStatsDevPbrRouteMapPrecedence, extremeWingStatsDevPbrRuleString }
			::= { extremeWingStatsDevPbrRulesTable 1 }

		
		ExtremeWingStatsDevPbrRulesEntry ::=
			SEQUENCE { 
				extremeWingStatsDevPbrRuleString
					ExtremeWingIdentifier,
				extremeWingStatsDevPbrRulesHitcount
					Unsigned32
			 }

		-- 1.3.6.1.4.1.1916.2.131.50.1.4.2.33.2.1.1
		extremeWingStatsDevPbrRuleString OBJECT-TYPE
			SYNTAX ExtremeWingIdentifier
			MAX-ACCESS read-only
			STATUS current
			DESCRIPTION
				"
				
				XPath: /extremeWing-stats/device[mac=key1]/pbr_stats[route_map_precedence=key2]/rules[rule_string=key3]/match_criteria/rule_string"
			::= { extremeWingStatsDevPbrRulesEntry 1 }

		
		-- 1.3.6.1.4.1.1916.2.131.50.1.4.2.33.2.1.3
		extremeWingStatsDevPbrRulesHitcount OBJECT-TYPE
			SYNTAX Unsigned32
			MAX-ACCESS read-only
			STATUS current
			DESCRIPTION
				"
				
				XPath: /extremeWing-stats/device[mac=key1]/pbr_stats[route_map_precedence=key2]/rules[rule_string=key3]/match_criteria/hitcount"
			::= { extremeWingStatsDevPbrRulesEntry 3 }

		
		-- 1.3.6.1.4.1.1916.2.131.50.1.4.2.34
		extremeWingStatsDevDynRoute OBJECT IDENTIFIER ::= { extremeWingStatsDev 34 }
-- Ospf Stats
		
		-- 1.3.6.1.4.1.1916.2.131.50.1.4.2.34.1
		extremeWingStatsDevDynRouteIpOspfTable OBJECT-TYPE
			SYNTAX SEQUENCE OF ExtremeWingStatsDevDynRouteIpOspfEntry
			MAX-ACCESS not-accessible
			STATUS current
			DESCRIPTION
				"Ip Ospf Stats."
			::= { extremeWingStatsDevDynRoute 1 }

		
		-- 1.3.6.1.4.1.1916.2.131.50.1.4.2.34.1.1
		extremeWingStatsDevDynRouteIpOspfEntry OBJECT-TYPE
			SYNTAX ExtremeWingStatsDevDynRouteIpOspfEntry
			MAX-ACCESS not-accessible
			STATUS current
			DESCRIPTION
				"An entry in the table."
			INDEX { extremeWingStatsDevMac }
			::= { extremeWingStatsDevDynRouteIpOspfTable 1 }

		
		ExtremeWingStatsDevDynRouteIpOspfEntry ::=
			SEQUENCE { 
				extremeWingStatsDevDynRouteIpOspfRouterId
					ExtremeWingIdentifier,
				extremeWingStatsDevDynRouteIpOspfShutdownFlag
					TruthValue,
				extremeWingStatsDevDynRouteIpOspfShutdownDueTime
					DisplayString,
				extremeWingStatsDevDynRouteIpOspfTos
					Unsigned32,
				extremeWingStatsDevDynRouteIpOspfRFC2328ConformanceFlag
					TruthValue,
				extremeWingStatsDevDynRouteIpOspfRFC1583CompatFlag
					TruthValue,
				extremeWingStatsDevDynRouteIpOspfOpaquelsaFlag
					TruthValue,
				extremeWingStatsDevDynRouteIpOspfOpaquelsaOriginationBlockedFlag
					TruthValue,
				extremeWingStatsDevDynRouteIpOspfStubRouterAdvFlag
					TruthValue,
				extremeWingStatsDevDynRouteIpOspfStubRouterStartupTime
					Unsigned32,
				extremeWingStatsDevDynRouteIpOspfStubRouterShutdownTime
					Unsigned32,
				extremeWingStatsDevDynRouteIpOspfDelay
					Unsigned32,
				extremeWingStatsDevDynRouteIpOspfHoldTime
					Unsigned32,
				extremeWingStatsDevDynRouteIpOspfMaxHoldTime
					Unsigned32,
				extremeWingStatsDevDynRouteIpOspfHoldMultiplier
					Unsigned32,
				extremeWingStatsDevDynRouteIpOspfExecutedFlag
					TruthValue,
				extremeWingStatsDevDynRouteIpOspfExecutedWhen
					DisplayString,
				extremeWingStatsDevDynRouteIpOspfTimerDueFlag
					TruthValue,
				extremeWingStatsDevDynRouteIpOspfDueIn
					DisplayString,
				extremeWingStatsDevDynRouteIpOspflsaRefreshTimer
					Unsigned32,
				extremeWingStatsDevDynRouteIpOspfAbrFlag
					TruthValue,
				extremeWingStatsDevDynRouteIpOspfAbrType
					DisplayString,
				extremeWingStatsDevDynRouteIpOspfAsbrFlag
					TruthValue,
				extremeWingStatsDevDynRouteIpOspfExtLsdbCount
					Counter64,
				extremeWingStatsDevDynRouteIpOspfExtLsdbCsum
					Unsigned32,
				extremeWingStatsDevDynRouteIpOspfOpaqueLsdbCount
					Counter64,
				extremeWingStatsDevDynRouteIpOspfOpaqueExtLsdbCsum
					Unsigned32,
				extremeWingStatsDevDynRouteIpOspfNumAreasAttached
					Unsigned32,
				extremeWingStatsDevDynRouteIpOspfMaxRoutes
					Unsigned32,
				extremeWingStatsDevDynRouteIpOspfRoutesReceived
					Unsigned32,
				extremeWingStatsDevDynRouteIpOspfMaxIgnoreStateCount
					Unsigned32,
				extremeWingStatsDevDynRouteIpOspfIgnoreStateCount
					Unsigned32,
				extremeWingStatsDevDynRouteIpOspfIgnoreStateTimeout
					Unsigned32,
				extremeWingStatsDevDynRouteIpOspfIgnoreStateMonitorTimeout
					Unsigned32,
				extremeWingStatsDevDynRouteIpOspfState
					DisplayString
			 }

		-- 1.3.6.1.4.1.1916.2.131.50.1.4.2.34.1.1.1
		extremeWingStatsDevDynRouteIpOspfRouterId OBJECT-TYPE
			SYNTAX ExtremeWingIdentifier
			MAX-ACCESS read-only
			STATUS current
			DESCRIPTION
				"Router-ID for this device.
				
				XPath: /extremeWing-stats/device[mac=key1]/ospf_stats/ip_ospf_stats/router_id"
			::= { extremeWingStatsDevDynRouteIpOspfEntry 1 }

		
		-- 1.3.6.1.4.1.1916.2.131.50.1.4.2.34.1.1.2
		extremeWingStatsDevDynRouteIpOspfShutdownFlag OBJECT-TYPE
			SYNTAX TruthValue
			MAX-ACCESS read-only
			STATUS current
			DESCRIPTION
				"Whether gracefull shutdown is in progress.
				
				XPath: /extremeWing-stats/device[mac=key1]/ospf_stats/ip_ospf_stats/gracefull_shutdown_flag"
			::= { extremeWingStatsDevDynRouteIpOspfEntry 2 }

		
		-- 1.3.6.1.4.1.1916.2.131.50.1.4.2.34.1.1.3
		extremeWingStatsDevDynRouteIpOspfShutdownDueTime OBJECT-TYPE
			SYNTAX DisplayString
			MAX-ACCESS read-only
			STATUS current
			DESCRIPTION
				"Last time SPF was executed in <HH>h<MM>m<SS>s format.
				
				XPath: /extremeWing-stats/device[mac=key1]/ospf_stats/ip_ospf_stats/shutdown_due_time"
			::= { extremeWingStatsDevDynRouteIpOspfEntry 3 }

		
		-- 1.3.6.1.4.1.1916.2.131.50.1.4.2.34.1.1.4
		extremeWingStatsDevDynRouteIpOspfTos OBJECT-TYPE
			SYNTAX Unsigned32
			MAX-ACCESS read-only
			STATUS current
			DESCRIPTION
				"This implementaion of OSPF supports only single TOS(TOS0) routes.
				
				XPath: /extremeWing-stats/device[mac=key1]/ospf_stats/ip_ospf_stats/tos
				"
			::= { extremeWingStatsDevDynRouteIpOspfEntry 4 }

		
		-- 1.3.6.1.4.1.1916.2.131.50.1.4.2.34.1.1.5
		extremeWingStatsDevDynRouteIpOspfRFC2328ConformanceFlag OBJECT-TYPE
			SYNTAX TruthValue
			MAX-ACCESS read-only
			STATUS current
			DESCRIPTION
				"Whether this implementation of OSPF is RFC 2328 compliant
				
				XPath: /extremeWing-stats/device[mac=key1]/ospf_stats/ip_ospf_stats/rfc2328_conformance_flag"
			::= { extremeWingStatsDevDynRouteIpOspfEntry 5 }

		
		-- 1.3.6.1.4.1.1916.2.131.50.1.4.2.34.1.1.6
		extremeWingStatsDevDynRouteIpOspfRFC1583CompatFlag OBJECT-TYPE
			SYNTAX TruthValue
			MAX-ACCESS read-only
			STATUS current
			DESCRIPTION
				"Whether this implementation of OSPF is RFC 1583 compliant.
				
				XPath: /extremeWing-stats/device[mac=key1]/ospf_stats/ip_ospf_stats/rfc1583_compat_flag"
			::= { extremeWingStatsDevDynRouteIpOspfEntry 6 }

		
		-- 1.3.6.1.4.1.1916.2.131.50.1.4.2.34.1.1.7
		extremeWingStatsDevDynRouteIpOspfOpaquelsaFlag OBJECT-TYPE
			SYNTAX TruthValue
			MAX-ACCESS read-only
			STATUS current
			DESCRIPTION
				"Whether opaque LSA is supported.
				
				XPath: /extremeWing-stats/device[mac=key1]/ospf_stats/ip_ospf_stats/opaque_lsa_flag"
			::= { extremeWingStatsDevDynRouteIpOspfEntry 7 }

		
		-- 1.3.6.1.4.1.1916.2.131.50.1.4.2.34.1.1.8
		extremeWingStatsDevDynRouteIpOspfOpaquelsaOriginationBlockedFlag OBJECT-TYPE
			SYNTAX TruthValue
			MAX-ACCESS read-only
			STATUS current
			DESCRIPTION
				"Whether opaque LSA origination is blocked.
				
				XPath: /extremeWing-stats/device[mac=key1]/ospf_stats/ip_ospf_stats/opaque_lsa_origination_blocked_flag"
			::= { extremeWingStatsDevDynRouteIpOspfEntry 8 }

		
		-- 1.3.6.1.4.1.1916.2.131.50.1.4.2.34.1.1.9
		extremeWingStatsDevDynRouteIpOspfStubRouterAdvFlag OBJECT-TYPE
			SYNTAX TruthValue
			MAX-ACCESS read-only
			STATUS current
			DESCRIPTION
				"Whether stub router advertisement is configured.
				
				XPath: /extremeWing-stats/device[mac=key1]/ospf_stats/ip_ospf_stats/stub_router_adv_flag"
			::= { extremeWingStatsDevDynRouteIpOspfEntry 9 }

		
		-- 1.3.6.1.4.1.1916.2.131.50.1.4.2.34.1.1.10
		extremeWingStatsDevDynRouteIpOspfStubRouterStartupTime OBJECT-TYPE
			SYNTAX Unsigned32
			MAX-ACCESS read-only
			STATUS current
			DESCRIPTION
				"Stub router advertisement starts configured seconds after startup.
				
				XPath: /extremeWing-stats/device[mac=key1]/ospf_stats/ip_ospf_stats/stub_router_startup_time"
			::= { extremeWingStatsDevDynRouteIpOspfEntry 10 }

		
		-- 1.3.6.1.4.1.1916.2.131.50.1.4.2.34.1.1.11
		extremeWingStatsDevDynRouteIpOspfStubRouterShutdownTime OBJECT-TYPE
			SYNTAX Unsigned32
			MAX-ACCESS read-only
			STATUS current
			DESCRIPTION
				"Stub router advertisement stops configured seconds prior to shutdown.
				
				XPath: /extremeWing-stats/device[mac=key1]/ospf_stats/ip_ospf_stats/stub_router_shutdown_time"
			::= { extremeWingStatsDevDynRouteIpOspfEntry 11 }

		
		-- 1.3.6.1.4.1.1916.2.131.50.1.4.2.34.1.1.12
		extremeWingStatsDevDynRouteIpOspfDelay OBJECT-TYPE
			SYNTAX Unsigned32
			MAX-ACCESS read-only
			STATUS current
			DESCRIPTION
				"Initial SPF scheduling delay in milliseconds.
				
				XPath: /extremeWing-stats/device[mac=key1]/ospf_stats/ip_ospf_stats/spf_delay"
			::= { extremeWingStatsDevDynRouteIpOspfEntry 12 }

		
		-- 1.3.6.1.4.1.1916.2.131.50.1.4.2.34.1.1.13
		extremeWingStatsDevDynRouteIpOspfHoldTime OBJECT-TYPE
			SYNTAX Unsigned32
			MAX-ACCESS read-only
			STATUS current
			DESCRIPTION
				"Minimum hold time between consecutive SPFs in milliseconds.
				
				XPath: /extremeWing-stats/device[mac=key1]/ospf_stats/ip_ospf_stats/spf_holdtime"
			::= { extremeWingStatsDevDynRouteIpOspfEntry 13 }

		
		-- 1.3.6.1.4.1.1916.2.131.50.1.4.2.34.1.1.14
		extremeWingStatsDevDynRouteIpOspfMaxHoldTime OBJECT-TYPE
			SYNTAX Unsigned32
			MAX-ACCESS read-only
			STATUS current
			DESCRIPTION
				"Maximum hold time between consecutive SPFs in milliseconds.
				
				XPath: /extremeWing-stats/device[mac=key1]/ospf_stats/ip_ospf_stats/spf_max_holdtime"
			::= { extremeWingStatsDevDynRouteIpOspfEntry 14 }

		
		-- 1.3.6.1.4.1.1916.2.131.50.1.4.2.34.1.1.15
		extremeWingStatsDevDynRouteIpOspfHoldMultiplier OBJECT-TYPE
			SYNTAX Unsigned32
			MAX-ACCESS read-only
			STATUS current
			DESCRIPTION
				"Holdtime multiplier factor.
				
				XPath: /extremeWing-stats/device[mac=key1]/ospf_stats/ip_ospf_stats/spf_hold_multiplier"
			::= { extremeWingStatsDevDynRouteIpOspfEntry 15 }

		
		-- 1.3.6.1.4.1.1916.2.131.50.1.4.2.34.1.1.16
		extremeWingStatsDevDynRouteIpOspfExecutedFlag OBJECT-TYPE
			SYNTAX TruthValue
			MAX-ACCESS read-only
			STATUS current
			DESCRIPTION
				"Whether SPF algorithm has been executed.
				
				XPath: /extremeWing-stats/device[mac=key1]/ospf_stats/ip_ospf_stats/spf_executed_flag
				"
			::= { extremeWingStatsDevDynRouteIpOspfEntry 16 }

		
		-- 1.3.6.1.4.1.1916.2.131.50.1.4.2.34.1.1.17
		extremeWingStatsDevDynRouteIpOspfExecutedWhen OBJECT-TYPE
			SYNTAX DisplayString
			MAX-ACCESS read-only
			STATUS current
			DESCRIPTION
				"Last time SPF was executed in <HH>h<MM>m<SS>s format.
				
				XPath: /extremeWing-stats/device[mac=key1]/ospf_stats/ip_ospf_stats/spf_executed_when"
			::= { extremeWingStatsDevDynRouteIpOspfEntry 17 }

		
		-- 1.3.6.1.4.1.1916.2.131.50.1.4.2.34.1.1.18
		extremeWingStatsDevDynRouteIpOspfTimerDueFlag OBJECT-TYPE
			SYNTAX TruthValue
			MAX-ACCESS read-only
			STATUS current
			DESCRIPTION
				"Whether SPF timer is due or not.
				
				XPath: /extremeWing-stats/device[mac=key1]/ospf_stats/ip_ospf_stats/spf_timer_due_flag
				"
			::= { extremeWingStatsDevDynRouteIpOspfEntry 18 }

		
		-- 1.3.6.1.4.1.1916.2.131.50.1.4.2.34.1.1.19
		extremeWingStatsDevDynRouteIpOspfDueIn OBJECT-TYPE
			SYNTAX DisplayString
			MAX-ACCESS read-only
			STATUS current
			DESCRIPTION
				"Time SPF algorithm is due in <HH>h<MM>m<SS>s format.
				
				XPath: /extremeWing-stats/device[mac=key1]/ospf_stats/ip_ospf_stats/spf_due_in"
			::= { extremeWingStatsDevDynRouteIpOspfEntry 19 }

		
		-- 1.3.6.1.4.1.1916.2.131.50.1.4.2.34.1.1.20
		extremeWingStatsDevDynRouteIpOspflsaRefreshTimer OBJECT-TYPE
			SYNTAX Unsigned32
			MAX-ACCESS read-only
			STATUS current
			DESCRIPTION
				"LSA refresh timer in seconds.
				
				XPath: /extremeWing-stats/device[mac=key1]/ospf_stats/ip_ospf_stats/lsa_refresh_timer"
			::= { extremeWingStatsDevDynRouteIpOspfEntry 20 }

		
		-- 1.3.6.1.4.1.1916.2.131.50.1.4.2.34.1.1.21
		extremeWingStatsDevDynRouteIpOspfAbrFlag OBJECT-TYPE
			SYNTAX TruthValue
			MAX-ACCESS read-only
			STATUS current
			DESCRIPTION
				"Whether this router is an ABR.
				
				XPath: /extremeWing-stats/device[mac=key1]/ospf_stats/ip_ospf_stats/abr_flag"
			::= { extremeWingStatsDevDynRouteIpOspfEntry 21 }

		
		-- 1.3.6.1.4.1.1916.2.131.50.1.4.2.34.1.1.22
		extremeWingStatsDevDynRouteIpOspfAbrType OBJECT-TYPE
			SYNTAX DisplayString
			MAX-ACCESS read-only
			STATUS current
			DESCRIPTION
				"Type of ABR.
				
				enum Unknown
				enum Standard (RFC2328)
				enum Alternative IBM
				enum Alternative CISCO
				enum Alternative Shortcut.
				
				XPath: /extremeWing-stats/device[mac=key1]/ospf_stats/ip_ospf_stats/abr_type"
			::= { extremeWingStatsDevDynRouteIpOspfEntry 22 }

		
		-- 1.3.6.1.4.1.1916.2.131.50.1.4.2.34.1.1.23
		extremeWingStatsDevDynRouteIpOspfAsbrFlag OBJECT-TYPE
			SYNTAX TruthValue
			MAX-ACCESS read-only
			STATUS current
			DESCRIPTION
				"Whetner this router is an ASBR.
				
				XPath: /extremeWing-stats/device[mac=key1]/ospf_stats/ip_ospf_stats/asbr_flag"
			::= { extremeWingStatsDevDynRouteIpOspfEntry 23 }

		
		-- 1.3.6.1.4.1.1916.2.131.50.1.4.2.34.1.1.24
		extremeWingStatsDevDynRouteIpOspfExtLsdbCount OBJECT-TYPE
			SYNTAX Counter64
			MAX-ACCESS read-only
			STATUS current
			DESCRIPTION
				"Number of external LSAs.
				
				XPath: /extremeWing-stats/device[mac=key1]/ospf_stats/ip_ospf_stats/ext_lsdb_count"
			::= { extremeWingStatsDevDynRouteIpOspfEntry 24 }

		
		-- 1.3.6.1.4.1.1916.2.131.50.1.4.2.34.1.1.25
		extremeWingStatsDevDynRouteIpOspfExtLsdbCsum OBJECT-TYPE
			SYNTAX Unsigned32
			MAX-ACCESS read-only
			STATUS current
			DESCRIPTION
				"External LSA checksum.
				
				XPath: /extremeWing-stats/device[mac=key1]/ospf_stats/ip_ospf_stats/ext_lsdb_csum"
			::= { extremeWingStatsDevDynRouteIpOspfEntry 25 }

		
		-- 1.3.6.1.4.1.1916.2.131.50.1.4.2.34.1.1.26
		extremeWingStatsDevDynRouteIpOspfOpaqueLsdbCount OBJECT-TYPE
			SYNTAX Counter64
			MAX-ACCESS read-only
			STATUS current
			DESCRIPTION
				"Number of opaque AS LSAs.
				
				XPath: /extremeWing-stats/device[mac=key1]/ospf_stats/ip_ospf_stats/opaque_lsdb_count"
			::= { extremeWingStatsDevDynRouteIpOspfEntry 26 }

		
		-- 1.3.6.1.4.1.1916.2.131.50.1.4.2.34.1.1.27
		extremeWingStatsDevDynRouteIpOspfOpaqueExtLsdbCsum OBJECT-TYPE
			SYNTAX Unsigned32
			MAX-ACCESS read-only
			STATUS current
			DESCRIPTION
				"Opaque AS LSA checksum.
				
				XPath: /extremeWing-stats/device[mac=key1]/ospf_stats/ip_ospf_stats/opaque_ext_lsdb_csum"
			::= { extremeWingStatsDevDynRouteIpOspfEntry 27 }

		
		-- 1.3.6.1.4.1.1916.2.131.50.1.4.2.34.1.1.28
		extremeWingStatsDevDynRouteIpOspfNumAreasAttached OBJECT-TYPE
			SYNTAX Unsigned32
			MAX-ACCESS read-only
			STATUS current
			DESCRIPTION
				"Number of OSPF areas attached to this router.
				
				XPath: /extremeWing-stats/device[mac=key1]/ospf_stats/ip_ospf_stats/num_areas_attached"
			::= { extremeWingStatsDevDynRouteIpOspfEntry 28 }

		
		-- 1.3.6.1.4.1.1916.2.131.50.1.4.2.34.1.1.29
		extremeWingStatsDevDynRouteIpOspfMaxRoutes OBJECT-TYPE
			SYNTAX Unsigned32
			MAX-ACCESS read-only
			STATUS current
			DESCRIPTION
				"Maximum number of OSPF routes allowed.
				
				XPath: /extremeWing-stats/device[mac=key1]/ospf_stats/ip_ospf_state/ospf_max_routes"
			::= { extremeWingStatsDevDynRouteIpOspfEntry 29 }

		
		-- 1.3.6.1.4.1.1916.2.131.50.1.4.2.34.1.1.30
		extremeWingStatsDevDynRouteIpOspfRoutesReceived OBJECT-TYPE
			SYNTAX Unsigned32
			MAX-ACCESS read-only
			STATUS current
			DESCRIPTION
				"Number of OSPF routes received so far.
				
				XPath: /extremeWing-stats/device[mac=key1]/ospf_stats/ip_ospf_state/ospf_routes_received"
			::= { extremeWingStatsDevDynRouteIpOspfEntry 30 }

		
		-- 1.3.6.1.4.1.1916.2.131.50.1.4.2.34.1.1.31
		extremeWingStatsDevDynRouteIpOspfMaxIgnoreStateCount OBJECT-TYPE
			SYNTAX Unsigned32
			MAX-ACCESS read-only
			STATUS current
			DESCRIPTION
				"Maximum number of times ospfd can be put in ignore state before entering permanent ignore state.
				
				XPath: /extremeWing-stats/device[mac=key1]/ospf_stats/ip_ospf_state/ospf_max_ignore_state_count"
			::= { extremeWingStatsDevDynRouteIpOspfEntry 31 }

		
		-- 1.3.6.1.4.1.1916.2.131.50.1.4.2.34.1.1.32
		extremeWingStatsDevDynRouteIpOspfIgnoreStateCount OBJECT-TYPE
			SYNTAX Unsigned32
			MAX-ACCESS read-only
			STATUS current
			DESCRIPTION
				"Number of times ospfd has been put in ignore state.
				
				XPath: /extremeWing-stats/device[mac=key1]/ospf_stats/ip_ospf_state/ospf_ignore_state_count"
			::= { extremeWingStatsDevDynRouteIpOspfEntry 32 }

		
		-- 1.3.6.1.4.1.1916.2.131.50.1.4.2.34.1.1.33
		extremeWingStatsDevDynRouteIpOspfIgnoreStateTimeout OBJECT-TYPE
			SYNTAX Unsigned32
			MAX-ACCESS read-only
			STATUS current
			DESCRIPTION
				"Time after which ospfd shall exit the ignore state.
				
				XPath: /extremeWing-stats/device[mac=key1]/ospf_stats/ip_ospf_state/ospf_ignore_state_timeout"
			::= { extremeWingStatsDevDynRouteIpOspfEntry 33 }

		
		-- 1.3.6.1.4.1.1916.2.131.50.1.4.2.34.1.1.34
		extremeWingStatsDevDynRouteIpOspfIgnoreStateMonitorTimeout OBJECT-TYPE
			SYNTAX Unsigned32
			MAX-ACCESS read-only
			STATUS current
			DESCRIPTION
				"Time after which ignore state count is reset to zero and ospfd continues in the state it was.
				
				XPath: /extremeWing-stats/device[mac=key1]/ospf_stats/ip_ospf_state/ospf_ignore_state_monitor_timeout"
			::= { extremeWingStatsDevDynRouteIpOspfEntry 34 }

		
		-- 1.3.6.1.4.1.1916.2.131.50.1.4.2.34.1.1.35
		extremeWingStatsDevDynRouteIpOspfState OBJECT-TYPE
			SYNTAX DisplayString
			MAX-ACCESS read-only
			STATUS current
			DESCRIPTION
				"current state of ospfd.
				Running,
				Temporary ignore,
				Permanent ignore
				
				XPath: /extremeWing-stats/device[mac=key1]/ospf_stats/ip_ospf_state/ospf_state"
			::= { extremeWingStatsDevDynRouteIpOspfEntry 35 }

		
		-- 1.3.6.1.4.1.1916.2.131.50.1.4.2.34.2
		extremeWingStatsDevDynRouteOspfAreaTable OBJECT-TYPE
			SYNTAX SEQUENCE OF ExtremeWingStatsDevDynRouteOspfAreaEntry
			MAX-ACCESS not-accessible
			STATUS current
			DESCRIPTION
				"Ospf Area Stats"
			::= { extremeWingStatsDevDynRoute 2 }

		
		-- 1.3.6.1.4.1.1916.2.131.50.1.4.2.34.2.1
		extremeWingStatsDevDynRouteOspfAreaEntry OBJECT-TYPE
			SYNTAX ExtremeWingStatsDevDynRouteOspfAreaEntry
			MAX-ACCESS not-accessible
			STATUS current
			DESCRIPTION
				"An entry in the table."
			INDEX { extremeWingStatsDevMac, extremeWingStatsDevDynRouteOspfAreaId }
			::= { extremeWingStatsDevDynRouteOspfAreaTable 1 }

		
		ExtremeWingStatsDevDynRouteOspfAreaEntry ::=
			SEQUENCE { 
				extremeWingStatsDevDynRouteOspfAreaId
					ExtremeWingIdentifier,
				extremeWingStatsDevDynRouteOspfAreaType
					DisplayString,
				extremeWingStatsDevDynRouteOspfAreaBackboneFlag
					TruthValue,
				extremeWingStatsDevDynRouteOspfAreaNoSummaryFlag
					TruthValue,
				extremeWingStatsDevDynRouteOspfAreaShortcutType
					DisplayString,
				extremeWingStatsDevDynRouteOspfAreaShortcutCapability
					TruthValue,
				extremeWingStatsDevDynRouteOspfAreaInterfaceNum
					Unsigned32,
				extremeWingStatsDevDynRouteOspfAreaActiveInterfaces
					Unsigned32,
				extremeWingStatsDevDynRouteOspfAreaNssaFlag
					TruthValue,
				extremeWingStatsDevDynRouteOspfAreaNssaTransType
					DisplayString,
				extremeWingStatsDevDynRouteOspfAreaStubRouterStateFlag
					TruthValue,
				extremeWingStatsDevDynRouteOspfAreaAdminStubRoutedFlag
					TruthValue,
				extremeWingStatsDevDynRouteOspfAreaStartupTimeDue
					DisplayString,
				extremeWingStatsDevDynRouteOspfAreaNumFullyAdjNbrs
					Unsigned32,
				extremeWingStatsDevDynRouteOspfAreaAuthType
					DisplayString,
				extremeWingStatsDevDynRouteOspfAreaNumFullVirtualAdj
					Unsigned32,
				extremeWingStatsDevDynRouteOspfAreaNumSpfExecuted
					Unsigned32,
				extremeWingStatsDevDynRouteOspfAreaNumTotalLsa
					Counter64,
				extremeWingStatsDevDynRouteOspfAreaNumRouterLsa
					Counter64,
				extremeWingStatsDevDynRouteOspfAreaRouterLsaCsum
					Unsigned32,
				extremeWingStatsDevDynRouteOspfAreaNumNetworkLsa
					Counter64,
				extremeWingStatsDevDynRouteOspfAreaNetworkLsaCsum
					Unsigned32,
				extremeWingStatsDevDynRouteOspfAreaNumSummaryLsa
					Counter64,
				extremeWingStatsDevDynRouteOspfAreaSummaryLsaCsum
					Unsigned32,
				extremeWingStatsDevDynRouteOspfAreaNumAsbrSummaryLsa
					Counter64,
				extremeWingStatsDevDynRouteOspfAreaAsbrSummaryLsaCsum
					Unsigned32,
				extremeWingStatsDevDynRouteOspfAreaNumNssaLsa
					Counter64,
				extremeWingStatsDevDynRouteOspfAreaNssaLsaCsum
					Unsigned32,
				extremeWingStatsDevDynRouteOspfAreaNumOpaqueLinkLsa
					Counter64,
				extremeWingStatsDevDynRouteOspfAreaOpaqueLinkLsaCsum
					Unsigned32,
				extremeWingStatsDevDynRouteOspfAreaNumOpaqueAreaLsa
					Counter64,
				extremeWingStatsDevDynRouteOspfAreaOpaqueAreaLsaCsum
					Unsigned32
			 }

		-- 1.3.6.1.4.1.1916.2.131.50.1.4.2.34.2.1.1
		extremeWingStatsDevDynRouteOspfAreaId OBJECT-TYPE
			SYNTAX ExtremeWingIdentifier
			MAX-ACCESS read-only
			STATUS current
			DESCRIPTION
				"OSPF area-id.
				
				XPath: /extremeWing-stats/device[mac=key1]/ospf_stats/ip_ospf_stats/ospf_area_stats[ospf_area_id=key2]/ospf_area_id"
			::= { extremeWingStatsDevDynRouteOspfAreaEntry 1 }

		
		-- 1.3.6.1.4.1.1916.2.131.50.1.4.2.34.2.1.2
		extremeWingStatsDevDynRouteOspfAreaType OBJECT-TYPE
			SYNTAX DisplayString
			MAX-ACCESS read-only
			STATUS current
			DESCRIPTION
				"Type of this OSPF area.
				
				XPath: /extremeWing-stats/device[mac=key1]/ospf_stats/ip_ospf_stats/ospf_area_stats[ospf_area_id=key2]/area_type"
			::= { extremeWingStatsDevDynRouteOspfAreaEntry 2 }

		
		-- 1.3.6.1.4.1.1916.2.131.50.1.4.2.34.2.1.3
		extremeWingStatsDevDynRouteOspfAreaBackboneFlag OBJECT-TYPE
			SYNTAX TruthValue
			MAX-ACCESS read-only
			STATUS current
			DESCRIPTION
				"Whether this area is backbone.
				
				XPath: /extremeWing-stats/device[mac=key1]/ospf_stats/ip_ospf_stats/ospf_area_stats[ospf_area_id=key2]/backbone_flag"
			::= { extremeWingStatsDevDynRouteOspfAreaEntry 3 }

		
		-- 1.3.6.1.4.1.1916.2.131.50.1.4.2.34.2.1.4
		extremeWingStatsDevDynRouteOspfAreaNoSummaryFlag OBJECT-TYPE
			SYNTAX TruthValue
			MAX-ACCESS read-only
			STATUS current
			DESCRIPTION
				"Whether to inject inter-area routes into stub.
				
				XPath: /extremeWing-stats/device[mac=key1]/ospf_stats/ip_ospf_stats/ospf_area_stats[ospf_area_id=key2]/no_summary_flag"
			::= { extremeWingStatsDevDynRouteOspfAreaEntry 4 }

		
		-- 1.3.6.1.4.1.1916.2.131.50.1.4.2.34.2.1.5
		extremeWingStatsDevDynRouteOspfAreaShortcutType OBJECT-TYPE
			SYNTAX DisplayString
			MAX-ACCESS read-only
			STATUS current
			DESCRIPTION
				"Shortcutting mode of this area.
				
				XPath: /extremeWing-stats/device[mac=key1]/ospf_stats/ip_ospf_stats/ospf_area_stats[ospf_area_id=key2]/shortcut_type"
			::= { extremeWingStatsDevDynRouteOspfAreaEntry 5 }

		
		-- 1.3.6.1.4.1.1916.2.131.50.1.4.2.34.2.1.6
		extremeWingStatsDevDynRouteOspfAreaShortcutCapability OBJECT-TYPE
			SYNTAX TruthValue
			MAX-ACCESS read-only
			STATUS current
			DESCRIPTION
				"Whether other ABRs agree on S-bit.
				
				XPath: /extremeWing-stats/device[mac=key1]/ospf_stats/ip_ospf_stats/ospf_area_stats[ospf_area_id=key2]/shortcut_capability"
			::= { extremeWingStatsDevDynRouteOspfAreaEntry 6 }

		
		-- 1.3.6.1.4.1.1916.2.131.50.1.4.2.34.2.1.7
		extremeWingStatsDevDynRouteOspfAreaInterfaceNum OBJECT-TYPE
			SYNTAX Unsigned32
			MAX-ACCESS read-only
			STATUS current
			DESCRIPTION
				"Total number of OSPF interfaces in this area.
				
				XPath: /extremeWing-stats/device[mac=key1]/ospf_stats/ip_ospf_stats/ospf_area_stats[ospf_area_id=key2]/num_ospf_inf"
			::= { extremeWingStatsDevDynRouteOspfAreaEntry 7 }

		
		-- 1.3.6.1.4.1.1916.2.131.50.1.4.2.34.2.1.8
		extremeWingStatsDevDynRouteOspfAreaActiveInterfaces OBJECT-TYPE
			SYNTAX Unsigned32
			MAX-ACCESS read-only
			STATUS current
			DESCRIPTION
				"Total number of active OSPF interfaces in this area.
				
				XPath: /extremeWing-stats/device[mac=key1]/ospf_stats/ip_ospf_stats/ospf_area_stats[ospf_area_id=key2]/num_active_ospf_inf"
			::= { extremeWingStatsDevDynRouteOspfAreaEntry 8 }

		
		-- 1.3.6.1.4.1.1916.2.131.50.1.4.2.34.2.1.9
		extremeWingStatsDevDynRouteOspfAreaNssaFlag OBJECT-TYPE
			SYNTAX TruthValue
			MAX-ACCESS read-only
			STATUS current
			DESCRIPTION
				"Whether this area is NSSA.
				
				XPath: /extremeWing-stats/device[mac=key1]/ospf_stats/ip_ospf_stats/ospf_area_stats[ospf_area_id=key2]/nssa_area_flag"
			::= { extremeWingStatsDevDynRouteOspfAreaEntry 9 }

		
		-- 1.3.6.1.4.1.1916.2.131.50.1.4.2.34.2.1.10
		extremeWingStatsDevDynRouteOspfAreaNssaTransType OBJECT-TYPE
			SYNTAX DisplayString
			MAX-ACCESS read-only
			STATUS current
			DESCRIPTION
				"LSA type7 to LSA type5 translation in NSSA.
				
				XPath: /extremeWing-stats/device[mac=key1]/ospf_stats/ip_ospf_stats/ospf_area_stats[ospf_area_id=key2]/nssa_translator_type"
			::= { extremeWingStatsDevDynRouteOspfAreaEntry 10 }

		
		-- 1.3.6.1.4.1.1916.2.131.50.1.4.2.34.2.1.11
		extremeWingStatsDevDynRouteOspfAreaStubRouterStateFlag OBJECT-TYPE
			SYNTAX TruthValue
			MAX-ACCESS read-only
			STATUS current
			DESCRIPTION
				"Whether the router is in STUB state for this area.
				
				XPath: /extremeWing-stats/device[mac=key1]/ospf_stats/ip_ospf_stats/ospf_area_stats[ospf_area_id=key2]/stub_router_state_flag"
			::= { extremeWingStatsDevDynRouteOspfAreaEntry 11 }

		
		-- 1.3.6.1.4.1.1916.2.131.50.1.4.2.34.2.1.12
		extremeWingStatsDevDynRouteOspfAreaAdminStubRoutedFlag OBJECT-TYPE
			SYNTAX TruthValue
			MAX-ACCESS read-only
			STATUS current
			DESCRIPTION
				"Admin stub router state.
				
				XPath: /extremeWing-stats/device[mac=key1]/ospf_stats/ip_ospf_stats/ospf_area_stats[ospf_area_id=key2]/admin_stub_routed_flag"
			::= { extremeWingStatsDevDynRouteOspfAreaEntry 12 }

		
		-- 1.3.6.1.4.1.1916.2.131.50.1.4.2.34.2.1.13
		extremeWingStatsDevDynRouteOspfAreaStartupTimeDue OBJECT-TYPE
			SYNTAX DisplayString
			MAX-ACCESS read-only
			STATUS current
			DESCRIPTION
				"Time remaining to enter STUB state in <HH>h<MM>m<SS>s format.
				
				XPath: /extremeWing-stats/device[mac=key1]/ospf_stats/ip_ospf_stats/ospf_area_stats[ospf_area_id=key2]/startup_time_due"
			::= { extremeWingStatsDevDynRouteOspfAreaEntry 13 }

		
		-- 1.3.6.1.4.1.1916.2.131.50.1.4.2.34.2.1.14
		extremeWingStatsDevDynRouteOspfAreaNumFullyAdjNbrs OBJECT-TYPE
			SYNTAX Unsigned32
			MAX-ACCESS read-only
			STATUS current
			DESCRIPTION
				"Number of fully adjacent neighbors in this area.
				
				XPath: /extremeWing-stats/device[mac=key1]/ospf_stats/ip_ospf_stats/ospf_area_stats[ospf_area_id=key2]/num_fully_adj_nbrs"
			::= { extremeWingStatsDevDynRouteOspfAreaEntry 14 }

		
		-- 1.3.6.1.4.1.1916.2.131.50.1.4.2.34.2.1.15
		extremeWingStatsDevDynRouteOspfAreaAuthType OBJECT-TYPE
			SYNTAX DisplayString
			MAX-ACCESS read-only
			STATUS current
			DESCRIPTION
				"Authentication type of OSPF area.
				
				XPath: /extremeWing-stats/device[mac=key1]/ospf_stats/ip_ospf_stats/ospf_area_stats[ospf_area_id=key2]/auth_type"
			::= { extremeWingStatsDevDynRouteOspfAreaEntry 15 }

		
		-- 1.3.6.1.4.1.1916.2.131.50.1.4.2.34.2.1.16
		extremeWingStatsDevDynRouteOspfAreaNumFullVirtualAdj OBJECT-TYPE
			SYNTAX Unsigned32
			MAX-ACCESS read-only
			STATUS current
			DESCRIPTION
				"Number of full virtual adjacencies going through this area.
				
				XPath: /extremeWing-stats/device[mac=key1]/ospf_stats/ip_ospf_stats/ospf_area_stats[ospf_area_id=key2]/num_full_virt_adj"
			::= { extremeWingStatsDevDynRouteOspfAreaEntry 16 }

		
		-- 1.3.6.1.4.1.1916.2.131.50.1.4.2.34.2.1.17
		extremeWingStatsDevDynRouteOspfAreaNumSpfExecuted OBJECT-TYPE
			SYNTAX Unsigned32
			MAX-ACCESS read-only
			STATUS current
			DESCRIPTION
				"Number of times SPF algorithm executed.
				
				XPath: /extremeWing-stats/device[mac=key1]/ospf_stats/ip_ospf_stats/ospf_area_stats[ospf_area_id=key2]/num_spf_executed"
			::= { extremeWingStatsDevDynRouteOspfAreaEntry 17 }

		
		-- 1.3.6.1.4.1.1916.2.131.50.1.4.2.34.2.1.18
		extremeWingStatsDevDynRouteOspfAreaNumTotalLsa OBJECT-TYPE
			SYNTAX Counter64
			MAX-ACCESS read-only
			STATUS current
			DESCRIPTION
				"Total nimber of LSAs.
				
				XPath: /extremeWing-stats/device[mac=key1]/ospf_stats/ip_ospf_stats/ospf_area_stats[ospf_area_id=key2]/num_total_lsa"
			::= { extremeWingStatsDevDynRouteOspfAreaEntry 18 }

		
		-- 1.3.6.1.4.1.1916.2.131.50.1.4.2.34.2.1.19
		extremeWingStatsDevDynRouteOspfAreaNumRouterLsa OBJECT-TYPE
			SYNTAX Counter64
			MAX-ACCESS read-only
			STATUS current
			DESCRIPTION
				"Number of router LSAs.
				
				XPath: /extremeWing-stats/device[mac=key1]/ospf_stats/ip_ospf_stats/ospf_area_stats[ospf_area_id=key2]/num_router_lsa"
			::= { extremeWingStatsDevDynRouteOspfAreaEntry 19 }

		
		-- 1.3.6.1.4.1.1916.2.131.50.1.4.2.34.2.1.20
		extremeWingStatsDevDynRouteOspfAreaRouterLsaCsum OBJECT-TYPE
			SYNTAX Unsigned32
			MAX-ACCESS read-only
			STATUS current
			DESCRIPTION
				"Router LSA checksum
				
				XPath: /extremeWing-stats/device[mac=key1]/ospf_stats/ip_ospf_stats/ospf_area_stats[ospf_area_id=key2]/router_lsa_csum"
			::= { extremeWingStatsDevDynRouteOspfAreaEntry 20 }

		
		-- 1.3.6.1.4.1.1916.2.131.50.1.4.2.34.2.1.21
		extremeWingStatsDevDynRouteOspfAreaNumNetworkLsa OBJECT-TYPE
			SYNTAX Counter64
			MAX-ACCESS read-only
			STATUS current
			DESCRIPTION
				"Number of network LSAs.
				
				XPath: /extremeWing-stats/device[mac=key1]/ospf_stats/ip_ospf_stats/ospf_area_stats[ospf_area_id=key2]/num_network_lsa"
			::= { extremeWingStatsDevDynRouteOspfAreaEntry 21 }

		
		-- 1.3.6.1.4.1.1916.2.131.50.1.4.2.34.2.1.22
		extremeWingStatsDevDynRouteOspfAreaNetworkLsaCsum OBJECT-TYPE
			SYNTAX Unsigned32
			MAX-ACCESS read-only
			STATUS current
			DESCRIPTION
				"Network LSA checksum.
				
				XPath: /extremeWing-stats/device[mac=key1]/ospf_stats/ip_ospf_stats/ospf_area_stats[ospf_area_id=key2]/network_lsa_csum"
			::= { extremeWingStatsDevDynRouteOspfAreaEntry 22 }

		
		-- 1.3.6.1.4.1.1916.2.131.50.1.4.2.34.2.1.23
		extremeWingStatsDevDynRouteOspfAreaNumSummaryLsa OBJECT-TYPE
			SYNTAX Counter64
			MAX-ACCESS read-only
			STATUS current
			DESCRIPTION
				"Number of summary LSAs.
				
				XPath: /extremeWing-stats/device[mac=key1]/ospf_stats/ip_ospf_stats/ospf_area_stats[ospf_area_id=key2]/num_summary_lsa"
			::= { extremeWingStatsDevDynRouteOspfAreaEntry 23 }

		
		-- 1.3.6.1.4.1.1916.2.131.50.1.4.2.34.2.1.24
		extremeWingStatsDevDynRouteOspfAreaSummaryLsaCsum OBJECT-TYPE
			SYNTAX Unsigned32
			MAX-ACCESS read-only
			STATUS current
			DESCRIPTION
				"Summary LSA checksum.
				
				XPath: /extremeWing-stats/device[mac=key1]/ospf_stats/ip_ospf_stats/ospf_area_stats[ospf_area_id=key2]/summary_lsa_csum"
			::= { extremeWingStatsDevDynRouteOspfAreaEntry 24 }

		
		-- 1.3.6.1.4.1.1916.2.131.50.1.4.2.34.2.1.25
		extremeWingStatsDevDynRouteOspfAreaNumAsbrSummaryLsa OBJECT-TYPE
			SYNTAX Counter64
			MAX-ACCESS read-only
			STATUS current
			DESCRIPTION
				"Number of ASBR LSAs.
				
				XPath: /extremeWing-stats/device[mac=key1]/ospf_stats/ip_ospf_stats/ospf_area_stats[ospf_area_id=key2]/num_asbr_summary_lsa"
			::= { extremeWingStatsDevDynRouteOspfAreaEntry 25 }

		
		-- 1.3.6.1.4.1.1916.2.131.50.1.4.2.34.2.1.26
		extremeWingStatsDevDynRouteOspfAreaAsbrSummaryLsaCsum OBJECT-TYPE
			SYNTAX Unsigned32
			MAX-ACCESS read-only
			STATUS current
			DESCRIPTION
				"ASBR LSA checksum.
				
				XPath: /extremeWing-stats/device[mac=key1]/ospf_stats/ip_ospf_stats/ospf_area_stats[ospf_area_id=key2]/asbr_summary_lsa_csum"
			::= { extremeWingStatsDevDynRouteOspfAreaEntry 26 }

		
		-- 1.3.6.1.4.1.1916.2.131.50.1.4.2.34.2.1.27
		extremeWingStatsDevDynRouteOspfAreaNumNssaLsa OBJECT-TYPE
			SYNTAX Counter64
			MAX-ACCESS read-only
			STATUS current
			DESCRIPTION
				"Number of NSSA LSAs.
				
				XPath: /extremeWing-stats/device[mac=key1]/ospf_stats/ip_ospf_stats/ospf_area_stats[ospf_area_id=key2]/num_nssa_lsa"
			::= { extremeWingStatsDevDynRouteOspfAreaEntry 27 }

		
		-- 1.3.6.1.4.1.1916.2.131.50.1.4.2.34.2.1.28
		extremeWingStatsDevDynRouteOspfAreaNssaLsaCsum OBJECT-TYPE
			SYNTAX Unsigned32
			MAX-ACCESS read-only
			STATUS current
			DESCRIPTION
				"NSSA LSA checksum.
				
				XPath: /extremeWing-stats/device[mac=key1]/ospf_stats/ip_ospf_stats/ospf_area_stats[ospf_area_id=key2]/nssa_lsa_csum"
			::= { extremeWingStatsDevDynRouteOspfAreaEntry 28 }

		
		-- 1.3.6.1.4.1.1916.2.131.50.1.4.2.34.2.1.29
		extremeWingStatsDevDynRouteOspfAreaNumOpaqueLinkLsa OBJECT-TYPE
			SYNTAX Counter64
			MAX-ACCESS read-only
			STATUS current
			DESCRIPTION
				"Number of opaque link LSAs.
				
				XPath: /extremeWing-stats/device[mac=key1]/ospf_stats/ip_ospf_stats/ospf_area_stats[ospf_area_id=key2]/num_opaque_link_lsa"
			::= { extremeWingStatsDevDynRouteOspfAreaEntry 29 }

		
		-- 1.3.6.1.4.1.1916.2.131.50.1.4.2.34.2.1.30
		extremeWingStatsDevDynRouteOspfAreaOpaqueLinkLsaCsum OBJECT-TYPE
			SYNTAX Unsigned32
			MAX-ACCESS read-only
			STATUS current
			DESCRIPTION
				"Opaque link LSA checksum.
				
				XPath: /extremeWing-stats/device[mac=key1]/ospf_stats/ip_ospf_stats/ospf_area_stats[ospf_area_id=key2]/opaque_link_lsa_csum"
			::= { extremeWingStatsDevDynRouteOspfAreaEntry 30 }

		
		-- 1.3.6.1.4.1.1916.2.131.50.1.4.2.34.2.1.31
		extremeWingStatsDevDynRouteOspfAreaNumOpaqueAreaLsa OBJECT-TYPE
			SYNTAX Counter64
			MAX-ACCESS read-only
			STATUS current
			DESCRIPTION
				"Number of opaque area LSAs.
				
				XPath: /extremeWing-stats/device[mac=key1]/ospf_stats/ip_ospf_stats/ospf_area_stats[ospf_area_id=key2]/num_opaque_area_lsa"
			::= { extremeWingStatsDevDynRouteOspfAreaEntry 31 }

		
		-- 1.3.6.1.4.1.1916.2.131.50.1.4.2.34.2.1.32
		extremeWingStatsDevDynRouteOspfAreaOpaqueAreaLsaCsum OBJECT-TYPE
			SYNTAX Unsigned32
			MAX-ACCESS read-only
			STATUS current
			DESCRIPTION
				"Opaque area LSA checksum.
				
				XPath: /extremeWing-stats/device[mac=key1]/ospf_stats/ip_ospf_stats/ospf_area_stats[ospf_area_id=key2]/opaque_area_lsa_csum"
			::= { extremeWingStatsDevDynRouteOspfAreaEntry 32 }

		
		-- 1.3.6.1.4.1.1916.2.131.50.1.4.2.34.3
		extremeWingStatsDevDynRouteIpOspfNetworkRoutesTable OBJECT-TYPE
			SYNTAX SEQUENCE OF ExtremeWingStatsDevDynRouteIpOspfNetworkRoutesEntry
			MAX-ACCESS not-accessible
			STATUS current
			DESCRIPTION
				"Description."
			::= { extremeWingStatsDevDynRoute 3 }

		
		-- 1.3.6.1.4.1.1916.2.131.50.1.4.2.34.3.1
		extremeWingStatsDevDynRouteIpOspfNetworkRoutesEntry OBJECT-TYPE
			SYNTAX ExtremeWingStatsDevDynRouteIpOspfNetworkRoutesEntry
			MAX-ACCESS not-accessible
			STATUS current
			DESCRIPTION
				"Description."
			INDEX { extremeWingStatsDevMac, extremeWingStatsDevDynRouteIpOspfNetworkRoute }
			::= { extremeWingStatsDevDynRouteIpOspfNetworkRoutesTable 1 }

		
		ExtremeWingStatsDevDynRouteIpOspfNetworkRoutesEntry ::=
			SEQUENCE { 
				extremeWingStatsDevDynRouteIpOspfNetworkRoute
					ExtremeWingIdentifier,
				extremeWingStatsDevDynRouteIpOspfNetworkRoutesPathType
					DisplayString,
				extremeWingStatsDevDynRouteIpOspfNetworkRoutesDestType
					DisplayString,
				extremeWingStatsDevDynRouteIpOspfNetworkRoutesCost
					Unsigned32,
				extremeWingStatsDevDynRouteIpOspfNetworkRoutesArea
					DisplayString
			 }

		-- 1.3.6.1.4.1.1916.2.131.50.1.4.2.34.3.1.1
		extremeWingStatsDevDynRouteIpOspfNetworkRoute OBJECT-TYPE
			SYNTAX ExtremeWingIdentifier
			MAX-ACCESS read-only
			STATUS current
			DESCRIPTION
				"Network represented in IP-Address/Mask format.
				
				XPath: /extremeWing-stats/device[mac=key1]/ospf_stats/network_routes[network=key2]/network"
			::= { extremeWingStatsDevDynRouteIpOspfNetworkRoutesEntry 1 }

		
		-- 1.3.6.1.4.1.1916.2.131.50.1.4.2.34.3.1.2
		extremeWingStatsDevDynRouteIpOspfNetworkRoutesPathType OBJECT-TYPE
			SYNTAX DisplayString
			MAX-ACCESS read-only
			STATUS current
			DESCRIPTION
				"Type of this OSPF network.
				
				XPath: /extremeWing-stats/device[mac=key1]/ospf_stats/network_routes[network=key2]/path_type"
			::= { extremeWingStatsDevDynRouteIpOspfNetworkRoutesEntry 2 }

		
		-- 1.3.6.1.4.1.1916.2.131.50.1.4.2.34.3.1.3
		extremeWingStatsDevDynRouteIpOspfNetworkRoutesDestType OBJECT-TYPE
			SYNTAX DisplayString
			MAX-ACCESS read-only
			STATUS current
			DESCRIPTION
				"Dest Type.
				
				XPath: /extremeWing-stats/device[mac=key1]/ospf_stats/network_routes[network=key2]/dest_type"
			::= { extremeWingStatsDevDynRouteIpOspfNetworkRoutesEntry 3 }

		
		-- 1.3.6.1.4.1.1916.2.131.50.1.4.2.34.3.1.4
		extremeWingStatsDevDynRouteIpOspfNetworkRoutesCost OBJECT-TYPE
			SYNTAX Unsigned32
			MAX-ACCESS read-only
			STATUS current
			DESCRIPTION
				"Cost of this OSPF network.
				
				XPath: /extremeWing-stats/device[mac=key1]/ospf_stats/network_routes[network=key2]/cost"
			::= { extremeWingStatsDevDynRouteIpOspfNetworkRoutesEntry 4 }

		
		-- 1.3.6.1.4.1.1916.2.131.50.1.4.2.34.3.1.5
		extremeWingStatsDevDynRouteIpOspfNetworkRoutesArea OBJECT-TYPE
			SYNTAX DisplayString
			MAX-ACCESS read-only
			STATUS current
			DESCRIPTION
				"Routes Area.
				
				XPath: /extremeWing-stats/device[mac=key1]/ospf_stats/network_routes[network=key2]/area"
			::= { extremeWingStatsDevDynRouteIpOspfNetworkRoutesEntry 5 }

		
		-- 1.3.6.1.4.1.1916.2.131.50.1.4.2.34.4
		extremeWingStatsDevDynRouteIpOspfNetworkRoutesMPathsTable OBJECT-TYPE
			SYNTAX SEQUENCE OF ExtremeWingStatsDevDynRouteIpOspfNetworkRoutesMPathsEntry
			MAX-ACCESS not-accessible
			STATUS current
			DESCRIPTION
				"Description."
			::= { extremeWingStatsDevDynRoute 4 }

		
		-- 1.3.6.1.4.1.1916.2.131.50.1.4.2.34.4.1
		extremeWingStatsDevDynRouteIpOspfNetworkRoutesMPathsEntry OBJECT-TYPE
			SYNTAX ExtremeWingStatsDevDynRouteIpOspfNetworkRoutesMPathsEntry
			MAX-ACCESS not-accessible
			STATUS current
			DESCRIPTION
				"Description."
			INDEX { extremeWingStatsDevMac, extremeWingStatsDevDynRouteIpOspfNetworkRoute, extremeWingStatsDevDynRouteIpOspfNetworkRoutesMPathsIndex }
			::= { extremeWingStatsDevDynRouteIpOspfNetworkRoutesMPathsTable 1 }

		
		ExtremeWingStatsDevDynRouteIpOspfNetworkRoutesMPathsEntry ::=
			SEQUENCE { 
				extremeWingStatsDevDynRouteIpOspfNetworkRoutesMPathsIndex
					Unsigned32,
				extremeWingStatsDevDynRouteIpOspfNetworkRoutesAttachedFlags
					TruthValue,
				extremeWingStatsDevDynRouteIpOspfNetworkRoutesIfName
					DisplayString,
				extremeWingStatsDevDynRouteIpOspfNetworkRoutesNextHop
					DisplayString
			 }

		-- 1.3.6.1.4.1.1916.2.131.50.1.4.2.34.4.1.1
		extremeWingStatsDevDynRouteIpOspfNetworkRoutesMPathsIndex OBJECT-TYPE
			SYNTAX Unsigned32 (1..4294967295)
			MAX-ACCESS read-only
			STATUS current
			DESCRIPTION
				"Network routes multipath table index.
				
				XPath: /extremeWing-stats/device[mac=key1]/ospf_stats/network_routes[network=key2]/multipaths[m_path_index=key3]/m_path_index"
			::= { extremeWingStatsDevDynRouteIpOspfNetworkRoutesMPathsEntry 1 }

		
		-- 1.3.6.1.4.1.1916.2.131.50.1.4.2.34.4.1.2
		extremeWingStatsDevDynRouteIpOspfNetworkRoutesAttachedFlags OBJECT-TYPE
			SYNTAX TruthValue
			MAX-ACCESS read-only
			STATUS current
			DESCRIPTION
				"Whether the network is directly connected or not
				
				XPath: /extremeWing-stats/device[mac=key1]/ospf_stats/network_routes[network=key2]/multipaths[m_path_index=key3]/attached_flag"
			::= { extremeWingStatsDevDynRouteIpOspfNetworkRoutesMPathsEntry 2 }

		
		-- 1.3.6.1.4.1.1916.2.131.50.1.4.2.34.4.1.3
		extremeWingStatsDevDynRouteIpOspfNetworkRoutesIfName OBJECT-TYPE
			SYNTAX DisplayString
			MAX-ACCESS read-only
			STATUS current
			DESCRIPTION
				"Name of the interface to which the network is attached.
				
				XPath: /extremeWing-stats/device[mac=key1]/ospf_stats/network_routes[network=key2]/multipaths[m_path_index=key3]/ifname"
			::= { extremeWingStatsDevDynRouteIpOspfNetworkRoutesMPathsEntry 3 }

		
		-- 1.3.6.1.4.1.1916.2.131.50.1.4.2.34.4.1.4
		extremeWingStatsDevDynRouteIpOspfNetworkRoutesNextHop OBJECT-TYPE
			SYNTAX DisplayString
			MAX-ACCESS read-only
			STATUS current
			DESCRIPTION
				"Next hop through which the network is reachable.
				
				XPath: /extremeWing-stats/device[mac=key1]/ospf_stats/network_routes[network=key2]/multipaths[m_path_index=key3]/next_hop"
			::= { extremeWingStatsDevDynRouteIpOspfNetworkRoutesMPathsEntry 4 }

		
		-- 1.3.6.1.4.1.1916.2.131.50.1.4.2.34.5
		extremeWingStatsDevDynRouteIpOspfRouterRoutesTable OBJECT-TYPE
			SYNTAX SEQUENCE OF ExtremeWingStatsDevDynRouteIpOspfRouterRoutesEntry
			MAX-ACCESS not-accessible
			STATUS current
			DESCRIPTION
				"Description."
			::= { extremeWingStatsDevDynRoute 5 }

		
		-- 1.3.6.1.4.1.1916.2.131.50.1.4.2.34.5.1
		extremeWingStatsDevDynRouteIpOspfRouterRoutesEntry OBJECT-TYPE
			SYNTAX ExtremeWingStatsDevDynRouteIpOspfRouterRoutesEntry
			MAX-ACCESS not-accessible
			STATUS current
			DESCRIPTION
				"Description."
			INDEX { extremeWingCfgDevMac, extremeWingStatsDevDynRouteIpOspfRouterRoute }
			::= { extremeWingStatsDevDynRouteIpOspfRouterRoutesTable 1 }

		
		ExtremeWingStatsDevDynRouteIpOspfRouterRoutesEntry ::=
			SEQUENCE { 
				extremeWingStatsDevDynRouteIpOspfRouterRoute
					ExtremeWingIdentifier
			 }

		-- 1.3.6.1.4.1.1916.2.131.50.1.4.2.34.5.1.1
		extremeWingStatsDevDynRouteIpOspfRouterRoute OBJECT-TYPE
			SYNTAX ExtremeWingIdentifier
			MAX-ACCESS read-only
			STATUS current
			DESCRIPTION
				"Router IP address.
				
				XPath: /extremeWing-stats/device[mac=key1]/ospf_stats/router_routes[router=key2]/router
				"
			::= { extremeWingStatsDevDynRouteIpOspfRouterRoutesEntry 1 }

		
		-- 1.3.6.1.4.1.1916.2.131.50.1.4.2.34.6
		extremeWingStatsDevDynRouteIpOspfRouterRoutesInfoTable OBJECT-TYPE
			SYNTAX SEQUENCE OF ExtremeWingStatsDevDynRouteIpOspfRouterRoutesInfoEntry
			MAX-ACCESS not-accessible
			STATUS current
			DESCRIPTION
				"Description."
			::= { extremeWingStatsDevDynRoute 6 }

		
		-- 1.3.6.1.4.1.1916.2.131.50.1.4.2.34.6.1
		extremeWingStatsDevDynRouteIpOspfRouterRoutesInfoEntry OBJECT-TYPE
			SYNTAX ExtremeWingStatsDevDynRouteIpOspfRouterRoutesInfoEntry
			MAX-ACCESS not-accessible
			STATUS current
			DESCRIPTION
				"Description."
			INDEX { extremeWingStatsDevMac, extremeWingStatsDevDynRouteIpOspfRouterRoute, extremeWingStatsDevDynRouteIpOspfRouterRoutesInfoIndex }
			::= { extremeWingStatsDevDynRouteIpOspfRouterRoutesInfoTable 1 }

		
		ExtremeWingStatsDevDynRouteIpOspfRouterRoutesInfoEntry ::=
			SEQUENCE { 
				extremeWingStatsDevDynRouteIpOspfRouterRoutesInfoIndex
					Unsigned32,
				extremeWingStatsDevDynRouteIpOspfRouterRoutePathType
					DisplayString,
				extremeWingStatsDevDynRouteIpOspfRouterRouteArea
					DisplayString,
				extremeWingStatsDevDynRouteIpOspfRouterRouteCost
					Unsigned32,
				extremeWingStatsDevDynRouteIpOspfRouterRouteFlags
					DisplayString,
				extremeWingStatsDevDynRouteIpOspfRouterRouteAttachedFlag
					TruthValue,
				extremeWingStatsDevDynRouteIpOspfRouterRouteIfName
					DisplayString,
				extremeWingStatsDevDynRouteIpOspfRouterRouteNextHop
					DisplayString
			 }

		-- 1.3.6.1.4.1.1916.2.131.50.1.4.2.34.6.1.1
		extremeWingStatsDevDynRouteIpOspfRouterRoutesInfoIndex OBJECT-TYPE
			SYNTAX Unsigned32 (1..4294967295)
			MAX-ACCESS read-only
			STATUS current
			DESCRIPTION
				"Router Information table index.
				
				XPath: /extremeWing-stats/device[mac=key1]/ospf_stats/router_routes[router=key2]/route_info_nodes[route_node_index=key3]/route_node_index"
			::= { extremeWingStatsDevDynRouteIpOspfRouterRoutesInfoEntry 1 }

		
		-- 1.3.6.1.4.1.1916.2.131.50.1.4.2.34.6.1.2
		extremeWingStatsDevDynRouteIpOspfRouterRoutePathType OBJECT-TYPE
			SYNTAX DisplayString
			MAX-ACCESS read-only
			STATUS current
			DESCRIPTION
				"Type of this OSPF route.
				
				XPath: /extremeWing-stats/device[mac=key1]/ospf_stats/router_routes[router=key2]/route_info_nodes[route_node_index=key3]/path_type"
			::= { extremeWingStatsDevDynRouteIpOspfRouterRoutesInfoEntry 2 }

		
		-- 1.3.6.1.4.1.1916.2.131.50.1.4.2.34.6.1.3
		extremeWingStatsDevDynRouteIpOspfRouterRouteArea OBJECT-TYPE
			SYNTAX DisplayString
			MAX-ACCESS read-only
			STATUS current
			DESCRIPTION
				"Area ID this OSPF router belongs to.
				
				XPath: /extremeWing-stats/device[mac=key1]/ospf_stats/router_routes[router=key2]/route_info_nodes[route_node_index=key3]/area"
			::= { extremeWingStatsDevDynRouteIpOspfRouterRoutesInfoEntry 3 }

		
		-- 1.3.6.1.4.1.1916.2.131.50.1.4.2.34.6.1.4
		extremeWingStatsDevDynRouteIpOspfRouterRouteCost OBJECT-TYPE
			SYNTAX Unsigned32
			MAX-ACCESS read-only
			STATUS current
			DESCRIPTION
				"Cost of this OSPF route.
				
				XPath: /extremeWing-stats/device[mac=key1]/ospf_stats/router_routes[router=key2]/route_info_nodes[route_node_index=key3]/cost"
			::= { extremeWingStatsDevDynRouteIpOspfRouterRoutesInfoEntry 4 }

		
		-- 1.3.6.1.4.1.1916.2.131.50.1.4.2.34.6.1.5
		extremeWingStatsDevDynRouteIpOspfRouterRouteFlags OBJECT-TYPE
			SYNTAX DisplayString
			MAX-ACCESS read-only
			STATUS current
			DESCRIPTION
				"OSPF Router LSA Flags.
				
				XPath: /extremeWing-stats/device[mac=key1]/ospf_stats/router_routes[router=key2]/route_info_nodes[route_node_index=key3]/flags"
			::= { extremeWingStatsDevDynRouteIpOspfRouterRoutesInfoEntry 5 }

		
		-- 1.3.6.1.4.1.1916.2.131.50.1.4.2.34.6.1.6
		extremeWingStatsDevDynRouteIpOspfRouterRouteAttachedFlag OBJECT-TYPE
			SYNTAX TruthValue
			MAX-ACCESS read-only
			STATUS current
			DESCRIPTION
				"Whether the network is directly connected or not.
				
				XPath: /extremeWing-stats/device[mac=key1]/ospf_stats/router_routes[router=key2]/route_info_nodes[route_node_index=key3]/attached_flag
				
				"
			::= { extremeWingStatsDevDynRouteIpOspfRouterRoutesInfoEntry 6 }

		
		-- 1.3.6.1.4.1.1916.2.131.50.1.4.2.34.6.1.7
		extremeWingStatsDevDynRouteIpOspfRouterRouteIfName OBJECT-TYPE
			SYNTAX DisplayString
			MAX-ACCESS read-only
			STATUS current
			DESCRIPTION
				"Name of the interface to which the network is attached.
				
				XPath: /extremeWing-stats/device[mac=key1]/ospf_stats/router_routes[router=key2]/route_info_nodes[route_node_index=key3]/ifname"
			::= { extremeWingStatsDevDynRouteIpOspfRouterRoutesInfoEntry 7 }

		
		-- 1.3.6.1.4.1.1916.2.131.50.1.4.2.34.6.1.8
		extremeWingStatsDevDynRouteIpOspfRouterRouteNextHop OBJECT-TYPE
			SYNTAX DisplayString
			MAX-ACCESS read-only
			STATUS current
			DESCRIPTION
				"Next hop through which the network is reachable.
				
				XPath: /extremeWing-stats/device[mac=key1]/ospf_stats/router_routes[router=key2]/route_info_nodes[route_node_index=key3]/next_hop"
			::= { extremeWingStatsDevDynRouteIpOspfRouterRoutesInfoEntry 8 }

		
		-- 1.3.6.1.4.1.1916.2.131.50.1.4.2.34.7
		extremeWingstatsDevDynRouteIpOspfExtRoutesTable OBJECT-TYPE
			SYNTAX SEQUENCE OF ExtremeWingstatsDevDynRouteIpOspfExtRoutesEntry
			MAX-ACCESS not-accessible
			STATUS current
			DESCRIPTION
				"Description."
			::= { extremeWingStatsDevDynRoute 7 }

		
		-- 1.3.6.1.4.1.1916.2.131.50.1.4.2.34.7.1
		extremeWingstatsDevDynRouteIpOspfExtRoutesEntry OBJECT-TYPE
			SYNTAX ExtremeWingstatsDevDynRouteIpOspfExtRoutesEntry
			MAX-ACCESS not-accessible
			STATUS current
			DESCRIPTION
				"Description."
			INDEX { extremeWingStatsDevMac, extremeWingstatsDevDynRouteIpOspfExtRoute }
			::= { extremeWingstatsDevDynRouteIpOspfExtRoutesTable 1 }

		
		ExtremeWingstatsDevDynRouteIpOspfExtRoutesEntry ::=
			SEQUENCE { 
				extremeWingstatsDevDynRouteIpOspfExtRoute
					ExtremeWingIdentifier,
				extremeWingstatsDevDynRouteIpOspfExtRoutePathType
					DisplayString,
				extremeWingstatsDevDynRouteIpOspfExtRouteArea
					DisplayString,
				extremeWingstatsDevDynRouteIpOspfExtRouteCost
					Unsigned32,
				extremeWingstatsDevDynRouteIpOspfExtRouteType2Cost
					Unsigned32,
				extremeWingstatsDevDynRouteIpOspfExtRouteTag
					Unsigned32
			 }

		-- 1.3.6.1.4.1.1916.2.131.50.1.4.2.34.7.1.1
		extremeWingstatsDevDynRouteIpOspfExtRoute OBJECT-TYPE
			SYNTAX ExtremeWingIdentifier
			MAX-ACCESS read-only
			STATUS current
			DESCRIPTION
				"External OSPF route.
				
				XPath: /extremeWing-stats/device[mac=key1]/ospf_stats/external_routes[ext_route=key2]/ext_route"
			::= { extremeWingstatsDevDynRouteIpOspfExtRoutesEntry 1 }

		
		-- 1.3.6.1.4.1.1916.2.131.50.1.4.2.34.7.1.2
		extremeWingstatsDevDynRouteIpOspfExtRoutePathType OBJECT-TYPE
			SYNTAX DisplayString
			MAX-ACCESS read-only
			STATUS current
			DESCRIPTION
				"Type of this OSPF network.
				
				XPath: /extremeWing-stats/device[mac=key1]/ospf_stats/external_routes[ext_route=key2]/path_type"
			::= { extremeWingstatsDevDynRouteIpOspfExtRoutesEntry 2 }

		
		-- 1.3.6.1.4.1.1916.2.131.50.1.4.2.34.7.1.3
		extremeWingstatsDevDynRouteIpOspfExtRouteArea OBJECT-TYPE
			SYNTAX DisplayString
			MAX-ACCESS read-only
			STATUS current
			DESCRIPTION
				"Area ID this OSPF network belongs to.
				
				XPath: /extremeWing-stats/device[mac=key1]/ospf_stats/external_routes[ext_route=key2]/area"
			::= { extremeWingstatsDevDynRouteIpOspfExtRoutesEntry 3 }

		
		-- 1.3.6.1.4.1.1916.2.131.50.1.4.2.34.7.1.4
		extremeWingstatsDevDynRouteIpOspfExtRouteCost OBJECT-TYPE
			SYNTAX Unsigned32
			MAX-ACCESS read-only
			STATUS current
			DESCRIPTION
				"Cost of this OSPF external route.
				
				XPath: /extremeWing-stats/device[mac=key1]/ospf_stats/external_routes[ext_route=key2]/cost"
			::= { extremeWingstatsDevDynRouteIpOspfExtRoutesEntry 4 }

		
		-- 1.3.6.1.4.1.1916.2.131.50.1.4.2.34.7.1.5
		extremeWingstatsDevDynRouteIpOspfExtRouteType2Cost OBJECT-TYPE
			SYNTAX Unsigned32
			MAX-ACCESS read-only
			STATUS current
			DESCRIPTION
				"Cost of this type 2 OSPF route.
				
				XPath: /extremeWing-stats/device[mac=key1]/ospf_stats/external_routes[ext_route=key2]/type_2_cost"
			::= { extremeWingstatsDevDynRouteIpOspfExtRoutesEntry 5 }

		
		-- 1.3.6.1.4.1.1916.2.131.50.1.4.2.34.7.1.6
		extremeWingstatsDevDynRouteIpOspfExtRouteTag OBJECT-TYPE
			SYNTAX Unsigned32
			MAX-ACCESS read-only
			STATUS current
			DESCRIPTION
				"Tag of external route.
				
				XPath: /extremeWing-stats/device[mac=key1]/ospf_stats/external_routes[ext_route=key2]/tag"
			::= { extremeWingstatsDevDynRouteIpOspfExtRoutesEntry 6 }

		
		-- 1.3.6.1.4.1.1916.2.131.50.1.4.2.34.8
		extremeWingstatsDevDynRouteIpOspfExtRoutesMPathsTable OBJECT-TYPE
			SYNTAX SEQUENCE OF ExtremeWingstatsDevDynRouteIpOspfExtRoutesMPathsEntry
			MAX-ACCESS not-accessible
			STATUS current
			DESCRIPTION
				"Description."
			::= { extremeWingStatsDevDynRoute 8 }

		
		-- 1.3.6.1.4.1.1916.2.131.50.1.4.2.34.8.1
		extremeWingstatsDevDynRouteIpOspfExtRoutesMPathsEntry OBJECT-TYPE
			SYNTAX ExtremeWingstatsDevDynRouteIpOspfExtRoutesMPathsEntry
			MAX-ACCESS not-accessible
			STATUS current
			DESCRIPTION
				"Description."
			INDEX { extremeWingStatsDevMac, extremeWingstatsDevDynRouteIpOspfExtRoute, extremeWingstatsDevDynRouteIpOspfExtRoutesMPathsIndex }
			::= { extremeWingstatsDevDynRouteIpOspfExtRoutesMPathsTable 1 }

		
		ExtremeWingstatsDevDynRouteIpOspfExtRoutesMPathsEntry ::=
			SEQUENCE { 
				extremeWingstatsDevDynRouteIpOspfExtRoutesMPathsIndex
					Unsigned32,
				extremeWingstatsDevDynRouteIpOspfExtRouteAttachedFlag
					TruthValue,
				extremeWingstatsDevDynRouteIpOspfExtRouteIfName
					DisplayString,
				extremeWingstatsDevDynRouteIpOspfExtRouteNextHop
					DisplayString
			 }

		-- 1.3.6.1.4.1.1916.2.131.50.1.4.2.34.8.1.1
		extremeWingstatsDevDynRouteIpOspfExtRoutesMPathsIndex OBJECT-TYPE
			SYNTAX Unsigned32 (1..4294967295)
			MAX-ACCESS read-only
			STATUS current
			DESCRIPTION
				"External routes multipath table index.
				
				XPath: /extremeWing-stats/device[mac=key1]/ospf_stats/external_routes[ext_route=key2]/multipaths[m_path_index=key3]/m_path_index
				"
			::= { extremeWingstatsDevDynRouteIpOspfExtRoutesMPathsEntry 1 }

		
		-- 1.3.6.1.4.1.1916.2.131.50.1.4.2.34.8.1.2
		extremeWingstatsDevDynRouteIpOspfExtRouteAttachedFlag OBJECT-TYPE
			SYNTAX TruthValue
			MAX-ACCESS read-only
			STATUS current
			DESCRIPTION
				"Whether the network is directly connected or not.
				
				XPath: /extremeWing-stats/device[mac=key1]/ospf_stats/external_routes[ext_route=key2]/multipaths[m_path_index=key3]/attached_flag"
			::= { extremeWingstatsDevDynRouteIpOspfExtRoutesMPathsEntry 2 }

		
		-- 1.3.6.1.4.1.1916.2.131.50.1.4.2.34.8.1.3
		extremeWingstatsDevDynRouteIpOspfExtRouteIfName OBJECT-TYPE
			SYNTAX DisplayString
			MAX-ACCESS read-only
			STATUS current
			DESCRIPTION
				"Name of the interface to which the network is attached.
				
				XPath: /extremeWing-stats/device[mac=key1]/ospf_stats/external_routes[ext_route=key2]/multipaths[m_path_index=key3]/ifname"
			::= { extremeWingstatsDevDynRouteIpOspfExtRoutesMPathsEntry 3 }

		
		-- 1.3.6.1.4.1.1916.2.131.50.1.4.2.34.8.1.4
		extremeWingstatsDevDynRouteIpOspfExtRouteNextHop OBJECT-TYPE
			SYNTAX DisplayString
			MAX-ACCESS read-only
			STATUS current
			DESCRIPTION
				"Next hop through which the network is reachable.
				
				XPath: /extremeWing-stats/device[mac=key1]/ospf_stats/external_routes[ext_route=key2]/multipaths[m_path_index=key3]/next_hop"
			::= { extremeWingstatsDevDynRouteIpOspfExtRoutesMPathsEntry 4 }

		
		-- 1.3.6.1.4.1.1916.2.131.50.1.4.2.34.9
		extremeWingStatsDevDynRouteBorderRoutersTable OBJECT-TYPE
			SYNTAX SEQUENCE OF ExtremeWingStatsDevDynRouteBorderRoutersEntry
			MAX-ACCESS not-accessible
			STATUS current
			DESCRIPTION
				"Description."
			::= { extremeWingStatsDevDynRoute 9 }

		
		-- 1.3.6.1.4.1.1916.2.131.50.1.4.2.34.9.1
		extremeWingStatsDevDynRouteBorderRoutersEntry OBJECT-TYPE
			SYNTAX ExtremeWingStatsDevDynRouteBorderRoutersEntry
			MAX-ACCESS not-accessible
			STATUS current
			DESCRIPTION
				"Description."
			INDEX { extremeWingStatsDevMac, extremeWingStatsDevDynRouteBorderRouter }
			::= { extremeWingStatsDevDynRouteBorderRoutersTable 1 }

		
		ExtremeWingStatsDevDynRouteBorderRoutersEntry ::=
			SEQUENCE { 
				extremeWingStatsDevDynRouteBorderRouter
					ExtremeWingIdentifier
			 }

		-- 1.3.6.1.4.1.1916.2.131.50.1.4.2.34.9.1.1
		extremeWingStatsDevDynRouteBorderRouter OBJECT-TYPE
			SYNTAX ExtremeWingIdentifier
			MAX-ACCESS read-only
			STATUS current
			DESCRIPTION
				"Router IP address.
				
				XPath: /extremeWing-stats/device[mac=key1]/ospf_stats/border_routers[router=key2]/router"
			::= { extremeWingStatsDevDynRouteBorderRoutersEntry 1 }

		
		-- 1.3.6.1.4.1.1916.2.131.50.1.4.2.34.10
		extremeWingStatsDevDynRouteBorderRoutersInfoTable OBJECT-TYPE
			SYNTAX SEQUENCE OF ExtremeWingStatsDevDynRouteBorderRoutersInfoEntry
			MAX-ACCESS not-accessible
			STATUS current
			DESCRIPTION
				"Description."
			::= { extremeWingStatsDevDynRoute 10 }

		
		-- 1.3.6.1.4.1.1916.2.131.50.1.4.2.34.10.1
		extremeWingStatsDevDynRouteBorderRoutersInfoEntry OBJECT-TYPE
			SYNTAX ExtremeWingStatsDevDynRouteBorderRoutersInfoEntry
			MAX-ACCESS not-accessible
			STATUS current
			DESCRIPTION
				"Description."
			INDEX { extremeWingStatsDevMac, extremeWingStatsDevDynRouteBorderRouter, extremeWingStatsDevDynRouteBorderRoutersInfoIndex }
			::= { extremeWingStatsDevDynRouteBorderRoutersInfoTable 1 }

		
		ExtremeWingStatsDevDynRouteBorderRoutersInfoEntry ::=
			SEQUENCE { 
				extremeWingStatsDevDynRouteBorderRoutersInfoIndex
					Unsigned32,
				extremeWingStatsDevDynRouteBorderRouterPathType
					DisplayString,
				extremeWingStatsDevDynRouteBorderRouterArea
					DisplayString,
				extremeWingStatsDevDynRouteBorderRouterCost
					Unsigned32,
				extremeWingStatsDevDynRouteBorderRouterFlags
					DisplayString,
				extremeWingStatsDevDynRouteBorderRouterAttachedFlag
					TruthValue,
				extremeWingStatsDevDynRouteBorderRouterIfName
					DisplayString,
				extremeWingStatsDevDynRouteBorderRouterNextHop
					DisplayString
			 }

		-- 1.3.6.1.4.1.1916.2.131.50.1.4.2.34.10.1.1
		extremeWingStatsDevDynRouteBorderRoutersInfoIndex OBJECT-TYPE
			SYNTAX Unsigned32 (1..4294967295)
			MAX-ACCESS read-only
			STATUS current
			DESCRIPTION
				"Router Information table index.
				
				XPath: /extremeWing-stats/device[mac=key1]/ospf_stats/border_routers[router=key2]/route_info_nodes[route_node_index=key3]/route_node_index"
			::= { extremeWingStatsDevDynRouteBorderRoutersInfoEntry 1 }

		
		-- 1.3.6.1.4.1.1916.2.131.50.1.4.2.34.10.1.2
		extremeWingStatsDevDynRouteBorderRouterPathType OBJECT-TYPE
			SYNTAX DisplayString
			MAX-ACCESS read-only
			STATUS current
			DESCRIPTION
				"Type of this OSPF route
				
				XPath: /extremeWing-stats/device[mac=key1]/ospf_stats/border_routers[router=key2]/route_info_nodes[route_node_index=key3]/path_type"
			::= { extremeWingStatsDevDynRouteBorderRoutersInfoEntry 2 }

		
		-- 1.3.6.1.4.1.1916.2.131.50.1.4.2.34.10.1.3
		extremeWingStatsDevDynRouteBorderRouterArea OBJECT-TYPE
			SYNTAX DisplayString
			MAX-ACCESS read-only
			STATUS current
			DESCRIPTION
				"Area ID this OSPF router belongs to.
				
				XPath: /extremeWing-stats/device[mac=key1]/ospf_stats/border_routers[router=key2]/route_info_nodes[route_node_index=key3]/area"
			::= { extremeWingStatsDevDynRouteBorderRoutersInfoEntry 3 }

		
		-- 1.3.6.1.4.1.1916.2.131.50.1.4.2.34.10.1.4
		extremeWingStatsDevDynRouteBorderRouterCost OBJECT-TYPE
			SYNTAX Unsigned32
			MAX-ACCESS read-only
			STATUS current
			DESCRIPTION
				"Cost of this OSPF route.
				
				XPath: /extremeWing-stats/device[mac=key1]/ospf_stats/border_routers[router=key2]/route_info_nodes[route_node_index=key3]/cost"
			::= { extremeWingStatsDevDynRouteBorderRoutersInfoEntry 4 }

		
		-- 1.3.6.1.4.1.1916.2.131.50.1.4.2.34.10.1.5
		extremeWingStatsDevDynRouteBorderRouterFlags OBJECT-TYPE
			SYNTAX DisplayString
			MAX-ACCESS read-only
			STATUS current
			DESCRIPTION
				"OSPF Router LSA Flags.
				
				XPath: /extremeWing-stats/device[mac=key1]/ospf_stats/border_routers[router=key2]/route_info_nodes[route_node_index=key3]/flags"
			::= { extremeWingStatsDevDynRouteBorderRoutersInfoEntry 5 }

		
		-- 1.3.6.1.4.1.1916.2.131.50.1.4.2.34.10.1.6
		extremeWingStatsDevDynRouteBorderRouterAttachedFlag OBJECT-TYPE
			SYNTAX TruthValue
			MAX-ACCESS read-only
			STATUS current
			DESCRIPTION
				"Whether the network is directly connected or not.
				
				XPath: /extremeWing-stats/device[mac=key1]/ospf_stats/border_routers[router=key2]/route_info_nodes[route_node_index=key3]/attached_flag"
			::= { extremeWingStatsDevDynRouteBorderRoutersInfoEntry 6 }

		
		-- 1.3.6.1.4.1.1916.2.131.50.1.4.2.34.10.1.7
		extremeWingStatsDevDynRouteBorderRouterIfName OBJECT-TYPE
			SYNTAX DisplayString
			MAX-ACCESS read-only
			STATUS current
			DESCRIPTION
				"Name of the interface to which the network is attached
				
				XPath: /extremeWing-stats/device[mac=key1]/ospf_stats/border_routers[router=key2]/route_info_nodes[route_node_index=key3]/ifname"
			::= { extremeWingStatsDevDynRouteBorderRoutersInfoEntry 7 }

		
		-- 1.3.6.1.4.1.1916.2.131.50.1.4.2.34.10.1.8
		extremeWingStatsDevDynRouteBorderRouterNextHop OBJECT-TYPE
			SYNTAX DisplayString
			MAX-ACCESS read-only
			STATUS current
			DESCRIPTION
				"Next hop through which the network is reachable.
				
				XPath: /extremeWing-stats/device[mac=key1]/ospf_stats/border_routers[router=key2]/route_info_nodes[route_node_index=key3]/next_hop"
			::= { extremeWingStatsDevDynRouteBorderRoutersInfoEntry 8 }

		
		-- 1.3.6.1.4.1.1916.2.131.50.1.4.2.34.11
		extremeWingStatsDevDynRouteOspfIfTable OBJECT-TYPE
			SYNTAX SEQUENCE OF ExtremeWingStatsDevDynRouteOspfIfEntry
			MAX-ACCESS not-accessible
			STATUS current
			DESCRIPTION
				"Description."
			::= { extremeWingStatsDevDynRoute 11 }

		
		-- 1.3.6.1.4.1.1916.2.131.50.1.4.2.34.11.1
		extremeWingStatsDevDynRouteOspfIfEntry OBJECT-TYPE
			SYNTAX ExtremeWingStatsDevDynRouteOspfIfEntry
			MAX-ACCESS not-accessible
			STATUS current
			DESCRIPTION
				"Description."
			INDEX { extremeWingStatsDevMac, extremeWingStatsDevDynRouteOspfIfName }
			::= { extremeWingStatsDevDynRouteOspfIfTable 1 }

		
		ExtremeWingStatsDevDynRouteOspfIfEntry ::=
			SEQUENCE { 
				extremeWingStatsDevDynRouteOspfIfName
					ExtremeWingIdentifier,
				extremeWingStatsDevDynRouteOspfIfStatusFlag
					TruthValue,
				extremeWingStatsDevDynRouteOspfIfIndex
					Unsigned32,
				extremeWingStatsDevDynRouteOspfIfMtu
					Unsigned32,
				extremeWingStatsDevDynRouteOspfIfBandwidth
					Unsigned32,
				extremeWingStatsDevDynRouteOspfIfFlags
					Counter64,
				extremeWingStatsDevDynRouteOspfIfEnabled
					TruthValue
			 }

		-- 1.3.6.1.4.1.1916.2.131.50.1.4.2.34.11.1.1
		extremeWingStatsDevDynRouteOspfIfName OBJECT-TYPE
			SYNTAX ExtremeWingIdentifier
			MAX-ACCESS read-only
			STATUS current
			DESCRIPTION
				"Interface Name.
				
				XPath: /extremeWing-stats/device[mac=key1]/ospf_stats/ospf_if[ifname=key2]/ifname"
			::= { extremeWingStatsDevDynRouteOspfIfEntry 1 }

		
		-- 1.3.6.1.4.1.1916.2.131.50.1.4.2.34.11.1.2
		extremeWingStatsDevDynRouteOspfIfStatusFlag OBJECT-TYPE
			SYNTAX TruthValue
			MAX-ACCESS read-only
			STATUS current
			DESCRIPTION
				"Whether interface is up or down.
				
				XPath: /extremeWing-stats/device[mac=key1]/ospf_stats/ospf_if[ifname=key2]/up_dn_flag"
			::= { extremeWingStatsDevDynRouteOspfIfEntry 2 }

		
		-- 1.3.6.1.4.1.1916.2.131.50.1.4.2.34.11.1.3
		extremeWingStatsDevDynRouteOspfIfIndex OBJECT-TYPE
			SYNTAX Unsigned32
			MAX-ACCESS read-only
			STATUS current
			DESCRIPTION
				"Interface index.
				
				XPath: /extremeWing-stats/device[mac=key1]/ospf_stats/ospf_if[ifname=key2]/ifindex"
			::= { extremeWingStatsDevDynRouteOspfIfEntry 3 }

		
		-- 1.3.6.1.4.1.1916.2.131.50.1.4.2.34.11.1.4
		extremeWingStatsDevDynRouteOspfIfMtu OBJECT-TYPE
			SYNTAX Unsigned32
			MAX-ACCESS read-only
			STATUS current
			DESCRIPTION
				"Size of MTU of this interface in bytes.
				
				XPath: /extremeWing-stats/device[mac=key1]/ospf_stats/ospf_if[ifname=key2]/mtu"
			::= { extremeWingStatsDevDynRouteOspfIfEntry 4 }

		
		-- 1.3.6.1.4.1.1916.2.131.50.1.4.2.34.11.1.5
		extremeWingStatsDevDynRouteOspfIfBandwidth OBJECT-TYPE
			SYNTAX Unsigned32
			MAX-ACCESS read-only
			STATUS current
			DESCRIPTION
				"Bandwidth of this interface in Kbits.
				
				XPath: /extremeWing-stats/device[mac=key1]/ospf_stats/ospf_if[ifname=key2]/bw"
			::= { extremeWingStatsDevDynRouteOspfIfEntry 5 }

		
		-- 1.3.6.1.4.1.1916.2.131.50.1.4.2.34.11.1.6
		extremeWingStatsDevDynRouteOspfIfFlags OBJECT-TYPE
			SYNTAX Counter64
			MAX-ACCESS read-only
			STATUS current
			DESCRIPTION
				"Inteface flags.
				
				XPath: /extremeWing-stats/device[mac=key1]/ospf_stats/ospf_if[ifname=key2]/flags"
			::= { extremeWingStatsDevDynRouteOspfIfEntry 6 }

		
		-- 1.3.6.1.4.1.1916.2.131.50.1.4.2.34.11.1.7
		extremeWingStatsDevDynRouteOspfIfEnabled OBJECT-TYPE
			SYNTAX TruthValue
			MAX-ACCESS read-only
			STATUS current
			DESCRIPTION
				"Whether OSPF is enabled on this interface or not.
				
				XPath: /extremeWing-stats/device[mac=key1]/ospf_stats/ospf_if[ifname=key2]/ospf_enabled_flag"
			::= { extremeWingStatsDevDynRouteOspfIfEntry 7 }

		
		-- 1.3.6.1.4.1.1916.2.131.50.1.4.2.34.12
		extremeWingStatsDevDynRouteOspfIfInfoTable OBJECT-TYPE
			SYNTAX SEQUENCE OF ExtremeWingStatsDevDynRouteOspfIfInfoEntry
			MAX-ACCESS not-accessible
			STATUS current
			DESCRIPTION
				"Description."
			::= { extremeWingStatsDevDynRoute 12 }

		
		-- 1.3.6.1.4.1.1916.2.131.50.1.4.2.34.12.1
		extremeWingStatsDevDynRouteOspfIfInfoEntry OBJECT-TYPE
			SYNTAX ExtremeWingStatsDevDynRouteOspfIfInfoEntry
			MAX-ACCESS not-accessible
			STATUS current
			DESCRIPTION
				"Description."
			INDEX { extremeWingStatsDevMac, extremeWingStatsDevDynRouteOspfIfName, extremeWingStatsDevDynRouteOspfIfInfoIndex }
			::= { extremeWingStatsDevDynRouteOspfIfInfoTable 1 }

		
		ExtremeWingStatsDevDynRouteOspfIfInfoEntry ::=
			SEQUENCE { 
				extremeWingStatsDevDynRouteOspfIfInfoIndex
					Unsigned32,
				extremeWingStatsDevDynRouteOspfIfIpAddr
					DisplayString,
				extremeWingStatsDevDynRouteOspfIfMask
					Unsigned32,
				extremeWingStatsDevDynRouteOspfIfBroadcastOrP2P
					DisplayString,
				extremeWingStatsDevDynRouteOspfIfBroadcastOrP2PIpAddr
					DisplayString,
				extremeWingStatsDevDynRouteOspfIfAreaId
					DisplayString,
				extremeWingStatsDevDynRouteOspfIfMtuMismatchDetectFlag
					TruthValue,
				extremeWingStatsDevDynRouteOspfIfRouterId
					DisplayString,
				extremeWingStatsDevDynRouteOspfIfNetworkType
					DisplayString,
				extremeWingStatsDevDynRouteOspfIfCost
					Unsigned32,
				extremeWingStatsDevDynRouteOspfIfTransmitDelay
					Unsigned32,
				extremeWingStatsDevDynRouteOspfIfIsmState
					DisplayString,
				extremeWingStatsDevDynRouteOspfIfPriority
					Unsigned32,
				extremeWingStatsDevDynRouteOspfIfDesgRouterId
					DisplayString,
				extremeWingStatsDevDynRouteOspfIfDesgRouterAddr
					DisplayString,
				extremeWingStatsDevDynRouteOspfIfBackupDesgRouterId
					DisplayString,
				extremeWingStatsDevDynRouteOspfIfBackupDesgRouterAddr
					DisplayString,
				extremeWingStatsDevDynRouteOspfIfMcastMembership
					DisplayString,
				extremeWingStatsDevDynRouteOspfIfSubSecHelloFlag
					TruthValue,
				extremeWingStatsDevDynRouteOspfIfHelloInterval
					Unsigned32,
				extremeWingStatsDevDynRouteOspfIfDeadInterval
					Unsigned32,
				extremeWingStatsDevDynRouteOspfIfWaitInterval
					Unsigned32,
				extremeWingStatsDevDynRouteOspfIfRetransmitInterval
					Unsigned32,
				extremeWingStatsDevDynRouteOspfIfPassiveFlag
					TruthValue,
				extremeWingStatsDevDynRouteOspfIfHelloDueIn
					DisplayString,
				extremeWingStatsDevDynRouteOspfIfNeighborCount
					Unsigned32,
				extremeWingStatsDevDynRouteOspfIfAdjNeighborCount
					Unsigned32
			 }

		-- 1.3.6.1.4.1.1916.2.131.50.1.4.2.34.12.1.1
		extremeWingStatsDevDynRouteOspfIfInfoIndex OBJECT-TYPE
			SYNTAX Unsigned32 (1..4294967295)
			MAX-ACCESS read-only
			STATUS current
			DESCRIPTION
				"OSPF interface information table index.
				
				XPath: /extremeWing-stats/device[mac=key1]/ospf_stats/ospf_if[ifname=key2]/ospf_if_info[ospf_if_info_index=key3]/ospf_if_info_index"
			::= { extremeWingStatsDevDynRouteOspfIfInfoEntry 1 }

		
		-- 1.3.6.1.4.1.1916.2.131.50.1.4.2.34.12.1.2
		extremeWingStatsDevDynRouteOspfIfIpAddr OBJECT-TYPE
			SYNTAX DisplayString
			MAX-ACCESS read-only
			STATUS current
			DESCRIPTION
				"IP address of this interface.
				
				XPath: /extremeWing-stats/device[mac=key1]/ospf_stats/ospf_if[ifname=key2]/ospf_if_info[ospf_if_info_index=key3]/intf_ip"
			::= { extremeWingStatsDevDynRouteOspfIfInfoEntry 2 }

		
		-- 1.3.6.1.4.1.1916.2.131.50.1.4.2.34.12.1.3
		extremeWingStatsDevDynRouteOspfIfMask OBJECT-TYPE
			SYNTAX Unsigned32
			MAX-ACCESS read-only
			STATUS current
			DESCRIPTION
				"Network mask for this interface.
				
				XPath: /extremeWing-stats/device[mac=key1]/ospf_stats/ospf_if[ifname=key2]/ospf_if_info[ospf_if_info_index=key3]/mask"
			::= { extremeWingStatsDevDynRouteOspfIfInfoEntry 3 }

		
		-- 1.3.6.1.4.1.1916.2.131.50.1.4.2.34.12.1.4
		extremeWingStatsDevDynRouteOspfIfBroadcastOrP2P OBJECT-TYPE
			SYNTAX DisplayString
			MAX-ACCESS read-only
			STATUS current
			DESCRIPTION
				"Whether this interface is broadcast pr peer-to-peer.
				
				XPath: /extremeWing-stats/device[mac=key1]/ospf_stats/ospf_if[ifname=key2]/ospf_if_info[ospf_if_info_index=key3]/dstr"
			::= { extremeWingStatsDevDynRouteOspfIfInfoEntry 4 }

		
		-- 1.3.6.1.4.1.1916.2.131.50.1.4.2.34.12.1.5
		extremeWingStatsDevDynRouteOspfIfBroadcastOrP2PIpAddr OBJECT-TYPE
			SYNTAX DisplayString
			MAX-ACCESS read-only
			STATUS current
			DESCRIPTION
				"Broadcast or peer IP address of this interface.
				
				XPath: /extremeWing-stats/device[mac=key1]/ospf_stats/ospf_if[ifname=key2]/ospf_if_info[ospf_if_info_index=key3]/dest"
			::= { extremeWingStatsDevDynRouteOspfIfInfoEntry 5 }

		
		-- 1.3.6.1.4.1.1916.2.131.50.1.4.2.34.12.1.6
		extremeWingStatsDevDynRouteOspfIfAreaId OBJECT-TYPE
			SYNTAX DisplayString
			MAX-ACCESS read-only
			STATUS current
			DESCRIPTION
				"Area ID to which this interface belongs.
				
				XPath: /extremeWing-stats/device[mac=key1]/ospf_stats/ospf_if[ifname=key2]/ospf_if_info[ospf_if_info_index=key3]/area_id"
			::= { extremeWingStatsDevDynRouteOspfIfInfoEntry 6 }

		
		-- 1.3.6.1.4.1.1916.2.131.50.1.4.2.34.12.1.7
		extremeWingStatsDevDynRouteOspfIfMtuMismatchDetectFlag OBJECT-TYPE
			SYNTAX TruthValue
			MAX-ACCESS read-only
			STATUS current
			DESCRIPTION
				"Wheter MTU mismatch detection is enabled or not.
				
				XPath: /extremeWing-stats/device[mac=key1]/ospf_stats/ospf_if[ifname=key2]/ospf_if_info[ospf_if_info_index=key3]/mtu_mismatch_det_flag"
			::= { extremeWingStatsDevDynRouteOspfIfInfoEntry 7 }

		
		-- 1.3.6.1.4.1.1916.2.131.50.1.4.2.34.12.1.8
		extremeWingStatsDevDynRouteOspfIfRouterId OBJECT-TYPE
			SYNTAX DisplayString
			MAX-ACCESS read-only
			STATUS current
			DESCRIPTION
				"Router ID of this router.
				
				XPath: /extremeWing-stats/device[mac=key1]/ospf_stats/ospf_if[ifname=key2]/ospf_if_info[ospf_if_info_index=key3]/router_id"
			::= { extremeWingStatsDevDynRouteOspfIfInfoEntry 8 }

		
		-- 1.3.6.1.4.1.1916.2.131.50.1.4.2.34.12.1.9
		extremeWingStatsDevDynRouteOspfIfNetworkType OBJECT-TYPE
			SYNTAX DisplayString
			MAX-ACCESS read-only
			STATUS current
			DESCRIPTION
				"Type of the network connected to this interface.
				
				XPath: /extremeWing-stats/device[mac=key1]/ospf_stats/ospf_if[ifname=key2]/ospf_if_info[ospf_if_info_index=key3]/nw_type"
			::= { extremeWingStatsDevDynRouteOspfIfInfoEntry 9 }

		
		-- 1.3.6.1.4.1.1916.2.131.50.1.4.2.34.12.1.10
		extremeWingStatsDevDynRouteOspfIfCost OBJECT-TYPE
			SYNTAX Unsigned32
			MAX-ACCESS read-only
			STATUS current
			DESCRIPTION
				"Cost of this OSPF interface.
				
				XPath: /extremeWing-stats/device[mac=key1]/ospf_stats/ospf_if[ifname=key2]/ospf_if_info[ospf_if_info_index=key3]/cost"
			::= { extremeWingStatsDevDynRouteOspfIfInfoEntry 10 }

		
		-- 1.3.6.1.4.1.1916.2.131.50.1.4.2.34.12.1.11
		extremeWingStatsDevDynRouteOspfIfTransmitDelay OBJECT-TYPE
			SYNTAX Unsigned32
			MAX-ACCESS read-only
			STATUS current
			DESCRIPTION
				"Link state transmit interval.
				
				XPath: /extremeWing-stats/device[mac=key1]/ospf_stats/ospf_if[ifname=key2]/ospf_if_info[ospf_if_info_index=key3]/transmit_delay"
			::= { extremeWingStatsDevDynRouteOspfIfInfoEntry 11 }

		
		-- 1.3.6.1.4.1.1916.2.131.50.1.4.2.34.12.1.12
		extremeWingStatsDevDynRouteOspfIfIsmState OBJECT-TYPE
			SYNTAX DisplayString
			MAX-ACCESS read-only
			STATUS current
			DESCRIPTION
				"OSPF Interface State Machine state.
				
				XPath: /extremeWing-stats/device[mac=key1]/ospf_stats/ospf_if[ifname=key2]/ospf_if_info[ospf_if_info_index=key3]/ism_state"
			::= { extremeWingStatsDevDynRouteOspfIfInfoEntry 12 }

		
		-- 1.3.6.1.4.1.1916.2.131.50.1.4.2.34.12.1.13
		extremeWingStatsDevDynRouteOspfIfPriority OBJECT-TYPE
			SYNTAX Unsigned32
			MAX-ACCESS read-only
			STATUS current
			DESCRIPTION
				"OSPF inteface priority.
				
				XPath: /extremeWing-stats/device[mac=key1]/ospf_stats/ospf_if[ifname=key2]/ospf_if_info[ospf_if_info_index=key3]/priority"
			::= { extremeWingStatsDevDynRouteOspfIfInfoEntry 13 }

		
		-- 1.3.6.1.4.1.1916.2.131.50.1.4.2.34.12.1.14
		extremeWingStatsDevDynRouteOspfIfDesgRouterId OBJECT-TYPE
			SYNTAX DisplayString
			MAX-ACCESS read-only
			STATUS current
			DESCRIPTION
				"Designated Router ID.
				
				XPath: /extremeWing-stats/device[mac=key1]/ospf_stats/ospf_if[ifname=key2]/ospf_if_info[ospf_if_info_index=key3]/dr_id"
			::= { extremeWingStatsDevDynRouteOspfIfInfoEntry 14 }

		
		-- 1.3.6.1.4.1.1916.2.131.50.1.4.2.34.12.1.15
		extremeWingStatsDevDynRouteOspfIfDesgRouterAddr OBJECT-TYPE
			SYNTAX DisplayString
			MAX-ACCESS read-only
			STATUS current
			DESCRIPTION
				"Interface through which DR is reachable.
				
				XPath: /extremeWing-stats/device[mac=key1]/ospf_stats/ospf_if[ifname=key2]/ospf_if_info[ospf_if_info_index=key3]/dr_ifaddr"
			::= { extremeWingStatsDevDynRouteOspfIfInfoEntry 15 }

		
		-- 1.3.6.1.4.1.1916.2.131.50.1.4.2.34.12.1.16
		extremeWingStatsDevDynRouteOspfIfBackupDesgRouterId OBJECT-TYPE
			SYNTAX DisplayString
			MAX-ACCESS read-only
			STATUS current
			DESCRIPTION
				"Backup Designated Router ID.
				
				XPath: /extremeWing-stats/device[mac=key1]/ospf_stats/ospf_if[ifname=key2]/ospf_if_info[ospf_if_info_index=key3]/bdr_id"
			::= { extremeWingStatsDevDynRouteOspfIfInfoEntry 16 }

		
		-- 1.3.6.1.4.1.1916.2.131.50.1.4.2.34.12.1.17
		extremeWingStatsDevDynRouteOspfIfBackupDesgRouterAddr OBJECT-TYPE
			SYNTAX DisplayString
			MAX-ACCESS read-only
			STATUS current
			DESCRIPTION
				"Interface through which BDR is reachable.
				
				XPath: /extremeWing-stats/device[mac=key1]/ospf_stats/ospf_if[ifname=key2]/ospf_if_info[ospf_if_info_index=key3]/bdr_ifaddr"
			::= { extremeWingStatsDevDynRouteOspfIfInfoEntry 17 }

		
		-- 1.3.6.1.4.1.1916.2.131.50.1.4.2.34.12.1.18
		extremeWingStatsDevDynRouteOspfIfMcastMembership OBJECT-TYPE
			SYNTAX DisplayString
			MAX-ACCESS read-only
			STATUS current
			DESCRIPTION
				"What kind of multicast packets are acted upon by this interface.
				
				XPath: /extremeWing-stats/device[mac=key1]/ospf_stats/ospf_if[ifname=key2]/ospf_if_info[ospf_if_info_index=key3]/mc_membership"
			::= { extremeWingStatsDevDynRouteOspfIfInfoEntry 18 }

		
		-- 1.3.6.1.4.1.1916.2.131.50.1.4.2.34.12.1.19
		extremeWingStatsDevDynRouteOspfIfSubSecHelloFlag OBJECT-TYPE
			SYNTAX TruthValue
			MAX-ACCESS read-only
			STATUS current
			DESCRIPTION
				"Whether fast hello is enabled.
				
				XPath: /extremeWing-stats/device[mac=key1]/ospf_stats/ospf_if[ifname=key2]/ospf_if_info[ospf_if_info_index=key3]/sub_sec_hello_flag"
			::= { extremeWingStatsDevDynRouteOspfIfInfoEntry 19 }

		
		-- 1.3.6.1.4.1.1916.2.131.50.1.4.2.34.12.1.20
		extremeWingStatsDevDynRouteOspfIfHelloInterval OBJECT-TYPE
			SYNTAX Unsigned32
			MAX-ACCESS read-only
			STATUS current
			DESCRIPTION
				"Interval between OSPF Hello packets.
				
				XPath: /extremeWing-stats/device[mac=key1]/ospf_stats/ospf_if[ifname=key2]/ospf_if_info[ospf_if_info_index=key3]/hello_interval"
			::= { extremeWingStatsDevDynRouteOspfIfInfoEntry 20 }

		
		-- 1.3.6.1.4.1.1916.2.131.50.1.4.2.34.12.1.21
		extremeWingStatsDevDynRouteOspfIfDeadInterval OBJECT-TYPE
			SYNTAX Unsigned32
			MAX-ACCESS read-only
			STATUS current
			DESCRIPTION
				"Interval after which a neighbor is declared dead.
				
				XPath: /extremeWing-stats/device[mac=key1]/ospf_stats/ospf_if[ifname=key2]/ospf_if_info[ospf_if_info_index=key3]/dead_interval"
			::= { extremeWingStatsDevDynRouteOspfIfInfoEntry 21 }

		
		-- 1.3.6.1.4.1.1916.2.131.50.1.4.2.34.12.1.22
		extremeWingStatsDevDynRouteOspfIfWaitInterval OBJECT-TYPE
			SYNTAX Unsigned32
			MAX-ACCESS read-only
			STATUS current
			DESCRIPTION
				"Interval after which a neighbor is declared dead.
				
				XPath: /extremeWing-stats/device[mac=key1]/ospf_stats/ospf_if[ifname=key2]/ospf_if_info[ospf_if_info_index=key3]/wait_interval"
			::= { extremeWingStatsDevDynRouteOspfIfInfoEntry 22 }

		
		-- 1.3.6.1.4.1.1916.2.131.50.1.4.2.34.12.1.23
		extremeWingStatsDevDynRouteOspfIfRetransmitInterval OBJECT-TYPE
			SYNTAX Unsigned32
			MAX-ACCESS read-only
			STATUS current
			DESCRIPTION
				"Time between retransmitting lost link state advertisements.
				
				XPath: /extremeWing-stats/device[mac=key1]/ospf_stats/ospf_if[ifname=key2]/ospf_if_info[ospf_if_info_index=key3]/retransmit_interval"
			::= { extremeWingStatsDevDynRouteOspfIfInfoEntry 23 }

		
		-- 1.3.6.1.4.1.1916.2.131.50.1.4.2.34.12.1.24
		extremeWingStatsDevDynRouteOspfIfPassiveFlag OBJECT-TYPE
			SYNTAX TruthValue
			MAX-ACCESS read-only
			STATUS current
			DESCRIPTION
				"Whether this interface is passive or not.
				
				XPath: /extremeWing-stats/device[mac=key1]/ospf_stats/ospf_if[ifname=key2]/ospf_if_info[ospf_if_info_index=key3]/passive_flag"
			::= { extremeWingStatsDevDynRouteOspfIfInfoEntry 24 }

		
		-- 1.3.6.1.4.1.1916.2.131.50.1.4.2.34.12.1.25
		extremeWingStatsDevDynRouteOspfIfHelloDueIn OBJECT-TYPE
			SYNTAX DisplayString
			MAX-ACCESS read-only
			STATUS current
			DESCRIPTION
				"Interval after which next HELLO will be sent.
				
				XPath: /extremeWing-stats/device[mac=key1]/ospf_stats/ospf_if[ifname=key2]/ospf_if_info[ospf_if_info_index=key3]/hello_due_in"
			::= { extremeWingStatsDevDynRouteOspfIfInfoEntry 25 }

		
		-- 1.3.6.1.4.1.1916.2.131.50.1.4.2.34.12.1.26
		extremeWingStatsDevDynRouteOspfIfNeighborCount OBJECT-TYPE
			SYNTAX Unsigned32
			MAX-ACCESS read-only
			STATUS current
			DESCRIPTION
				"Number of OSPF neighbors.
				
				XPath: /extremeWing-stats/device[mac=key1]/ospf_stats/ospf_if[ifname=key2]/ospf_if_info[ospf_if_info_index=key3]/ospf_nbr_count"
			::= { extremeWingStatsDevDynRouteOspfIfInfoEntry 26 }

		
		-- 1.3.6.1.4.1.1916.2.131.50.1.4.2.34.12.1.27
		extremeWingStatsDevDynRouteOspfIfAdjNeighborCount OBJECT-TYPE
			SYNTAX Unsigned32
			MAX-ACCESS read-only
			STATUS current
			DESCRIPTION
				"Number of adjacent OSPF neighbors.
				
				XPath: /extremeWing-stats/device[mac=key1]/ospf_stats/ospf_if[ifname=key2]/ospf_if_info[ospf_if_info_index=key3]/ospf_adj_nbr_count"
			::= { extremeWingStatsDevDynRouteOspfIfInfoEntry 27 }

		
		-- 1.3.6.1.4.1.1916.2.131.50.1.4.2.34.13
		extremeWingStatsDevDynRouteNeighborTable OBJECT-TYPE
			SYNTAX SEQUENCE OF ExtremeWingStatsDevDynRouteNeighborEntry
			MAX-ACCESS not-accessible
			STATUS current
			DESCRIPTION
				"Description."
			::= { extremeWingStatsDevDynRoute 13 }

		
		-- 1.3.6.1.4.1.1916.2.131.50.1.4.2.34.13.1
		extremeWingStatsDevDynRouteNeighborEntry OBJECT-TYPE
			SYNTAX ExtremeWingStatsDevDynRouteNeighborEntry
			MAX-ACCESS not-accessible
			STATUS current
			DESCRIPTION
				"Description."
			INDEX { extremeWingStatsDevMac, extremeWingStatsDevDynRouteNeighborIndex }
			::= { extremeWingStatsDevDynRouteNeighborTable 1 }

		
		ExtremeWingStatsDevDynRouteNeighborEntry ::=
			SEQUENCE { 
				extremeWingStatsDevDynRouteNeighborIndex
					Unsigned32,
				extremeWingStatsDevDynRouteNeighborRouterId
					DisplayString,
				extremeWingStatsDevDynRouteNeighborPriority
					Unsigned32,
				extremeWingStatsDevDynRouteNeighborSelfState
					DisplayString,
				extremeWingStatsDevDynRouteNeighborDeadTime
					Unsigned32,
				extremeWingStatsDevDynRouteNeighborAddr
					DisplayString,
				extremeWingStatsDevDynRouteNeighborIfName
					DisplayString,
				extremeWingStatsDevDynRouteNeighborSrcAddr
					DisplayString,
				extremeWingStatsDevDynRouteNeighborRetansmitCount
					Unsigned32,
				extremeWingStatsDevDynRouteNeighborRequestCount
					Unsigned32,
				extremeWingStatsDevDynRouteNeighborSummaryCount
					Unsigned32
			 }

		-- 1.3.6.1.4.1.1916.2.131.50.1.4.2.34.13.1.1
		extremeWingStatsDevDynRouteNeighborIndex OBJECT-TYPE
			SYNTAX Unsigned32 (1..4294967295)
			MAX-ACCESS read-only
			STATUS current
			DESCRIPTION
				"Neighbor information table index.
				
				XPath: /extremeWing-stats/device[mac=key1]/ospf_stats/neighbor_info[neighbor_index=key2]/neighbor_index"
			::= { extremeWingStatsDevDynRouteNeighborEntry 1 }

		
		-- 1.3.6.1.4.1.1916.2.131.50.1.4.2.34.13.1.2
		extremeWingStatsDevDynRouteNeighborRouterId OBJECT-TYPE
			SYNTAX DisplayString
			MAX-ACCESS read-only
			STATUS current
			DESCRIPTION
				"Router ID.
				
				XPath: /extremeWing-stats/device[mac=key1]/ospf_stats/neighbor_info[neighbor_index=key2]/router_id"
			::= { extremeWingStatsDevDynRouteNeighborEntry 2 }

		
		-- 1.3.6.1.4.1.1916.2.131.50.1.4.2.34.13.1.3
		extremeWingStatsDevDynRouteNeighborPriority OBJECT-TYPE
			SYNTAX Unsigned32
			MAX-ACCESS read-only
			STATUS current
			DESCRIPTION
				"OSPF Priority of this neighbor.
				
				XPath: /extremeWing-stats/device[mac=key1]/ospf_stats/neighbor_info[neighbor_index=key2]/nbr_priority"
			::= { extremeWingStatsDevDynRouteNeighborEntry 3 }

		
		-- 1.3.6.1.4.1.1916.2.131.50.1.4.2.34.13.1.4
		extremeWingStatsDevDynRouteNeighborSelfState OBJECT-TYPE
			SYNTAX DisplayString
			MAX-ACCESS read-only
			STATUS current
			DESCRIPTION
				"OSPF state of this router and neighbor router
				
				XPath: /extremeWing-stats/device[mac=key1]/ospf_stats/neighbor_info[neighbor_index=key2]/self_nbr_state"
			::= { extremeWingStatsDevDynRouteNeighborEntry 4 }

		
		-- 1.3.6.1.4.1.1916.2.131.50.1.4.2.34.13.1.5
		extremeWingStatsDevDynRouteNeighborDeadTime OBJECT-TYPE
			SYNTAX Unsigned32
			MAX-ACCESS read-only
			STATUS current
			DESCRIPTION
				"Interval after which the will be declared dead.
				
				XPath: /extremeWing-stats/device[mac=key1]/ospf_stats/neighbor_info[neighbor_index=key2]/dead_time"
			::= { extremeWingStatsDevDynRouteNeighborEntry 5 }

		
		-- 1.3.6.1.4.1.1916.2.131.50.1.4.2.34.13.1.6
		extremeWingStatsDevDynRouteNeighborAddr OBJECT-TYPE
			SYNTAX DisplayString
			MAX-ACCESS read-only
			STATUS current
			DESCRIPTION
				"IP Address of the neighbor router.
				
				XPath: /extremeWing-stats/device[mac=key1]/ospf_stats/neighbor_info[neighbor_index=key2]/nbr_addr"
			::= { extremeWingStatsDevDynRouteNeighborEntry 6 }

		
		-- 1.3.6.1.4.1.1916.2.131.50.1.4.2.34.13.1.7
		extremeWingStatsDevDynRouteNeighborIfName OBJECT-TYPE
			SYNTAX DisplayString
			MAX-ACCESS read-only
			STATUS current
			DESCRIPTION
				"Interface Name.
				
				XPath: /extremeWing-stats/device[mac=key1]/ospf_stats/neighbor_info[neighbor_index=key2]/ifname"
			::= { extremeWingStatsDevDynRouteNeighborEntry 7 }

		
		-- 1.3.6.1.4.1.1916.2.131.50.1.4.2.34.13.1.8
		extremeWingStatsDevDynRouteNeighborSrcAddr OBJECT-TYPE
			SYNTAX DisplayString
			MAX-ACCESS read-only
			STATUS current
			DESCRIPTION
				"IP Address of this router.
				
				XPath: /extremeWing-stats/device[mac=key1]/ospf_stats/neighbor_info[neighbor_index=key2]/src_addr"
			::= { extremeWingStatsDevDynRouteNeighborEntry 8 }

		
		-- 1.3.6.1.4.1.1916.2.131.50.1.4.2.34.13.1.9
		extremeWingStatsDevDynRouteNeighborRetansmitCount OBJECT-TYPE
			SYNTAX Unsigned32
			MAX-ACCESS read-only
			STATUS current
			DESCRIPTION
				"Link state request message retransmit count.
				
				XPath: /extremeWing-stats/device[mac=key1]/ospf_stats/neighbor_info[neighbor_index=key2]/retransmit_count"
			::= { extremeWingStatsDevDynRouteNeighborEntry 9 }

		
		-- 1.3.6.1.4.1.1916.2.131.50.1.4.2.34.13.1.10
		extremeWingStatsDevDynRouteNeighborRequestCount OBJECT-TYPE
			SYNTAX Unsigned32
			MAX-ACCESS read-only
			STATUS current
			DESCRIPTION
				"Link state request message request count
				
				XPath: /extremeWing-stats/device[mac=key1]/ospf_stats/neighbor_info[neighbor_index=key2]/request_count"
			::= { extremeWingStatsDevDynRouteNeighborEntry 10 }

		
		-- 1.3.6.1.4.1.1916.2.131.50.1.4.2.34.13.1.11
		extremeWingStatsDevDynRouteNeighborSummaryCount OBJECT-TYPE
			SYNTAX Unsigned32
			MAX-ACCESS read-only
			STATUS current
			DESCRIPTION
				"Summary LSA count.
				
				XPath: /extremeWing-stats/device[mac=key1]/ospf_stats/neighbor_info[neighbor_index=key2]/summary_count"
			::= { extremeWingStatsDevDynRouteNeighborEntry 11 }

		
-- /extremeWing-stats/device/pppoe
		-- 1.3.6.1.4.1.1916.2.131.50.1.4.2.35
		extremeWingStatsDevPppoe OBJECT IDENTIFIER ::= { extremeWingStatsDev 35 }

		
		-- 1.3.6.1.4.1.1916.2.131.50.1.4.2.35.1
		extremeWingStatsDevPppoeStatusTable OBJECT-TYPE
			SYNTAX SEQUENCE OF ExtremeWingStatsDevPppoeStatusEntry
			MAX-ACCESS not-accessible
			STATUS current
			DESCRIPTION
				"
				
				/extremeWing-stats/device/pppoe/status"
			::= { extremeWingStatsDevPppoe 1 }

		
		-- 1.3.6.1.4.1.1916.2.131.50.1.4.2.35.1.1
		extremeWingStatsDevPppoeStatusEntry OBJECT-TYPE
			SYNTAX ExtremeWingStatsDevPppoeStatusEntry
			MAX-ACCESS not-accessible
			STATUS current
			DESCRIPTION
				"An entry in the table."
			INDEX { extremeWingStatsDevMac }
			::= { extremeWingStatsDevPppoeStatusTable 1 }

		
		ExtremeWingStatsDevPppoeStatusEntry ::=
			SEQUENCE { 
				extremeWingStatsDevPppoeStatusPeer
					MacAddress,
				extremeWingStatsDevPppoeStatusSid
					OCTET STRING,
				extremeWingStatsDevPppoeStatusService
					DisplayString,
				extremeWingStatsDevPppoeStatusStatus
					DisplayString,
				extremeWingStatsDevPppoeStatusMtu
					Unsigned32,
				extremeWingStatsDevPppoeStatusDns1
					DisplayString,
				extremeWingStatsDevPppoeStatusDns2
					DisplayString
			 }

		-- 1.3.6.1.4.1.1916.2.131.50.1.4.2.35.1.1.1
		extremeWingStatsDevPppoeStatusPeer OBJECT-TYPE
			SYNTAX MacAddress
			MAX-ACCESS read-only
			STATUS current
			DESCRIPTION
				"PPPoE peer MAC address.
				
				XPath: /extremeWing-stats/device[mac=key1]/pppoe/status/peer"
			::= { extremeWingStatsDevPppoeStatusEntry 1 }

		
		-- 1.3.6.1.4.1.1916.2.131.50.1.4.2.35.1.1.2
		extremeWingStatsDevPppoeStatusSid OBJECT-TYPE
			SYNTAX OCTET STRING
			MAX-ACCESS read-only
			STATUS current
			DESCRIPTION
				"PPPoE session ID.
				
				XPath: /extremeWing-stats/device[mac=key1]/pppoe/status/sid"
			::= { extremeWingStatsDevPppoeStatusEntry 2 }

		
		-- 1.3.6.1.4.1.1916.2.131.50.1.4.2.35.1.1.3
		extremeWingStatsDevPppoeStatusService OBJECT-TYPE
			SYNTAX DisplayString
			MAX-ACCESS read-only
			STATUS current
			DESCRIPTION
				"PPPoE service name.
				
				XPath: /extremeWing-stats/device[mac=key1]/pppoe/status/service"
			::= { extremeWingStatsDevPppoeStatusEntry 3 }

		
		-- 1.3.6.1.4.1.1916.2.131.50.1.4.2.35.1.1.4
		extremeWingStatsDevPppoeStatusStatus OBJECT-TYPE
			SYNTAX DisplayString
			MAX-ACCESS read-only
			STATUS current
			DESCRIPTION
				"PPPoE client connection status.
				
				XPath: /extremeWing-stats/device[mac=key1]/pppoe/status/status"
			::= { extremeWingStatsDevPppoeStatusEntry 4 }

		
		-- 1.3.6.1.4.1.1916.2.131.50.1.4.2.35.1.1.5
		extremeWingStatsDevPppoeStatusMtu OBJECT-TYPE
			SYNTAX Unsigned32
			MAX-ACCESS read-only
			STATUS current
			DESCRIPTION
				"PPPoE client negotiated MTU with peer.
				
				XPath: /extremeWing-stats/device[mac=key1]/pppoe/status/mtu"
			::= { extremeWingStatsDevPppoeStatusEntry 5 }

		
		-- 1.3.6.1.4.1.1916.2.131.50.1.4.2.35.1.1.6
		extremeWingStatsDevPppoeStatusDns1 OBJECT-TYPE
			SYNTAX DisplayString
			MAX-ACCESS read-only
			STATUS current
			DESCRIPTION
				"PPPoE server supplied name server1.
				
				XPath: /extremeWing-stats/device[mac=key1]/pppoe/status/dns1"
			::= { extremeWingStatsDevPppoeStatusEntry 6 }

		
		-- 1.3.6.1.4.1.1916.2.131.50.1.4.2.35.1.1.7
		extremeWingStatsDevPppoeStatusDns2 OBJECT-TYPE
			SYNTAX DisplayString
			MAX-ACCESS read-only
			STATUS current
			DESCRIPTION
				"PPPoE server supplied name server2.
				
				XPath: /extremeWing-stats/device[mac=key1]/pppoe/status/dns2"
			::= { extremeWingStatsDevPppoeStatusEntry 7 }

		
		-- 1.3.6.1.4.1.1916.2.131.50.1.4.2.35.2
		extremeWingStatsDevPppoeCfgTable OBJECT-TYPE
			SYNTAX SEQUENCE OF ExtremeWingStatsDevPppoeCfgEntry
			MAX-ACCESS not-accessible
			STATUS current
			DESCRIPTION
				"
				
				/extremeWing-stats/device/pppoe/config"
			::= { extremeWingStatsDevPppoe 2 }

		
		-- 1.3.6.1.4.1.1916.2.131.50.1.4.2.35.2.1
		extremeWingStatsDevPppoeCfgEntry OBJECT-TYPE
			SYNTAX ExtremeWingStatsDevPppoeCfgEntry
			MAX-ACCESS not-accessible
			STATUS current
			DESCRIPTION
				"An entry in the table."
			INDEX { extremeWingStatsDevMac }
			::= { extremeWingStatsDevPppoeCfgTable 1 }

		
		ExtremeWingStatsDevPppoeCfgEntry ::=
			SEQUENCE { 
				extremeWingStatsDevPppoeCfgAuthtype
					DisplayString,
				extremeWingStatsDevPppoeCfgIdleTime
					Unsigned32,
				extremeWingStatsDevPppoeCfgKalive
					TruthValue,
				extremeWingStatsDevPppoeCfgMtu
					Unsigned32,
				extremeWingStatsDevPppoeCfgNet
					DisplayString,
				extremeWingStatsDevPppoeCfgService
					DisplayString,
				extremeWingStatsDevPppoeCfgUsername
					DisplayString,
				extremeWingStatsDevPppoeCfgPasswd
					DisplayString,
				extremeWingStatsDevPppoeCfgShutdown
					TruthValue
			 }

		-- 1.3.6.1.4.1.1916.2.131.50.1.4.2.35.2.1.1
		extremeWingStatsDevPppoeCfgAuthtype OBJECT-TYPE
			SYNTAX DisplayString
			MAX-ACCESS read-only
			STATUS current
			DESCRIPTION
				"PPPoE client authentication type.
				
				XPath: /extremeWing-stats/device[mac=key1]/pppoe/config/authtype"
			::= { extremeWingStatsDevPppoeCfgEntry 1 }

		
		-- 1.3.6.1.4.1.1916.2.131.50.1.4.2.35.2.1.2
		extremeWingStatsDevPppoeCfgIdleTime OBJECT-TYPE
			SYNTAX Unsigned32
			MAX-ACCESS read-only
			STATUS current
			DESCRIPTION
				"PPPoE client idle time.
				
				XPath: /extremeWing-stats/device[mac=key1]/pppoe/config/idle_time"
			::= { extremeWingStatsDevPppoeCfgEntry 2 }

		
		-- 1.3.6.1.4.1.1916.2.131.50.1.4.2.35.2.1.3
		extremeWingStatsDevPppoeCfgKalive OBJECT-TYPE
			SYNTAX TruthValue
			MAX-ACCESS read-only
			STATUS current
			DESCRIPTION
				"PPPoE client keepalive.
				
				XPath: /extremeWing-stats/device[mac=key1]/pppoe/config/kalive"
			::= { extremeWingStatsDevPppoeCfgEntry 3 }

		
		-- 1.3.6.1.4.1.1916.2.131.50.1.4.2.35.2.1.4
		extremeWingStatsDevPppoeCfgMtu OBJECT-TYPE
			SYNTAX Unsigned32
			MAX-ACCESS read-only
			STATUS current
			DESCRIPTION
				"PPPoE client MTU.
				
				XPath: /extremeWing-stats/device[mac=key1]/pppoe/config/mtu"
			::= { extremeWingStatsDevPppoeCfgEntry 4 }

		
		-- 1.3.6.1.4.1.1916.2.131.50.1.4.2.35.2.1.5
		extremeWingStatsDevPppoeCfgNet OBJECT-TYPE
			SYNTAX DisplayString
			MAX-ACCESS read-only
			STATUS current
			DESCRIPTION
				"PPPoE client network in which DSL modem is connected.
				
				XPath: /extremeWing-stats/device[mac=key1]/pppoe/config/net"
			::= { extremeWingStatsDevPppoeCfgEntry 5 }

		
		-- 1.3.6.1.4.1.1916.2.131.50.1.4.2.35.2.1.6
		extremeWingStatsDevPppoeCfgService OBJECT-TYPE
			SYNTAX DisplayString
			MAX-ACCESS read-only
			STATUS current
			DESCRIPTION
				"PPPoE service name.
				
				XPath: /extremeWing-stats/device[mac=key1]/pppoe/config/service"
			::= { extremeWingStatsDevPppoeCfgEntry 6 }

		
		-- 1.3.6.1.4.1.1916.2.131.50.1.4.2.35.2.1.7
		extremeWingStatsDevPppoeCfgUsername OBJECT-TYPE
			SYNTAX DisplayString
			MAX-ACCESS read-only
			STATUS current
			DESCRIPTION
				"PPPoE client authentication username.
				
				XPath: /extremeWing-stats/device[mac=key1]/pppoe/config/username"
			::= { extremeWingStatsDevPppoeCfgEntry 7 }

		
		-- 1.3.6.1.4.1.1916.2.131.50.1.4.2.35.2.1.8
		extremeWingStatsDevPppoeCfgPasswd OBJECT-TYPE
			SYNTAX DisplayString
			MAX-ACCESS read-only
			STATUS current
			DESCRIPTION
				"PPPoE client authentication password.
				
				XPath: /extremeWing-stats/device[mac=key1]/pppoe/config/passwd"
			::= { extremeWingStatsDevPppoeCfgEntry 8 }

		
		-- 1.3.6.1.4.1.1916.2.131.50.1.4.2.35.2.1.9
		extremeWingStatsDevPppoeCfgShutdown OBJECT-TYPE
			SYNTAX TruthValue
			MAX-ACCESS read-only
			STATUS current
			DESCRIPTION
				"PPPoE client mode of operation.
				
				XPath: /extremeWing-stats/device[mac=key1]/pppoe/config/shutdown"
			::= { extremeWingStatsDevPppoeCfgEntry 9 }

		
-- /extremeWing-stats/device/l2tpv3_stats
		-- 1.3.6.1.4.1.1916.2.131.50.1.4.2.36
		extremeWingStatsDevl2tpv3 OBJECT IDENTIFIER ::= { extremeWingStatsDev 36 }

		
		-- 1.3.6.1.4.1.1916.2.131.50.1.4.2.36.1
		extremeWingStatsDevl2tpv3TunnelTable OBJECT-TYPE
			SYNTAX SEQUENCE OF ExtremeWingStatsDevl2tpv3TunnelEntry
			MAX-ACCESS not-accessible
			STATUS current
			DESCRIPTION
				"/extremeWing-stats/device/l2tpv3_stats/l2tpv3_tunnels"
			::= { extremeWingStatsDevl2tpv3 1 }

		
		-- 1.3.6.1.4.1.1916.2.131.50.1.4.2.36.1.1
		extremeWingStatsDevl2tpv3TunnelEntry OBJECT-TYPE
			SYNTAX ExtremeWingStatsDevl2tpv3TunnelEntry
			MAX-ACCESS not-accessible
			STATUS current
			DESCRIPTION
				"An entry in the table."
			INDEX { extremeWingStatsDevMac, extremeWingStatsDevl2tpv3TunnelName }
			::= { extremeWingStatsDevl2tpv3TunnelTable 1 }

		
		ExtremeWingStatsDevl2tpv3TunnelEntry ::=
			SEQUENCE { 
				extremeWingStatsDevl2tpv3TunnelName
					ExtremeWingIdentifier,
				extremeWingStatsDevl2tpv3TunnelCtrlConnId
					Unsigned32,
				extremeWingStatsDevl2tpv3TunnelUpTime
					Integer32,
				extremeWingStatsDevl2tpv3TunnelPeerAddr
					DisplayString,
				extremeWingStatsDevl2tpv3TunnelLocalAddr
					DisplayString,
				extremeWingStatsDevl2tpv3TunnelMtu
					Unsigned32,
				extremeWingStatsDevl2tpv3TunnelPeerHostName
					DisplayString,
				extremeWingStatsDevl2tpv3TunnelPeerCtrlConnId
					Unsigned32,
				extremeWingStatsDevl2tpv3TunnelPeerVendorName
					DisplayString,
				extremeWingStatsDevl2tpv3TunnelState
					DisplayString,
				extremeWingStatsDevl2tpv3TunnelEncapsulationProtocol
					DisplayString,
				extremeWingStatsDevl2tpv3TunnelNextTxSeqNum
					Unsigned32,
				extremeWingStatsDevl2tpv3TunnelNextRxSeqNum
					Unsigned32,
				extremeWingStatsDevl2tpv3TunnelRxAckSeqNum
					Unsigned32,
				extremeWingStatsDevl2tpv3TunnelRetransmitCount
					Unsigned32,
				extremeWingStatsDevl2tpv3TunnelReconnectCount
					Unsigned32
			 }

		-- 1.3.6.1.4.1.1916.2.131.50.1.4.2.36.1.1.1
		extremeWingStatsDevl2tpv3TunnelName OBJECT-TYPE
			SYNTAX ExtremeWingIdentifier
			MAX-ACCESS read-only
			STATUS current
			DESCRIPTION
				"Name of the L2TP-v3 tunnel.
				
				XPath: /extremeWing-stats/device[mac=key1]/l2tpv3_stats/l2tpv3_tunnels[tunnel_name=key2]/tunnel_name"
			::= { extremeWingStatsDevl2tpv3TunnelEntry 1 }

		
		-- 1.3.6.1.4.1.1916.2.131.50.1.4.2.36.1.1.2
		extremeWingStatsDevl2tpv3TunnelCtrlConnId OBJECT-TYPE
			SYNTAX Unsigned32
			MAX-ACCESS read-only
			STATUS current
			DESCRIPTION
				"Control connection ID.
				
				XPath: /extremeWing-stats/device[mac=key1]/l2tpv3_stats/l2tpv3_tunnels[tunnel_name=key2]/ctrl_conn_id"
			::= { extremeWingStatsDevl2tpv3TunnelEntry 2 }

		
		-- 1.3.6.1.4.1.1916.2.131.50.1.4.2.36.1.1.3
		extremeWingStatsDevl2tpv3TunnelUpTime OBJECT-TYPE
			SYNTAX Integer32
			MAX-ACCESS read-only
			STATUS current
			DESCRIPTION
				"Tunnel uptime in seconds.
				
				XPath: /extremeWing-stats/device[mac=key1]/l2tpv3_stats/l2tpv3_tunnels[tunnel_name=key2]/uptime"
			::= { extremeWingStatsDevl2tpv3TunnelEntry 3 }

		
		-- 1.3.6.1.4.1.1916.2.131.50.1.4.2.36.1.1.4
		extremeWingStatsDevl2tpv3TunnelPeerAddr OBJECT-TYPE
			SYNTAX DisplayString
			MAX-ACCESS read-only
			STATUS current
			DESCRIPTION
				"L2TPv3 Peer.
				
				XPath: /extremeWing-stats/device[mac=key1]/l2tpv3_stats/l2tpv3_tunnels[tunnel_name=key2]/peer_addr"
			::= { extremeWingStatsDevl2tpv3TunnelEntry 4 }

		
		-- 1.3.6.1.4.1.1916.2.131.50.1.4.2.36.1.1.5
		extremeWingStatsDevl2tpv3TunnelLocalAddr OBJECT-TYPE
			SYNTAX DisplayString
			MAX-ACCESS read-only
			STATUS current
			DESCRIPTION
				"IP address of local end-point of the L2TPv3 tunnel.
				
				XPath: /extremeWing-stats/device[mac=key1]/l2tpv3_stats/l2tpv3_tunnels[tunnel_name=key2]/local_addr"
			::= { extremeWingStatsDevl2tpv3TunnelEntry 5 }

		
		-- 1.3.6.1.4.1.1916.2.131.50.1.4.2.36.1.1.6
		extremeWingStatsDevl2tpv3TunnelMtu OBJECT-TYPE
			SYNTAX Unsigned32
			MAX-ACCESS read-write
			STATUS current
			DESCRIPTION
				"MTU size for this tunnel.
				
				XPath: /extremeWing-stats/device[mac=key1]/l2tpv3_stats/l2tpv3_tunnels[tunnel_name=key2]/mtu"
			::= { extremeWingStatsDevl2tpv3TunnelEntry 6 }

		
		-- 1.3.6.1.4.1.1916.2.131.50.1.4.2.36.1.1.7
		extremeWingStatsDevl2tpv3TunnelPeerHostName OBJECT-TYPE
			SYNTAX DisplayString
			MAX-ACCESS read-only
			STATUS current
			DESCRIPTION
				"Peer's hostname.
				
				XPath: /extremeWing-stats/device[mac=key1]/l2tpv3_stats/l2tpv3_tunnels[tunnel_name=key2]/peer_host_name"
			::= { extremeWingStatsDevl2tpv3TunnelEntry 7 }

		
		-- 1.3.6.1.4.1.1916.2.131.50.1.4.2.36.1.1.8
		extremeWingStatsDevl2tpv3TunnelPeerCtrlConnId OBJECT-TYPE
			SYNTAX Unsigned32
			MAX-ACCESS read-only
			STATUS current
			DESCRIPTION
				"Peer's control connection ID.
				
				XPath: /extremeWing-stats/device[mac=key1]/l2tpv3_stats/l2tpv3_tunnels[tunnel_name=key2]/peer_ctrl_conn_id"
			::= { extremeWingStatsDevl2tpv3TunnelEntry 8 }

		
		-- 1.3.6.1.4.1.1916.2.131.50.1.4.2.36.1.1.9
		extremeWingStatsDevl2tpv3TunnelPeerVendorName OBJECT-TYPE
			SYNTAX DisplayString
			MAX-ACCESS read-only
			STATUS current
			DESCRIPTION
				"Peer's vendor name.
				
				XPath: /extremeWing-stats/device[mac=key1]/l2tpv3_stats/l2tpv3_tunnels[tunnel_name=key2]/peer_vendor_name"
			::= { extremeWingStatsDevl2tpv3TunnelEntry 9 }

		
		-- 1.3.6.1.4.1.1916.2.131.50.1.4.2.36.1.1.10
		extremeWingStatsDevl2tpv3TunnelState OBJECT-TYPE
			SYNTAX DisplayString
			MAX-ACCESS read-only
			STATUS current
			DESCRIPTION
				"Tunnel state
				Idle
				WaitForSCCRP
				WaitForSCCCN
				Established
				Closing
				
				XPath: /extremeWing-stats/device[mac=key1]/l2tpv3_stats/l2tpv3_tunnels[tunnel_name=key2]/tunnel_state"
			::= { extremeWingStatsDevl2tpv3TunnelEntry 10 }

		
		-- 1.3.6.1.4.1.1916.2.131.50.1.4.2.36.1.1.11
		extremeWingStatsDevl2tpv3TunnelEncapsulationProtocol OBJECT-TYPE
			SYNTAX DisplayString
			MAX-ACCESS read-write
			STATUS current
			DESCRIPTION
				"EncapsulationProtocol
				IP
				UDP
				
				XPath: /extremeWing-stats/device[mac=key1]/l2tpv3_stats/l2tpv3_tunnels[tunnel_name=key2]/encapsulation_protocol"
			::= { extremeWingStatsDevl2tpv3TunnelEntry 11 }

		
		-- 1.3.6.1.4.1.1916.2.131.50.1.4.2.36.1.1.12
		extremeWingStatsDevl2tpv3TunnelNextTxSeqNum OBJECT-TYPE
			SYNTAX Unsigned32
			MAX-ACCESS read-only
			STATUS current
			DESCRIPTION
				"Sequence number of the next msg to the peer.
				
				XPath: /extremeWing-stats/device[mac=key1]/l2tpv3_stats/l2tpv3_tunnels[tunnel_name=key2]/next_tx_seq_num"
			::= { extremeWingStatsDevl2tpv3TunnelEntry 12 }

		
		-- 1.3.6.1.4.1.1916.2.131.50.1.4.2.36.1.1.13
		extremeWingStatsDevl2tpv3TunnelNextRxSeqNum OBJECT-TYPE
			SYNTAX Unsigned32
			MAX-ACCESS read-only
			STATUS current
			DESCRIPTION
				"Expected sequence number of the next msg from the peer.
				
				XPath: /extremeWing-stats/device[mac=key1]/l2tpv3_stats/l2tpv3_tunnels[tunnel_name=key2]/next_rx_seq_num"
			::= { extremeWingStatsDevl2tpv3TunnelEntry 13 }

		
		-- 1.3.6.1.4.1.1916.2.131.50.1.4.2.36.1.1.14
		extremeWingStatsDevl2tpv3TunnelRxAckSeqNum OBJECT-TYPE
			SYNTAX Unsigned32
			MAX-ACCESS read-only
			STATUS current
			DESCRIPTION
				"Seuence number of the next msg expected by the peer.
				
				XPath: /extremeWing-stats/device[mac=key1]/l2tpv3_stats/l2tpv3_tunnels[tunnel_name=key2]/rx_ack_seq_num"
			::= { extremeWingStatsDevl2tpv3TunnelEntry 14 }

		
		-- 1.3.6.1.4.1.1916.2.131.50.1.4.2.36.1.1.15
		extremeWingStatsDevl2tpv3TunnelRetransmitCount OBJECT-TYPE
			SYNTAX Unsigned32
			MAX-ACCESS read-only
			STATUS current
			DESCRIPTION
				"Retransmission count.
				
				XPath: /extremeWing-stats/device[mac=key1]/l2tpv3_stats/l2tpv3_tunnels[tunnel_name=key2]/retransmit_count"
			::= { extremeWingStatsDevl2tpv3TunnelEntry 15 }

		
		-- 1.3.6.1.4.1.1916.2.131.50.1.4.2.36.1.1.16
		extremeWingStatsDevl2tpv3TunnelReconnectCount OBJECT-TYPE
			SYNTAX Unsigned32
			MAX-ACCESS read-only
			STATUS current
			DESCRIPTION
				"Reconnection count.
				
				XPath: /extremeWing-stats/device[mac=key1]/l2tpv3_stats/l2tpv3_tunnels[tunnel_name=key2]/reconnect_count"
			::= { extremeWingStatsDevl2tpv3TunnelEntry 16 }

		
-- /extremeWing-stats/device/l2tpv3_stats/l2tpv3_tunnels/l2tpv3_sessions
		-- 1.3.6.1.4.1.1916.2.131.50.1.4.2.36.2
		extremeWingStatsDevl2tpv3Sessions OBJECT IDENTIFIER ::= { extremeWingStatsDevl2tpv3 2 }

		
		-- 1.3.6.1.4.1.1916.2.131.50.1.4.2.36.2.1
		extremeWingStatsDevl2tpv3SessionsVlansTable OBJECT-TYPE
			SYNTAX SEQUENCE OF ExtremeWingStatsDevl2tpv3SessionsVlansEntry
			MAX-ACCESS not-accessible
			STATUS current
			DESCRIPTION
				"/extremeWing-stats/device/l2tpv3_stats/l2tpv3_tunnels/l2tpv3_sessions/vlans"
			::= { extremeWingStatsDevl2tpv3Sessions 1 }

		
		-- 1.3.6.1.4.1.1916.2.131.50.1.4.2.36.2.1.1
		extremeWingStatsDevl2tpv3SessionsVlansEntry OBJECT-TYPE
			SYNTAX ExtremeWingStatsDevl2tpv3SessionsVlansEntry
			MAX-ACCESS not-accessible
			STATUS current
			DESCRIPTION
				"An entry in the table."
			INDEX { extremeWingStatsDevMac, extremeWingStatsDevl2tpv3SessionsName, extremeWingStatsDevl2tpv3SessionsVlanId }
			::= { extremeWingStatsDevl2tpv3SessionsVlansTable 1 }

		
		ExtremeWingStatsDevl2tpv3SessionsVlansEntry ::=
			SEQUENCE { 
				extremeWingStatsDevl2tpv3SessionsVlanId
					Unsigned32
			 }

		-- 1.3.6.1.4.1.1916.2.131.50.1.4.2.36.2.1.1.1
		extremeWingStatsDevl2tpv3SessionsVlanId OBJECT-TYPE
			SYNTAX Unsigned32 (1..65535)
			MAX-ACCESS read-only
			STATUS current
			DESCRIPTION
				"Extended VLAN ID.
				
				XPath: /extremeWing-stats/device[mac=key1]/l2tpv3_stats/l2tpv3_tunnels[tunnel_name=key2]/l2tpv3_sessions[session_name=key3]/vlans[vlan_id=key4]/vlan_id"
			::= { extremeWingStatsDevl2tpv3SessionsVlansEntry 1 }

		
		-- 1.3.6.1.4.1.1916.2.131.50.1.4.2.36.2.2
		extremeWingStatsDevl2tpv3SessionsTable OBJECT-TYPE
			SYNTAX SEQUENCE OF ExtremeWingStatsDevl2tpv3SessionsEntry
			MAX-ACCESS not-accessible
			STATUS current
			DESCRIPTION
				"/extremeWing-stats/device/l2tpv3_stats/l2tpv3_tunnels/l2tpv3_sessions"
			::= { extremeWingStatsDevl2tpv3Sessions 2 }

		
		-- 1.3.6.1.4.1.1916.2.131.50.1.4.2.36.2.2.1
		extremeWingStatsDevl2tpv3SessionsEntry OBJECT-TYPE
			SYNTAX ExtremeWingStatsDevl2tpv3SessionsEntry
			MAX-ACCESS not-accessible
			STATUS current
			DESCRIPTION
				"An entry in the table."
			INDEX { extremeWingStatsDevMac, extremeWingStatsDevl2tpv3TunnelName, extremeWingStatsDevl2tpv3SessionsName }
			::= { extremeWingStatsDevl2tpv3SessionsTable 1 }

		
		ExtremeWingStatsDevl2tpv3SessionsEntry ::=
			SEQUENCE { 
				extremeWingStatsDevl2tpv3SessionsName
					ExtremeWingIdentifier,
				extremeWingStatsDevl2tpv3TunnelNativeVlanId
					Unsigned32,
				extremeWingStatsDevl2tpv3TunnelTrunkSession
					TruthValue,
				extremeWingStatsDevl2tpv3TunnelNativeVlanTagged
					TruthValue,
				extremeWingStatsDevl2tpv3SessionsPseudoWireType
					DisplayString,
				extremeWingStatsDevl2tpv3SessionsCallSerialNumber
					Unsigned32,
				extremeWingStatsDevl2tpv3SessionsLocalSessionId
					Unsigned32,
				extremeWingStatsDevl2tpv3SessionsRemoteSessionId
					Unsigned32,
				extremeWingStatsDevl2tpv3SessionsLocalCookieSize
					Unsigned32,
				extremeWingStatsDevl2tpv3SessionsLocalcookieWord1
					Unsigned32,
				extremeWingStatsDevl2tpv3SessionsLocalCookieWord2
					Unsigned32,
				extremeWingStatsDevl2tpv3SessionsRemoteCookieSize
					Unsigned32,
				extremeWingStatsDevl2tpv3SessionsRemoteCookieWord1
					Unsigned32,
				extremeWingStatsDevl2tpv3SessionsRemoteCookieWord2
					Unsigned32,
				extremeWingStatsDevl2tpv3SessionsState
					DisplayString,
				extremeWingStatsDevl2tpv3SessionsRemoteEndId
					DisplayString,
				extremeWingStatsDevl2tpv3SessionsRxPktCounter
					Unsigned32,
				extremeWingStatsDevl2tpv3SessionsRxBytesCounter
					Unsigned32,
				extremeWingStatsDevl2tpv3SessionsTxPktCounter
					Unsigned32,
				extremeWingStatsDevl2tpv3SessionsTxBytesCounter
					Unsigned32,
				extremeWingStatsDevl2tpv3SessionsNumDroppedPkts
					Unsigned32
			 }

		-- 1.3.6.1.4.1.1916.2.131.50.1.4.2.36.2.2.1.1
		extremeWingStatsDevl2tpv3SessionsName OBJECT-TYPE
			SYNTAX ExtremeWingIdentifier
			MAX-ACCESS read-only
			STATUS current
			DESCRIPTION
				"Name of the L2TPv3 session
				
				XPath: /extremeWing-stats/device[mac=key1]/l2tpv3_stats/l2tpv3_tunnels[tunnel_name=key2]/l2tpv3_sessions[session_name=key3]/session_name"
			::= { extremeWingStatsDevl2tpv3SessionsEntry 1 }

		
		-- 1.3.6.1.4.1.1916.2.131.50.1.4.2.36.2.2.1.2
		extremeWingStatsDevl2tpv3TunnelNativeVlanId OBJECT-TYPE
			SYNTAX Unsigned32
			MAX-ACCESS read-only
			STATUS current
			DESCRIPTION
				"Native VLAN ID.
				
				XPath: /extremeWing-stats/device[mac=key1]/l2tpv3_stats/l2tpv3_tunnels[tunnel_name=key2]/l2tpv3_sessions[session_name=key3]/native_vlan_id"
			::= { extremeWingStatsDevl2tpv3SessionsEntry 2 }

		
		-- 1.3.6.1.4.1.1916.2.131.50.1.4.2.36.2.2.1.3
		extremeWingStatsDevl2tpv3TunnelTrunkSession OBJECT-TYPE
			SYNTAX TruthValue
			MAX-ACCESS read-only
			STATUS current
			DESCRIPTION
				"Whether session carries traffic from/to multiple vlans.
				
				XPath: /extremeWing-stats/device[mac=key1]/l2tpv3_stats/l2tpv3_tunnels[tunnel_name=key2]/l2tpv3_sessions[session_name=key3]/trunk_session"
			::= { extremeWingStatsDevl2tpv3SessionsEntry 3 }

		
		-- 1.3.6.1.4.1.1916.2.131.50.1.4.2.36.2.2.1.4
		extremeWingStatsDevl2tpv3TunnelNativeVlanTagged OBJECT-TYPE
			SYNTAX TruthValue
			MAX-ACCESS read-only
			STATUS current
			DESCRIPTION
				"Whether native VLAN packets are tagged.
				
				XPath: /extremeWing-stats/device[mac=key1]/l2tpv3_stats/l2tpv3_tunnels[tunnel_name=key2]/l2tpv3_sessions[session_name=key3]/native_vlan_tagged"
			::= { extremeWingStatsDevl2tpv3SessionsEntry 4 }

		
		-- 1.3.6.1.4.1.1916.2.131.50.1.4.2.36.2.2.1.5
		extremeWingStatsDevl2tpv3SessionsPseudoWireType OBJECT-TYPE
			SYNTAX DisplayString
			MAX-ACCESS read-only
			STATUS current
			DESCRIPTION
				"L2TPv3 pseudo wire type.
				Ethernet
				Ethernet_VLAN
				
				XPath: /extremeWing-stats/device[mac=key1]/l2tpv3_stats/l2tpv3_tunnels[tunnel_name=key2]/l2tpv3_sessions[session_name=key3]/pseudo_wire_type"
			::= { extremeWingStatsDevl2tpv3SessionsEntry 5 }

		
		-- 1.3.6.1.4.1.1916.2.131.50.1.4.2.36.2.2.1.6
		extremeWingStatsDevl2tpv3SessionsCallSerialNumber OBJECT-TYPE
			SYNTAX Unsigned32
			MAX-ACCESS read-only
			STATUS current
			DESCRIPTION
				"Serial number for the session.
				
				XPath: /extremeWing-stats/device[mac=key1]/l2tpv3_stats/l2tpv3_tunnels[tunnel_name=key2]/l2tpv3_sessions[session_name=key3]/call_serial_number"
			::= { extremeWingStatsDevl2tpv3SessionsEntry 6 }

		
		-- 1.3.6.1.4.1.1916.2.131.50.1.4.2.36.2.2.1.7
		extremeWingStatsDevl2tpv3SessionsLocalSessionId OBJECT-TYPE
			SYNTAX Unsigned32
			MAX-ACCESS read-only
			STATUS current
			DESCRIPTION
				"Local Session ID.
				
				XPath: /extremeWing-stats/device[mac=key1]/l2tpv3_stats/l2tpv3_tunnels[tunnel_name=key2]/l2tpv3_sessions[session_name=key3]/local_session_id"
			::= { extremeWingStatsDevl2tpv3SessionsEntry 7 }

		
		-- 1.3.6.1.4.1.1916.2.131.50.1.4.2.36.2.2.1.8
		extremeWingStatsDevl2tpv3SessionsRemoteSessionId OBJECT-TYPE
			SYNTAX Unsigned32
			MAX-ACCESS read-only
			STATUS current
			DESCRIPTION
				"Remote Session ID.
				
				XPath: /extremeWing-stats/device[mac=key1]/l2tpv3_stats/l2tpv3_tunnels[tunnel_name=key2]/l2tpv3_sessions[session_name=key3]/remote_session_id"
			::= { extremeWingStatsDevl2tpv3SessionsEntry 8 }

		
		-- 1.3.6.1.4.1.1916.2.131.50.1.4.2.36.2.2.1.9
		extremeWingStatsDevl2tpv3SessionsLocalCookieSize OBJECT-TYPE
			SYNTAX Unsigned32
			MAX-ACCESS read-only
			STATUS current
			DESCRIPTION
				"Size of local cookie: 0, 4 or 8 bytes.
				
				XPath: /extremeWing-stats/device[mac=key1]/l2tpv3_stats/l2tpv3_tunnels[tunnel_name=key2]/l2tpv3_sessions[session_name=key3]/local_cookie_size"
			::= { extremeWingStatsDevl2tpv3SessionsEntry 9 }

		
		-- 1.3.6.1.4.1.1916.2.131.50.1.4.2.36.2.2.1.10
		extremeWingStatsDevl2tpv3SessionsLocalcookieWord1 OBJECT-TYPE
			SYNTAX Unsigned32
			MAX-ACCESS read-only
			STATUS current
			DESCRIPTION
				"First word of local cookie.
				
				XPath: /extremeWing-stats/device[mac=key1]/l2tpv3_stats/l2tpv3_tunnels[tunnel_name=key2]/l2tpv3_sessions[session_name=key3]/local_cookie_word1"
			::= { extremeWingStatsDevl2tpv3SessionsEntry 10 }

		
		-- 1.3.6.1.4.1.1916.2.131.50.1.4.2.36.2.2.1.11
		extremeWingStatsDevl2tpv3SessionsLocalCookieWord2 OBJECT-TYPE
			SYNTAX Unsigned32
			MAX-ACCESS read-only
			STATUS current
			DESCRIPTION
				"Second word of local cookie.
				
				XPath: /extremeWing-stats/device[mac=key1]/l2tpv3_stats/l2tpv3_tunnels[tunnel_name=key2]/l2tpv3_sessions[session_name=key3]/local_cookie_word2"
			::= { extremeWingStatsDevl2tpv3SessionsEntry 11 }

		
		-- 1.3.6.1.4.1.1916.2.131.50.1.4.2.36.2.2.1.12
		extremeWingStatsDevl2tpv3SessionsRemoteCookieSize OBJECT-TYPE
			SYNTAX Unsigned32
			MAX-ACCESS read-only
			STATUS current
			DESCRIPTION
				"Size of remote cookie: 0, 4 or 8 bytes.
				
				XPath: /extremeWing-stats/device[mac=key1]/l2tpv3_stats/l2tpv3_tunnels[tunnel_name=key2]/l2tpv3_sessions[session_name=key3]/remote_cookie_size"
			::= { extremeWingStatsDevl2tpv3SessionsEntry 12 }

		
		-- 1.3.6.1.4.1.1916.2.131.50.1.4.2.36.2.2.1.13
		extremeWingStatsDevl2tpv3SessionsRemoteCookieWord1 OBJECT-TYPE
			SYNTAX Unsigned32
			MAX-ACCESS read-only
			STATUS current
			DESCRIPTION
				"First word of remote cookie.
				
				XPath: /extremeWing-stats/device[mac=key1]/l2tpv3_stats/l2tpv3_tunnels[tunnel_name=key2]/l2tpv3_sessions[session_name=key3]/remote_cookie_word1"
			::= { extremeWingStatsDevl2tpv3SessionsEntry 13 }

		
		-- 1.3.6.1.4.1.1916.2.131.50.1.4.2.36.2.2.1.14
		extremeWingStatsDevl2tpv3SessionsRemoteCookieWord2 OBJECT-TYPE
			SYNTAX Unsigned32
			MAX-ACCESS read-only
			STATUS current
			DESCRIPTION
				"Second word of remote cookie.
				
				XPath: /extremeWing-stats/device[mac=key1]/l2tpv3_stats/l2tpv3_tunnels[tunnel_name=key2]/l2tpv3_sessions[session_name=key3]/remote_cookie_word2"
			::= { extremeWingStatsDevl2tpv3SessionsEntry 14 }

		
		-- 1.3.6.1.4.1.1916.2.131.50.1.4.2.36.2.2.1.15
		extremeWingStatsDevl2tpv3SessionsState OBJECT-TYPE
			SYNTAX DisplayString
			MAX-ACCESS read-only
			STATUS current
			DESCRIPTION
				"Session state.
				Idle
				WaitForICRP
				Established
				WaitForICCN
				LostTie
				
				XPath: /extremeWing-stats/device[mac=key1]/l2tpv3_stats/l2tpv3_tunnels[tunnel_name=key2]/l2tpv3_sessions[session_name=key3]/session_state"
			::= { extremeWingStatsDevl2tpv3SessionsEntry 15 }

		
		-- 1.3.6.1.4.1.1916.2.131.50.1.4.2.36.2.2.1.16
		extremeWingStatsDevl2tpv3SessionsRemoteEndId OBJECT-TYPE
			SYNTAX DisplayString
			MAX-ACCESS read-only
			STATUS current
			DESCRIPTION
				"Remote End ID.
				
				XPath: /extremeWing-stats/device[mac=key1]/l2tpv3_stats/l2tpv3_tunnels[tunnel_name=key2]/l2tpv3_sessions[session_name=key3]/remote_end_id"
			::= { extremeWingStatsDevl2tpv3SessionsEntry 16 }

		
		-- 1.3.6.1.4.1.1916.2.131.50.1.4.2.36.2.2.1.17
		extremeWingStatsDevl2tpv3SessionsRxPktCounter OBJECT-TYPE
			SYNTAX Unsigned32
			MAX-ACCESS read-only
			STATUS current
			DESCRIPTION
				"Number of packets received.
				
				XPath: /extremeWing-stats/device[mac=key1]/l2tpv3_stats/l2tpv3_tunnels[tunnel_name=key2]/l2tpv3_sessions[session_name=key3]/rx_pkt_counter"
			::= { extremeWingStatsDevl2tpv3SessionsEntry 17 }

		
		-- 1.3.6.1.4.1.1916.2.131.50.1.4.2.36.2.2.1.18
		extremeWingStatsDevl2tpv3SessionsRxBytesCounter OBJECT-TYPE
			SYNTAX Unsigned32
			MAX-ACCESS read-only
			STATUS current
			DESCRIPTION
				"Number of bytes received.
				
				XPath: /extremeWing-stats/device[mac=key1]/l2tpv3_stats/l2tpv3_tunnels[tunnel_name=key2]/l2tpv3_sessions[session_name=key3]/rx_bytes_counter"
			::= { extremeWingStatsDevl2tpv3SessionsEntry 18 }

		
		-- 1.3.6.1.4.1.1916.2.131.50.1.4.2.36.2.2.1.19
		extremeWingStatsDevl2tpv3SessionsTxPktCounter OBJECT-TYPE
			SYNTAX Unsigned32
			MAX-ACCESS read-only
			STATUS current
			DESCRIPTION
				"Number of packets sent.
				
				XPath: /extremeWing-stats/device[mac=key1]/l2tpv3_stats/l2tpv3_tunnels[tunnel_name=key2]/l2tpv3_sessions[session_name=key3]/tx_pkt_counter"
			::= { extremeWingStatsDevl2tpv3SessionsEntry 19 }

		
		-- 1.3.6.1.4.1.1916.2.131.50.1.4.2.36.2.2.1.20
		extremeWingStatsDevl2tpv3SessionsTxBytesCounter OBJECT-TYPE
			SYNTAX Unsigned32
			MAX-ACCESS read-only
			STATUS current
			DESCRIPTION
				"Number of bytes sent.
				
				XPath: /extremeWing-stats/device[mac=key1]/l2tpv3_stats/l2tpv3_tunnels[tunnel_name=key2]/l2tpv3_sessions[session_name=key3]/tx_bytes_counter"
			::= { extremeWingStatsDevl2tpv3SessionsEntry 20 }

		
		-- 1.3.6.1.4.1.1916.2.131.50.1.4.2.36.2.2.1.21
		extremeWingStatsDevl2tpv3SessionsNumDroppedPkts OBJECT-TYPE
			SYNTAX Unsigned32
			MAX-ACCESS read-only
			STATUS current
			DESCRIPTION
				"Number of packets dropped.
				
				XPath: /extremeWing-stats/device[mac=key1]/l2tpv3_stats/l2tpv3_tunnels[tunnel_name=key2]/l2tpv3_sessions[session_name=key3]/num_dropped_pkts"
			::= { extremeWingStatsDevl2tpv3SessionsEntry 21 }


		extremeWingStatsDevRaid OBJECT IDENTIFIER ::= { extremeWingStatsDev 37 }

		
		-- 1.3.6.1.4.1.1916.2.131.50.1.4.2.37.1
		extremeWingStatsDevRaidStatusTable OBJECT-TYPE
			SYNTAX SEQUENCE OF ExtremeWingStatsDevRaidStatusEntry
			MAX-ACCESS not-accessible
			STATUS current
			DESCRIPTION
				"Description."
			::= { extremeWingStatsDevRaid 1 }

		
		-- 1.3.6.1.4.1.1916.2.131.50.1.4.2.37.1.1
		extremeWingStatsDevRaidStatusEntry OBJECT-TYPE
			SYNTAX ExtremeWingStatsDevRaidStatusEntry
			MAX-ACCESS not-accessible
			STATUS current
			DESCRIPTION
				"Description."
			INDEX { extremeWingStatsDevMac }
			::= { extremeWingStatsDevRaidStatusTable 1 }

		
		ExtremeWingStatsDevRaidStatusEntry ::=
			SEQUENCE { 
				extremeWingStatsDevRaidStatusSize
					Unsigned32,
				extremeWingStatsDevRaidStatusState
					DisplayString,
				extremeWingStatsDevRaidStatusAlarmEnable
					TruthValue,
				extremeWingStatsDevRaidStatusDate
					DisplayString,
				extremeWingStatsDevRaidStatusResult
					DisplayString
			 }

		-- 1.3.6.1.4.1.1916.2.131.50.1.4.2.37.1.1.1
		extremeWingStatsDevRaidStatusSize OBJECT-TYPE
			SYNTAX Unsigned32
			MAX-ACCESS read-only
			STATUS current
			DESCRIPTION
				"XPath: /extremeWing-stats/device[mac=key1]/raid-status/size"
			::= { extremeWingStatsDevRaidStatusEntry 1 }

		
		-- 1.3.6.1.4.1.1916.2.131.50.1.4.2.37.1.1.2
		extremeWingStatsDevRaidStatusState OBJECT-TYPE
			SYNTAX DisplayString
			MAX-ACCESS read-only
			STATUS current
			DESCRIPTION
				"XPath: /extremeWing-stats/device[mac=key1]/raid-status/state"
			::= { extremeWingStatsDevRaidStatusEntry 3 }

		
		-- 1.3.6.1.4.1.1916.2.131.50.1.4.2.37.1.1.3
		extremeWingStatsDevRaidStatusAlarmEnable OBJECT-TYPE
			SYNTAX TruthValue
			MAX-ACCESS read-only
			STATUS current
			DESCRIPTION
				"The chassis alarm will sound on RAID degrade events.
				XPath: /extremeWing-stats/device[mac=key1]/raid-status/alarm_enable"
			::= { extremeWingStatsDevRaidStatusEntry 4 }

		
		-- 1.3.6.1.4.1.1916.2.131.50.1.4.2.37.1.1.4
		extremeWingStatsDevRaidStatusDate OBJECT-TYPE
			SYNTAX DisplayString
			MAX-ACCESS read-only
			STATUS current
			DESCRIPTION
				"Date and time of last consistency check activity
				XPath: /extremeWing-stats/device[mac=key1]/raid-status/last_check/date"
			::= { extremeWingStatsDevRaidStatusEntry 5 }

		
		-- 1.3.6.1.4.1.1916.2.131.50.1.4.2.37.1.1.5
		extremeWingStatsDevRaidStatusResult OBJECT-TYPE
			SYNTAX DisplayString
			MAX-ACCESS read-only
			STATUS current
			DESCRIPTION
				"Result of last consistency check activity
				XPath: /extremeWing-stats/device[mac=key1]/raid-status/last_check/result"
			::= { extremeWingStatsDevRaidStatusEntry 6 }

		
		-- 1.3.6.1.4.1.1916.2.131.50.1.4.2.37.2
		extremeWingStatsDevRaidStatusPhyDriveTable OBJECT-TYPE
			SYNTAX SEQUENCE OF ExtremeWingStatsDevRaidStatusPhyDriveEntry
			MAX-ACCESS not-accessible
			STATUS current
			DESCRIPTION
				"Description."
			::= { extremeWingStatsDevRaid 2 }

		
		-- 1.3.6.1.4.1.1916.2.131.50.1.4.2.37.2.1
		extremeWingStatsDevRaidStatusPhyDriveEntry OBJECT-TYPE
			SYNTAX ExtremeWingStatsDevRaidStatusPhyDriveEntry
			MAX-ACCESS not-accessible
			STATUS current
			DESCRIPTION
				"Description."
			INDEX { extremeWingStatsDevMac, extremeWingStatsDevRaidStatusPhyDriveSlot }
			::= { extremeWingStatsDevRaidStatusPhyDriveTable 1 }

		
		ExtremeWingStatsDevRaidStatusPhyDriveEntry ::=
			SEQUENCE { 
				extremeWingStatsDevRaidStatusPhyDriveSlot
					Unsigned32,
				extremeWingStatsDevRaidStatusPhyDriveState
					DisplayString
			 }


		-- 1.3.6.1.4.1.1916.2.131.50.1.4.2.37.2.1.1
		extremeWingStatsDevRaidStatusPhyDriveSlot OBJECT-TYPE
			SYNTAX Unsigned32
			MAX-ACCESS read-only
			STATUS current
			DESCRIPTION
				"Information about all physical drives and slots
				XPath: /extremeWing-stats/device[mac=key1]/raid-status/physical_drives[slot=key2]/slot
				"
			::= { extremeWingStatsDevRaidStatusPhyDriveEntry 1 }

		
		-- 1.3.6.1.4.1.1916.2.131.50.1.4.2.37.2.1.2
		extremeWingStatsDevRaidStatusPhyDriveState OBJECT-TYPE
			SYNTAX DisplayString
			MAX-ACCESS read-only
			STATUS current
			DESCRIPTION
				"Information about all physical drives and slots
				XPath: /extremeWing-stats/device[mac=key1]/raid-status/physical_drives[slot=key2]/state
				"
			::= { extremeWingStatsDevRaidStatusPhyDriveEntry 2 }


		-- 1.3.6.1.4.1.1916.2.131.50.1.4.2.38
		extremeWingStatsDevGre OBJECT IDENTIFIER ::= { extremeWingStatsDev 38 }

 		
		-- 1.3.6.1.4.1.1916.2.131.50.1.4.2.38.1
		extremeWingStatsDevGreInfoTable OBJECT-TYPE
			SYNTAX SEQUENCE OF ExtremeWingStatsDevGreInfoEntry
			MAX-ACCESS not-accessible
			STATUS current
			DESCRIPTION
				"Description."
			::= { extremeWingStatsDevGre 1 }

		
		-- 1.3.6.1.4.1.1916.2.131.50.1.4.2.38.1.1
		extremeWingStatsDevGreInfoEntry OBJECT-TYPE
			SYNTAX ExtremeWingStatsDevGreInfoEntry
			MAX-ACCESS not-accessible
			STATUS current
			DESCRIPTION
				"Description."
			INDEX { extremeWingStatsDevMac }
			::= { extremeWingStatsDevGreInfoTable 1 }

		
		ExtremeWingStatsDevGreInfoEntry ::=
			SEQUENCE { 
				extremeWingStatsDevGreInfoTunnelId
					Unsigned32,
				extremeWingStatsDevGreInfoTunnelCreated
					DisplayString,
				extremeWingStatsDevGreInfoPeerIp
					DisplayString,
				extremeWingStatsDevGreInfoRxPkt
					Counter32,
				extremeWingStatsDevGreInfoTxPkt
					Counter32,
				extremeWingStatsDevGreInfoPktDropped
					Counter32
			 }

		-- 1.3.6.1.4.1.1916.2.131.50.1.4.2.38.1.1.1
		extremeWingStatsDevGreInfoTunnelId OBJECT-TYPE
			SYNTAX Unsigned32
			MAX-ACCESS read-only
			STATUS current
			DESCRIPTION
				"Name of the GRE tunnel
				XPATH: /extremeWing-stats/device[mac=key1]/gre/info/tunnel-id
				"
			::= { extremeWingStatsDevGreInfoEntry 1 }

		
		-- 1.3.6.1.4.1.1916.2.131.50.1.4.2.38.1.1.2
		extremeWingStatsDevGreInfoTunnelCreated OBJECT-TYPE
			SYNTAX DisplayString
			MAX-ACCESS read-only
			STATUS current
			DESCRIPTION
				"Tunnel state
				XPATH: /extremeWing-stats/device[mac=key1]/gre/info/gre-tunnel-created"
			::= { extremeWingStatsDevGreInfoEntry 2 }

		
		-- 1.3.6.1.4.1.1916.2.131.50.1.4.2.38.1.1.3
		extremeWingStatsDevGreInfoPeerIp OBJECT-TYPE
			SYNTAX DisplayString
			MAX-ACCESS read-only
			STATUS current
			DESCRIPTION
				"IP address of peer of the GRE tunnel
				XPATH: /extremeWing-stats/device[mac=key1]/gre/info/peer-ip"
			::= { extremeWingStatsDevGreInfoEntry 3 }

		
		-- 1.3.6.1.4.1.1916.2.131.50.1.4.2.38.1.1.4
		extremeWingStatsDevGreInfoRxPkt OBJECT-TYPE
			SYNTAX Counter32
			MAX-ACCESS read-only
			STATUS current
			DESCRIPTION
				"Total pkt received by GRE tunnel
				XPATH: /extremeWing-stats/device[mac=key1]/gre/info/rx-pkt
				"
			::= { extremeWingStatsDevGreInfoEntry 4 }

		
		-- 1.3.6.1.4.1.1916.2.131.50.1.4.2.38.1.1.5
		extremeWingStatsDevGreInfoTxPkt OBJECT-TYPE
			SYNTAX Counter32
			MAX-ACCESS read-only
			STATUS current
			DESCRIPTION
				"Total pkt sent by GRE tunnel
				XPATH: /extremeWing-stats/device[mac=key1]/gre/info/tx-pkt"
			::= { extremeWingStatsDevGreInfoEntry 5 }

		
		-- 1.3.6.1.4.1.1916.2.131.50.1.4.2.38.1.1.6
		extremeWingStatsDevGreInfoPktDropped OBJECT-TYPE
			SYNTAX Counter32
			MAX-ACCESS read-only
			STATUS current
			DESCRIPTION
				"Total pkt dropped by GRE tunnel
				XPATH: /extremeWing-stats/device[mac=key1]/gre/info/pkt-dropped"
			::= { extremeWingStatsDevGreInfoEntry 6 }



		-- 1.3.6.1.4.1.1916.2.131.50.1.4.2.39
		extremeWingStatsDevApUpgradeResultTable OBJECT-TYPE
			SYNTAX SEQUENCE OF ExtremeWingStatsDevApUpgradeResultEntry
			MAX-ACCESS not-accessible
			STATUS current
			DESCRIPTION
				"Description."
			::= { extremeWingStatsDev 39 }

		
		-- 1.3.6.1.4.1.1916.2.131.50.1.4.2.39.1
		extremeWingStatsDevApUpgradeResultEntry OBJECT-TYPE
			SYNTAX ExtremeWingStatsDevApUpgradeResultEntry
			MAX-ACCESS not-accessible
			STATUS current
			DESCRIPTION
				"Description."
			INDEX { extremeWingStatsDevMac }
			::= { extremeWingStatsDevApUpgradeResultTable 1 }

		
		ExtremeWingStatsDevApUpgradeResultEntry ::=
			SEQUENCE { 
				extremeWingStatsDevApUpgradeResultStatus
					TruthValue,
				extremeWingStatsDevApUpgradeResultMessage
					DisplayString
			 }

		-- 1.3.6.1.4.1.1916.2.131.50.1.4.2.39.1.1
		extremeWingStatsDevApUpgradeResultStatus OBJECT-TYPE
			SYNTAX TruthValue
			MAX-ACCESS read-only
			STATUS current
			DESCRIPTION
				"Whether the action is successful.
				XPATH: /extremeWing-stats/noc/_actions/ap-upgrade/result[mac=key1]/status"
			::= { extremeWingStatsDevApUpgradeResultEntry 1 }

		
		-- 1.3.6.1.4.1.1916.2.131.50.1.4.2.39.1.2
		extremeWingStatsDevApUpgradeResultMessage OBJECT-TYPE
			SYNTAX DisplayString
			MAX-ACCESS read-only
			STATUS current
			DESCRIPTION
				"Error message if the action is not successful.
				XPATH: /extremeWing-stats/noc/_actions/ap-upgrade/result[mac=key1]/message"
			::= { extremeWingStatsDevApUpgradeResultEntry 2 }


		-- 1.3.6.1.4.1.1916.2.131.50.1.4.2.40
		extremeWingStatsDevClrApUpRfdHistoryResultTable OBJECT-TYPE
			SYNTAX SEQUENCE OF ExtremeWingStatsDevClrApUpRfdHistoryResultEntry
			MAX-ACCESS not-accessible
			STATUS current
			DESCRIPTION
				"Description."
			::= { extremeWingStatsDev 40 }


		-- 1.3.6.1.4.1.1916.2.131.50.1.4.2.40.1
		extremeWingStatsDevClrApUpRfdHistoryResultEntry OBJECT-TYPE
			SYNTAX ExtremeWingStatsDevClrApUpRfdHistoryResultEntry
			MAX-ACCESS not-accessible
			STATUS current
			DESCRIPTION
				"Description."
			INDEX { extremeWingStatsDevMac, extremeWingStatsRfdName }
			::= { extremeWingStatsDevClrApUpRfdHistoryResultTable 1 }


		ExtremeWingStatsDevClrApUpRfdHistoryResultEntry ::=
			SEQUENCE {
				extremeWingStatsDevClrApUpRfdHistResultMac
					MacAddress,
				extremeWingStatsDevClrApUpRfdHistResultStatus
					TruthValue,
				extremeWingStatsDevClrApUpRfdHistResultMessage
					DisplayString
			}


		-- 1.3.6.1.4.1.1916.2.131.50.1.4.2.40.1.1
		extremeWingStatsDevClrApUpRfdHistResultMac OBJECT-TYPE
			SYNTAX MacAddress
			MAX-ACCESS read-only
			STATUS current
			DESCRIPTION
				"Whether the action is successful.
				XPATH: /extremeWing-stats/rf_domain[name=key1]/_actions/clear-ap-upgrade-history/result[mac=key1]/mac"
			::= { extremeWingStatsDevClrApUpRfdHistoryResultEntry 1 }


		-- 1.3.6.1.4.1.1916.2.131.50.1.4.2.40.1.2
		extremeWingStatsDevClrApUpRfdHistResultStatus OBJECT-TYPE
			SYNTAX TruthValue
			MAX-ACCESS read-only
			STATUS current
			DESCRIPTION
				"Whether the action is successful.
				XPATH: /extremeWing-stats/rf_domain[name=key1]/_actions/clear-ap-upgrade-history/result[mac=key1]/status"
			::= { extremeWingStatsDevClrApUpRfdHistoryResultEntry 2 }


		-- 1.3.6.1.4.1.1916.2.131.50.1.4.2.40.1.3
		extremeWingStatsDevClrApUpRfdHistResultMessage OBJECT-TYPE
			SYNTAX DisplayString
			MAX-ACCESS read-only
			STATUS current
			DESCRIPTION
				"Error message if the action is not successful.
				XPATH: /extremeWing-stats/rf_domain[name=key1]/_actions/clear-ap-upgrade-history/result[mac=key1]/message"
			::= { extremeWingStatsDevClrApUpRfdHistoryResultEntry 3 }


		-- 1.3.6.1.4.1.1916.2.131.50.1.4.2.41
		extremeWingStatsDevClrApUpNocHistoryResultTable OBJECT-TYPE
			SYNTAX SEQUENCE OF ExtremeWingStatsDevClrApUpNocHistoryResultEntry
			MAX-ACCESS not-accessible
			STATUS current
			DESCRIPTION
				"Description."
			::= { extremeWingStatsDev 41 }


		-- 1.3.6.1.4.1.1916.2.131.50.1.4.2.41.1
		extremeWingStatsDevClrApUpNocHistoryResultEntry OBJECT-TYPE
			SYNTAX ExtremeWingStatsDevClrApUpNocHistoryResultEntry
			MAX-ACCESS not-accessible
			STATUS current
			DESCRIPTION
				"Description."
			INDEX { extremeWingStatsDevMac }
			::= { extremeWingStatsDevClrApUpNocHistoryResultTable 1 }


		ExtremeWingStatsDevClrApUpNocHistoryResultEntry ::=
			SEQUENCE {
				extremeWingStatsDevClrApUpNocHistResultMac
					MacAddress,
				extremeWingStatsDevClrApUpNocHistResultStatus
					TruthValue,
				extremeWingStatsDevClrApUpNocHistResultMessage
					DisplayString
			}			


		-- 1.3.6.1.4.1.1916.2.131.50.1.4.2.41.1.1
		extremeWingStatsDevClrApUpNocHistResultMac OBJECT-TYPE
			SYNTAX MacAddress
			MAX-ACCESS read-only
			STATUS current
			DESCRIPTION
				"Whether the action is successful.
				XPATH: /extremeWing-stats/noc/_actions/clear-ap-upgrade-history/result[mac=key1]/mac"
			::= { extremeWingStatsDevClrApUpNocHistoryResultEntry 1 }


		-- 1.3.6.1.4.1.1916.2.131.50.1.4.2.41.1.2
		extremeWingStatsDevClrApUpNocHistResultStatus OBJECT-TYPE
			SYNTAX TruthValue
			MAX-ACCESS read-only
			STATUS current
			DESCRIPTION
				"Whether the action is successful .
				XPATH: /extremeWing-stats/noc/_actions/clear-ap-upgrade-history/result[mac=key1]/status"
			::= { extremeWingStatsDevClrApUpNocHistoryResultEntry 2 }


		-- 1.3.6.1.4.1.1916.2.131.50.1.4.2.41.1.3
		extremeWingStatsDevClrApUpNocHistResultMessage OBJECT-TYPE
			SYNTAX DisplayString
			MAX-ACCESS read-only
			STATUS current
			DESCRIPTION
				"Error message if the action is not successful.
				XPATH: /extremeWing-stats/noc/_actions/clear-ap-upgrade-history/result[mac=key1]/message"
			::= { extremeWingStatsDevClrApUpNocHistoryResultEntry 3 }


		-- 1.3.6.1.4.1.1916.2.131.50.1.4.2.42
		extremeWingStatsDevAcl OBJECT IDENTIFIER ::= { extremeWingStatsDev 42 }

		
		-- 1.3.6.1.4.1.1916.2.131.50.1.4.2.42.1
		extremeWingStatsDevAclIpAcl OBJECT IDENTIFIER ::= { extremeWingStatsDevAcl 1 }

		
		-- 1.3.6.1.4.1.1916.2.131.50.1.4.2.42.1.1
		extremeWingStatsDevAclIpAclStats OBJECT IDENTIFIER ::= { extremeWingStatsDevAclIpAcl 1 }

		
		-- 1.3.6.1.4.1.1916.2.131.50.1.4.2.42.1.1.1
		extremeWingStatsDevAclIpAclStatsTable OBJECT-TYPE
			SYNTAX SEQUENCE OF ExtremeWingStatsDevAclIpAclStatsEntry
			MAX-ACCESS not-accessible
			STATUS current
			DESCRIPTION
				"Description."
			::= { extremeWingStatsDevAclIpAclStats 1 }

		
		-- 1.3.6.1.4.1.1916.2.131.50.1.4.2.42.1.1.1.1
		extremeWingStatsDevAclIpAclStatsEntry OBJECT-TYPE
			SYNTAX ExtremeWingStatsDevAclIpAclStatsEntry
			MAX-ACCESS not-accessible
			STATUS current
			DESCRIPTION
				"Description."
			INDEX { extremeWingStatsDevMac, extremeWingStatsDevAclIpAclStatsName }
			::= { extremeWingStatsDevAclIpAclStatsTable 1 }

		
		ExtremeWingStatsDevAclIpAclStatsEntry ::=
			SEQUENCE { 
				extremeWingStatsDevAclIpAclStatsName
					ExtremeWingIdentifier
			 }

		-- 1.3.6.1.4.1.1916.2.131.50.1.4.2.42.1.1.1.1.1
		extremeWingStatsDevAclIpAclStatsName OBJECT-TYPE
			SYNTAX ExtremeWingIdentifier
			MAX-ACCESS read-only
			STATUS current
			DESCRIPTION
				"Name of the IP acl
				
				XPATH:/extremeWing-stats/device[mac=key1]/firewall/ip_acl_stats[name=key2]/name"
			::= { extremeWingStatsDevAclIpAclStatsEntry 1 }

		
		-- 1.3.6.1.4.1.1916.2.131.50.1.4.2.42.1.1.2
		extremeWingStatsDevAclIpAclStatsRuleTable OBJECT-TYPE
			SYNTAX SEQUENCE OF ExtremeWingStatsDevAclIpAclStatsRuleEntry
			MAX-ACCESS not-accessible
			STATUS current
			DESCRIPTION
				"Description."
			::= { extremeWingStatsDevAclIpAclStats 2 }

		
		-- 1.3.6.1.4.1.1916.2.131.50.1.4.2.42.1.1.2.1
		extremeWingStatsDevAclIpAclStatsRuleEntry OBJECT-TYPE
			SYNTAX ExtremeWingStatsDevAclIpAclStatsRuleEntry
			MAX-ACCESS not-accessible
			STATUS current
			DESCRIPTION
				"Description."
			INDEX { extremeWingStatsDevMac, extremeWingStatsDevAclIpAclStatsName, extremeWingStatsDevAclIpAclStatsRulePrecedence }
			::= { extremeWingStatsDevAclIpAclStatsRuleTable 1 }

		
		ExtremeWingStatsDevAclIpAclStatsRuleEntry ::=
			SEQUENCE { 
				extremeWingStatsDevAclIpAclStatsRulePrecedence
					Unsigned32,
				extremeWingStatsDevAclIpAclStatsRuleFriendlyString
					DisplayString,
				extremeWingStatsDevAclIpAclStatsRuleHitcount
					Unsigned32,
				extremeWingStatsDevAclIpAclStatsRuleHwHitcount
					Unsigned32
			 }

		-- 1.3.6.1.4.1.1916.2.131.50.1.4.2.42.1.1.2.1.1
		extremeWingStatsDevAclIpAclStatsRulePrecedence OBJECT-TYPE
			SYNTAX Unsigned32 (1..5000)
			MAX-ACCESS read-only
			STATUS current
			DESCRIPTION
				"XPATH: /extremeWing-stats/device[mac=key1]/firewall/ip_acl_stats[name=key2]/rules[precedence=key3]/precedence"
			::= { extremeWingStatsDevAclIpAclStatsRuleEntry 1 }

		
		-- 1.3.6.1.4.1.1916.2.131.50.1.4.2.42.1.1.2.1.2
		extremeWingStatsDevAclIpAclStatsRuleFriendlyString OBJECT-TYPE
			SYNTAX DisplayString
			MAX-ACCESS read-only
			STATUS current
			DESCRIPTION
				"A CLI like friendly string describing the rule
				
				XPATH: /extremeWing-stats/device[mac=key1]/firewall/ip_acl_stats[name=key2]/rules[precedence=key3]/friendly_string"
			::= { extremeWingStatsDevAclIpAclStatsRuleEntry 2 }

		
		-- 1.3.6.1.4.1.1916.2.131.50.1.4.2.42.1.1.2.1.3
		extremeWingStatsDevAclIpAclStatsRuleHitcount OBJECT-TYPE
			SYNTAX Unsigned32
			MAX-ACCESS read-only
			STATUS current
			DESCRIPTION
				"XPATH: /extremeWing-stats/device[mac=key1]/firewall/ip_acl_stats[name=key2]/rules[precedence=key3]/hitcount"
			::= { extremeWingStatsDevAclIpAclStatsRuleEntry 3 }

		
		-- 1.3.6.1.4.1.1916.2.131.50.1.4.2.42.1.1.2.1.4
		extremeWingStatsDevAclIpAclStatsRuleHwHitcount OBJECT-TYPE
			SYNTAX Unsigned32
			MAX-ACCESS read-only
			STATUS current
			DESCRIPTION
				"Hit counter for rules installed into switch hardware
				
				XPATH: /extremeWing-stats/device[mac=key1]/firewall/ip_acl_stats[name=key2]/rules[precedence=key3]/hw_hitcount"
			::= { extremeWingStatsDevAclIpAclStatsRuleEntry 4 }

		
		-- 1.3.6.1.4.1.1916.2.131.50.1.4.2.42.1.2
		extremeWingStatsDevAclIpAclStatsDetail OBJECT IDENTIFIER ::= { extremeWingStatsDevAclIpAcl 2 }

		
		-- 1.3.6.1.4.1.1916.2.131.50.1.4.2.42.1.2.1
		extremeWingStatsDevAclIpAclStatsDetailTable OBJECT-TYPE
			SYNTAX SEQUENCE OF ExtremeWingStatsDevAclIpAclStatsDetailEntry
			MAX-ACCESS not-accessible
			STATUS current
			DESCRIPTION
				"Description."
			::= { extremeWingStatsDevAclIpAclStatsDetail 1 }

		
		-- 1.3.6.1.4.1.1916.2.131.50.1.4.2.42.1.2.1.1
		extremeWingStatsDevAclIpAclStatsDetailEntry OBJECT-TYPE
			SYNTAX ExtremeWingStatsDevAclIpAclStatsDetailEntry
			MAX-ACCESS not-accessible
			STATUS current
			DESCRIPTION
				"Description."
			INDEX { extremeWingStatsDevMac, extremeWingStatsDevAclIpAclStatsDetailName }
			::= { extremeWingStatsDevAclIpAclStatsDetailTable 1 }

		
		ExtremeWingStatsDevAclIpAclStatsDetailEntry ::=
			SEQUENCE { 
				extremeWingStatsDevAclIpAclStatsDetailName
					ExtremeWingIdentifier
			 }

		-- 1.3.6.1.4.1.1916.2.131.50.1.4.2.42.1.2.1.1.1
		extremeWingStatsDevAclIpAclStatsDetailName OBJECT-TYPE
			SYNTAX ExtremeWingIdentifier
			MAX-ACCESS read-only
			STATUS current
			DESCRIPTION
				"Name of the IP acl
				
				XPATH: /extremeWing-stats/device[mac=key1]/firewall/ip_acl_stats_detail[name=key2]/name"
			::= { extremeWingStatsDevAclIpAclStatsDetailEntry 1 }

		
		-- 1.3.6.1.4.1.1916.2.131.50.1.4.2.42.1.2.2
		extremeWingStatsDevAclIpAclStatsDetailRuleTable OBJECT-TYPE
			SYNTAX SEQUENCE OF ExtremeWingStatsDevAclIpAclStatsDetailRuleEntry
			MAX-ACCESS not-accessible
			STATUS current
			DESCRIPTION
				"Description."
			::= { extremeWingStatsDevAclIpAclStatsDetail 2 }

		
		-- 1.3.6.1.4.1.1916.2.131.50.1.4.2.42.1.2.2.1
		extremeWingStatsDevAclIpAclStatsDetailRuleEntry OBJECT-TYPE
			SYNTAX ExtremeWingStatsDevAclIpAclStatsDetailRuleEntry
			MAX-ACCESS not-accessible
			STATUS current
			DESCRIPTION
				"Description."
			INDEX { extremeWingStatsDevMac, extremeWingStatsDevAclIpAclStatsDetailName, extremeWingStatsDevAclIpAclStatsDetailRulePrecedence }
			::= { extremeWingStatsDevAclIpAclStatsDetailRuleTable 1 }

		
		ExtremeWingStatsDevAclIpAclStatsDetailRuleEntry ::=
			SEQUENCE { 
				extremeWingStatsDevAclIpAclStatsDetailRulePrecedence
					Unsigned32,
				extremeWingStatsDevAclIpAclStatsDetailRuleFriendlyString
					DisplayString,
				extremeWingStatsDevAclIpAclStatsDetailRuleHitcount
					Unsigned32
			 }

		-- 1.3.6.1.4.1.1916.2.131.50.1.4.2.42.1.2.2.1.1
		extremeWingStatsDevAclIpAclStatsDetailRulePrecedence OBJECT-TYPE
			SYNTAX Unsigned32 (1..5000)
			MAX-ACCESS read-only
			STATUS current
			DESCRIPTION
				"XPATH:/extremeWing-stats/device[mac=key1]/firewall/ip_acl_stats_detail[name=key2]/rules[precedence=key3]/
				precedence"
			::= { extremeWingStatsDevAclIpAclStatsDetailRuleEntry 1 }

		
		-- 1.3.6.1.4.1.1916.2.131.50.1.4.2.42.1.2.2.1.5
		extremeWingStatsDevAclIpAclStatsDetailRuleFriendlyString OBJECT-TYPE
			SYNTAX DisplayString
			MAX-ACCESS read-only
			STATUS current
			DESCRIPTION
				"Expanded rule format including derived rules from network and service aliases
				
				XPATH: /extremeWing-stats/device[mac=key1]/firewall/ip_acl_stats_detail[name=key2]/rules[precedence=key3]/
				friendly_string"
			::= { extremeWingStatsDevAclIpAclStatsDetailRuleEntry 5 }

		
		-- 1.3.6.1.4.1.1916.2.131.50.1.4.2.42.1.2.2.1.6
		extremeWingStatsDevAclIpAclStatsDetailRuleHitcount OBJECT-TYPE
			SYNTAX Unsigned32
			MAX-ACCESS read-only
			STATUS current
			DESCRIPTION
				"/extremeWing-stats/device[mac=key1]/firewall/ip_acl_stats_detail[name=key2]/rules[precedence=key3]/hitcount"
			::= { extremeWingStatsDevAclIpAclStatsDetailRuleEntry 6 }

		
		-- 1.3.6.1.4.1.1916.2.131.50.1.4.2.42.2
		extremeWingStatsDevAclMacAclStats OBJECT IDENTIFIER ::= { extremeWingStatsDevAcl 2 }

		
		-- 1.3.6.1.4.1.1916.2.131.50.1.4.2.42.2.1
		extremeWingStatsDevAclMacAclStatsTable OBJECT-TYPE
			SYNTAX SEQUENCE OF ExtremeWingStatsDevAclMacAclStatsEntry
			MAX-ACCESS not-accessible
			STATUS current
			DESCRIPTION
				"Description."
			::= { extremeWingStatsDevAclMacAclStats 1 }

		
		-- 1.3.6.1.4.1.1916.2.131.50.1.4.2.42.2.1.1
		extremeWingStatsDevAclMacAclStatsEntry OBJECT-TYPE
			SYNTAX ExtremeWingStatsDevAclMacAclStatsEntry
			MAX-ACCESS not-accessible
			STATUS current
			DESCRIPTION
				"Description."
			INDEX { extremeWingStatsDevMac, extremeWingStatsDevAclMacAclStatsName }
			::= { extremeWingStatsDevAclMacAclStatsTable 1 }

		
		ExtremeWingStatsDevAclMacAclStatsEntry ::=
			SEQUENCE { 
				extremeWingStatsDevAclMacAclStatsName
					ExtremeWingIdentifier
			 }

		-- 1.3.6.1.4.1.1916.2.131.50.1.4.2.42.2.1.1.1
		extremeWingStatsDevAclMacAclStatsName OBJECT-TYPE
			SYNTAX ExtremeWingIdentifier
			MAX-ACCESS read-only
			STATUS current
			DESCRIPTION
				"Name of the MAC acl
				
				XPATH: /extremeWing-stats/device[mac=key1]/firewall/mac_acl_stats[name=key2]/name"
			::= { extremeWingStatsDevAclMacAclStatsEntry 1 }

		
		-- 1.3.6.1.4.1.1916.2.131.50.1.4.2.42.2.2
		extremeWingStatsDevAclMacAclStatsRuleTable OBJECT-TYPE
			SYNTAX SEQUENCE OF ExtremeWingStatsDevAclMacAclStatsRuleEntry
			MAX-ACCESS not-accessible
			STATUS current
			DESCRIPTION
				"Description."
			::= { extremeWingStatsDevAclMacAclStats 2 }

		
		-- 1.3.6.1.4.1.1916.2.131.50.1.4.2.42.2.2.1
		extremeWingStatsDevAclMacAclStatsRuleEntry OBJECT-TYPE
			SYNTAX ExtremeWingStatsDevAclMacAclStatsRuleEntry
			MAX-ACCESS not-accessible
			STATUS current
			DESCRIPTION
				"Description."
			INDEX { extremeWingStatsDevMac, extremeWingStatsDevAclMacAclStatsName, extremeWingStatsDevAclMacAclStatsRulePrecedence }
			::= { extremeWingStatsDevAclMacAclStatsRuleTable 1 }

		
		ExtremeWingStatsDevAclMacAclStatsRuleEntry ::=
			SEQUENCE { 
				extremeWingStatsDevAclMacAclStatsRulePrecedence
					Unsigned32,
				extremeWingStatsDevAclMacAclStatsRuleFriendlyString
					DisplayString,
				extremeWingStatsDevAclMacAclStatsRuleHitcount
					Unsigned32,
				extremeWingStatsDevAclMacAclStatsRuleHwHitcount
					Unsigned32
			 }

		-- 1.3.6.1.4.1.1916.2.131.50.1.4.2.42.2.2.1.1
		extremeWingStatsDevAclMacAclStatsRulePrecedence OBJECT-TYPE
			SYNTAX Unsigned32 (1..5000)
			MAX-ACCESS read-write
			STATUS current
			DESCRIPTION
				"XPATH: /extremeWing-stats/device[mac=key1]/firewall/mac_acl_stats[name=key2]/rules[precedence=key3]/precedence"
			::= { extremeWingStatsDevAclMacAclStatsRuleEntry 1 }

		
		-- 1.3.6.1.4.1.1916.2.131.50.1.4.2.42.2.2.1.2
		extremeWingStatsDevAclMacAclStatsRuleFriendlyString OBJECT-TYPE
			SYNTAX DisplayString
			MAX-ACCESS read-only
			STATUS current
			DESCRIPTION
			"A CLI like friendly string describing the rule
				
				XPATH: /extremeWing-stats/device[mac=key1]/firewall/mac_acl_stats[name=key2]/rules[precedence=key3]/friendly_string"
			::= { extremeWingStatsDevAclMacAclStatsRuleEntry 2 }

		
		-- 1.3.6.1.4.1.1916.2.131.50.1.4.2.42.2.2.1.3
		extremeWingStatsDevAclMacAclStatsRuleHitcount OBJECT-TYPE
			SYNTAX Unsigned32
			MAX-ACCESS read-only
			STATUS current
			DESCRIPTION
				"XPATH: /extremeWing-stats/device[mac=key1]/firewall/mac_acl_stats[name=key2]/rules[precedence=key3]/hitcount"
			::= { extremeWingStatsDevAclMacAclStatsRuleEntry 3 }

		
		-- 1.3.6.1.4.1.1916.2.131.50.1.4.2.42.2.2.1.4
		extremeWingStatsDevAclMacAclStatsRuleHwHitcount OBJECT-TYPE
			SYNTAX Unsigned32
			MAX-ACCESS read-only
			STATUS current
			DESCRIPTION
				"Hit counter for rules installed into switch hardware
				
				XPATH: /extremeWing-stats/device[mac=key1]/firewall/mac_acl_stats[name=key2]/rules[precedence=key3]/hw_hitcount"
			::= { extremeWingStatsDevAclMacAclStatsRuleEntry 4 }


		
-- Statistics on RF Domain
-- /extremeWing-stats/rf_domain
		-- 1.3.6.1.4.1.1916.2.131.50.1.4.3
		extremeWingStatsRfd OBJECT IDENTIFIER ::= { extremeWingStats 3 }

		
		-- 1.3.6.1.4.1.1916.2.131.50.1.4.3.1
		extremeWingStatsRfdTable OBJECT-TYPE
			SYNTAX SEQUENCE OF ExtremeWingStatsRfdEntry
			MAX-ACCESS not-accessible
			STATUS current
			DESCRIPTION
				"Status of RF Domains
				
				/extremeWing-stats/rf_domain"
			::= { extremeWingStatsRfd 1 }

		
		-- 1.3.6.1.4.1.1916.2.131.50.1.4.3.1.1
		extremeWingStatsRfdEntry OBJECT-TYPE
			SYNTAX ExtremeWingStatsRfdEntry
			MAX-ACCESS not-accessible
			STATUS current
			DESCRIPTION
				"An entry in the table."
			INDEX { extremeWingStatsRfdName }
			::= { extremeWingStatsRfdTable 1 }

		
		ExtremeWingStatsRfdEntry ::=
			SEQUENCE { 
				extremeWingStatsRfdName
					ExtremeWingIdentifier,
				extremeWingStatsRfdManager
					MacAddress,
				extremeWingStatsRfdTotalAdoptedDevices
					Counter32
			 }

		-- 1.3.6.1.4.1.1916.2.131.50.1.4.3.1.1.1
		extremeWingStatsRfdName OBJECT-TYPE
			SYNTAX ExtremeWingIdentifier
			MAX-ACCESS read-only
			STATUS current
			DESCRIPTION
				"RF Domain name
				
				XPath: /extremeWing-stats/rf_domain[name=key1]/name"
			::= { extremeWingStatsRfdEntry 1 }

		
		-- 1.3.6.1.4.1.1916.2.131.50.1.4.3.1.1.2
		extremeWingStatsRfdManager OBJECT-TYPE
			SYNTAX MacAddress
			MAX-ACCESS read-only
			STATUS current
			DESCRIPTION
				"MAC address of RF Domain manager
				
				XPath: /extremeWing-stats/rf_domain[name=key1]/manager"
			::= { extremeWingStatsRfdEntry 2 }

		-- 1.3.6.1.4.1.1916.2.131.50.1.4.3.1.1.3
		extremeWingStatsRfdTotalAdoptedDevices OBJECT-TYPE
			SYNTAX Counter32
			MAX-ACCESS read-only
			STATUS current
			DESCRIPTION
				"number of online devices
				XPATH: /extremeWing-stats/noc/inventory/by_domain[rf_domain_name=key1]/num_online"
			::= { extremeWingStatsRfdEntry 3 }

		
-- /extremeWing-stats/rf_domain/wireless
		-- 1.3.6.1.4.1.1916.2.131.50.1.4.3.2
		extremeWingStatsRfdWl OBJECT IDENTIFIER ::= { extremeWingStatsRfd 2 }

		
-- /extremeWing-stats/rf_domain/wireless/ap-info
		-- 1.3.6.1.4.1.1916.2.131.50.1.4.3.2.1
		extremeWingStatsRfdWlApInfo OBJECT IDENTIFIER ::= { extremeWingStatsRfdWl 1 }

		
		-- 1.3.6.1.4.1.1916.2.131.50.1.4.3.2.1.1
		extremeWingStatsRfdWlApInfoTable OBJECT-TYPE
			SYNTAX SEQUENCE OF ExtremeWingStatsRfdWlApInfoEntry
			MAX-ACCESS not-accessible
			STATUS current
			DESCRIPTION
				"Status of managed Access Points on RF Domain
				
				/extremeWing-stats/rf_domain/wireless/ap-info"
			::= { extremeWingStatsRfdWlApInfo 1 }

		
		-- 1.3.6.1.4.1.1916.2.131.50.1.4.3.2.1.1.1
		extremeWingStatsRfdWlApInfoEntry OBJECT-TYPE
			SYNTAX ExtremeWingStatsRfdWlApInfoEntry
			MAX-ACCESS not-accessible
			STATUS current
			DESCRIPTION
				"An entry in the table."
			INDEX { extremeWingStatsRfdName, extremeWingStatsRfdWlApInfoMac }
			::= { extremeWingStatsRfdWlApInfoTable 1 }

		
		ExtremeWingStatsRfdWlApInfoEntry ::=
			SEQUENCE { 
				extremeWingStatsRfdWlApInfoMac
					MacAddress,
				extremeWingStatsRfdWlApInfoFaultDetected
					TruthValue,
				extremeWingStatsRfdWlApInfoNumRadios
					Unsigned32,
				extremeWingStatsRfdWlApInfoNumClients
					Unsigned32,
				extremeWingStatsRfdWlApInfoLastCalTime
					DisplayString,
				extremeWingStatsRfdWlApInfoType
					DisplayString,
				extremeWingStatsRfdWlApInfoStatsMode
					DisplayString,
				extremeWingStatsRfdWlApInfoStatsInterval
					Unsigned32,
				extremeWingStatsRfdWlApInfoHostname
					DisplayString,
				extremeWingStatsRfdWlApInfoRfDomainName
					DisplayString,
				extremeWingStatsRfdWlApInfoLocation
					DisplayString,
				extremeWingStatsRfdWlApInfoAdoptedTo
					MacAddress,
				extremeWingStatsRfdWlApInfoIp
					DisplayString
			 }

		-- 1.3.6.1.4.1.1916.2.131.50.1.4.3.2.1.1.1.1
		extremeWingStatsRfdWlApInfoMac OBJECT-TYPE
			SYNTAX MacAddress
			MAX-ACCESS read-only
			STATUS current
			DESCRIPTION
				"AP MAC
				
				XPath: /extremeWing-stats/rf_domain[name=key1]/wireless/ap-info[mac=key2]/mac"
			::= { extremeWingStatsRfdWlApInfoEntry 1 }

		
		-- 1.3.6.1.4.1.1916.2.131.50.1.4.3.2.1.1.1.2
		extremeWingStatsRfdWlApInfoFaultDetected OBJECT-TYPE
			SYNTAX TruthValue
			MAX-ACCESS read-only
			STATUS current
			DESCRIPTION
				"Whether any fault has been detected on the AP
				
				XPath: /extremeWing-stats/rf_domain[name=key1]/wireless/ap-info[mac=key2]/fault_detected"
			::= { extremeWingStatsRfdWlApInfoEntry 2 }

		
		-- 1.3.6.1.4.1.1916.2.131.50.1.4.3.2.1.1.1.3
		extremeWingStatsRfdWlApInfoNumRadios OBJECT-TYPE
			SYNTAX Unsigned32
			MAX-ACCESS read-only
			STATUS current
			DESCRIPTION
				"Number of radios on the AP
				
				XPath: /extremeWing-stats/rf_domain[name=key1]/wireless/ap-info[mac=key2]/num_radios"
			::= { extremeWingStatsRfdWlApInfoEntry 3 }

		
		-- 1.3.6.1.4.1.1916.2.131.50.1.4.3.2.1.1.1.4
		extremeWingStatsRfdWlApInfoNumClients OBJECT-TYPE
			SYNTAX Unsigned32
			MAX-ACCESS read-only
			STATUS current
			DESCRIPTION
				"Number of wireless clients on the AP
				
				XPath: /extremeWing-stats/rf_domain[name=key1]/wireless/ap-info[mac=key2]/num_clients"
			::= { extremeWingStatsRfdWlApInfoEntry 4 }

		
		-- 1.3.6.1.4.1.1916.2.131.50.1.4.3.2.1.1.1.5
		extremeWingStatsRfdWlApInfoLastCalTime OBJECT-TYPE
			SYNTAX DisplayString
			MAX-ACCESS read-only
			STATUS current
			DESCRIPTION
				"Last Smart-RF Calibration time on the AP
				
				XPath: /extremeWing-stats/rf_domain[name=key1]/wireless/ap-info[mac=key2]/last_cal_time"
			::= { extremeWingStatsRfdWlApInfoEntry 5 }

		
		-- 1.3.6.1.4.1.1916.2.131.50.1.4.3.2.1.1.1.6
		extremeWingStatsRfdWlApInfoType OBJECT-TYPE
			SYNTAX DisplayString
			MAX-ACCESS read-only
			STATUS current
			DESCRIPTION
				"AP device type
				
				XPath: /extremeWing-stats/rf_domain[name=key1]/wireless/ap-info[mac=key2]/type"
			::= { extremeWingStatsRfdWlApInfoEntry 6 }

		
		-- 1.3.6.1.4.1.1916.2.131.50.1.4.3.2.1.1.1.7
		extremeWingStatsRfdWlApInfoStatsMode OBJECT-TYPE
			SYNTAX DisplayString
			MAX-ACCESS read-only
			STATUS current
			DESCRIPTION
				"Statistics update mode
				
				XPath: /extremeWing-stats/rf_domain[name=key1]/wireless/ap-info[mac=key2]/stats_mode"
			::= { extremeWingStatsRfdWlApInfoEntry 7 }

		
		-- 1.3.6.1.4.1.1916.2.131.50.1.4.3.2.1.1.1.8
		extremeWingStatsRfdWlApInfoStatsInterval OBJECT-TYPE
			SYNTAX Unsigned32
			MAX-ACCESS read-only
			STATUS current
			DESCRIPTION
				"The current statistics update interval in seconds
				
				XPath: /extremeWing-stats/rf_domain[name=key1]/wireless/ap-info[mac=key2]/stats_interval"
			::= { extremeWingStatsRfdWlApInfoEntry 8 }

		
		-- 1.3.6.1.4.1.1916.2.131.50.1.4.3.2.1.1.1.9
		extremeWingStatsRfdWlApInfoHostname OBJECT-TYPE
			SYNTAX DisplayString
			MAX-ACCESS read-only
			STATUS current
			DESCRIPTION
				"Hostname of the AP
				
				XPath: /extremeWing-stats/rf_domain[name=key1]/wireless/ap-info[mac=key2]/hostname"
			::= { extremeWingStatsRfdWlApInfoEntry 9 }

		
		-- 1.3.6.1.4.1.1916.2.131.50.1.4.3.2.1.1.1.10
		extremeWingStatsRfdWlApInfoRfDomainName OBJECT-TYPE
			SYNTAX DisplayString
			MAX-ACCESS read-only
			STATUS current
			DESCRIPTION
				"RF Domain name of the AP
				
				XPath: /extremeWing-stats/rf_domain[name=key1]/wireless/ap-info[mac=key2]/rf_domain_name"
			::= { extremeWingStatsRfdWlApInfoEntry 10 }

		
		-- 1.3.6.1.4.1.1916.2.131.50.1.4.3.2.1.1.1.11
		extremeWingStatsRfdWlApInfoLocation OBJECT-TYPE
			SYNTAX DisplayString
			MAX-ACCESS read-only
			STATUS current
			DESCRIPTION
				"Location description of the AP
				
				XPath: /extremeWing-stats/rf_domain[name=key1]/wireless/ap-info[mac=key2]/location"
			::= { extremeWingStatsRfdWlApInfoEntry 11 }

		
		-- 1.3.6.1.4.1.1916.2.131.50.1.4.3.2.1.1.1.12
		extremeWingStatsRfdWlApInfoAdoptedTo OBJECT-TYPE
			SYNTAX MacAddress
			MAX-ACCESS read-only
			STATUS current
			DESCRIPTION
				"MAC address of the parent wireless controller that the AP
				is adopted to.
				
				XPath: /extremeWing-stats/rf_domain[name=key1]/wireless/ap-info[mac=key2]/adopted_to"
			::= { extremeWingStatsRfdWlApInfoEntry 12 }

		
		-- 1.3.6.1.4.1.1916.2.131.50.1.4.3.2.1.1.1.13
		extremeWingStatsRfdWlApInfoIp OBJECT-TYPE
			SYNTAX DisplayString
			MAX-ACCESS read-only
			STATUS current
			DESCRIPTION
				"Adopted AP IP address.
								
				XPath: /extremeWing-stats/rf_domain[name=key1]/wireless/ap-info[mac=key2]/ip"
			::= { extremeWingStatsRfdWlApInfoEntry 13 }

		
-- /extremeWing-stats/rf_domain/wireless/client
		-- 1.3.6.1.4.1.1916.2.131.50.1.4.3.2.3
		extremeWingStatsRfdWlClient OBJECT IDENTIFIER ::= { extremeWingStatsRfdWl 3 }

		
		-- 1.3.6.1.4.1.1916.2.131.50.1.4.3.2.3.1
		extremeWingStatsRfdWlClientTable OBJECT-TYPE
			SYNTAX SEQUENCE OF ExtremeWingStatsRfdWlClientEntry
			MAX-ACCESS not-accessible
			STATUS current
			DESCRIPTION
				"Status of wireless clients associated currently on RF Domain.
				
				/extremeWing-stats/rf_domain/wireless/client"
			::= { extremeWingStatsRfdWlClient 1 }

		
		-- 1.3.6.1.4.1.1916.2.131.50.1.4.3.2.3.1.1
		extremeWingStatsRfdWlClientEntry OBJECT-TYPE
			SYNTAX ExtremeWingStatsRfdWlClientEntry
			MAX-ACCESS not-accessible
			STATUS current
			DESCRIPTION
				"An entry in the table"
			INDEX { extremeWingStatsRfdName, extremeWingStatsRfdWlClientMac }
			::= { extremeWingStatsRfdWlClientTable 1 }

		
		ExtremeWingStatsRfdWlClientEntry ::=
			SEQUENCE { 
				extremeWingStatsRfdWlClientMac
					MacAddress,
				extremeWingStatsRfdWlClientMacName
					DisplayString,
				extremeWingStatsRfdWlClientVendor
					DisplayString,
				extremeWingStatsRfdWlClientBss
					MacAddress,
				extremeWingStatsRfdWlClientAp
					MacAddress,
				extremeWingStatsRfdWlClientRadioNum
					Unsigned32,
				extremeWingStatsRfdWlClientRadioType
					DisplayString,
				extremeWingStatsRfdWlClientRadioEnc
					DisplayString,
				extremeWingStatsRfdWlClientRadioAuth
					DisplayString,
				extremeWingStatsRfdWlClientWlan
					DisplayString,
				extremeWingStatsRfdWlClientState
					DisplayString,
				extremeWingStatsRfdWlClientHotspotAuthed
					TruthValue,
				extremeWingStatsRfdWlClientVlan
					Unsigned32,
				extremeWingStatsRfdWlClientUserName
					DisplayString,
				extremeWingStatsRfdWlClientIp
					DisplayString,
				extremeWingStatsRfdWlClientRfdName
					DisplayString,
				extremeWingStatsRfdWlClientHostname
					DisplayString,
				extremeWingStatsRfdWlClientLocation
					DisplayString,
				extremeWingStatsRfdWlClientRadioId
					DisplayString,
				extremeWingStatsRfdWlClientRadioAlias
					DisplayString
			 }

		-- 1.3.6.1.4.1.1916.2.131.50.1.4.3.2.3.1.1.1
		extremeWingStatsRfdWlClientMac OBJECT-TYPE
			SYNTAX MacAddress
			MAX-ACCESS read-only
			STATUS current
			DESCRIPTION
				"Client MAC
				
				XPath: /extremeWing-stats/rf_domain[name=key1]/wireless/client[mac=key2]/mac"
			::= { extremeWingStatsRfdWlClientEntry 1 }

		
		-- 1.3.6.1.4.1.1916.2.131.50.1.4.3.2.3.1.1.2
		extremeWingStatsRfdWlClientMacName OBJECT-TYPE
			SYNTAX DisplayString
			MAX-ACCESS read-only
			STATUS current
			DESCRIPTION
				"Hostname of the client which could be obtained from
				packet sniffing or by manually configured via
				mac-name configuration.
				
				XPath: /extremeWing-stats/rf_domain[name=key1]/wireless/client[mac=key2]/hostname"
			::= { extremeWingStatsRfdWlClientEntry 2 }

		
		-- 1.3.6.1.4.1.1916.2.131.50.1.4.3.2.3.1.1.3
		extremeWingStatsRfdWlClientVendor OBJECT-TYPE
			SYNTAX DisplayString
			MAX-ACCESS read-only
			STATUS current
			DESCRIPTION
				"Client vendor name based on the MAC OUI lookup
				
				XPath: /extremeWing-stats/rf_domain[name=key1]/wireless/client[mac=key2]/vendor"
			::= { extremeWingStatsRfdWlClientEntry 3 }

		
		-- 1.3.6.1.4.1.1916.2.131.50.1.4.3.2.3.1.1.4
		extremeWingStatsRfdWlClientBss OBJECT-TYPE
			SYNTAX MacAddress
			MAX-ACCESS read-only
			STATUS current
			DESCRIPTION
				"BSSID where the client is associated
				
				XPath: /extremeWing-stats/rf_domain[name=key1]/wireless/client[mac=key2]/bss"
			::= { extremeWingStatsRfdWlClientEntry 4 }

		
		-- 1.3.6.1.4.1.1916.2.131.50.1.4.3.2.3.1.1.5
		extremeWingStatsRfdWlClientAp OBJECT-TYPE
			SYNTAX MacAddress
			MAX-ACCESS read-only
			STATUS current
			DESCRIPTION
				"MAC address of the AP where the client is associated
				
				XPath: /extremeWing-stats/rf_domain[name=key1]/wireless/client[mac=key2]/ap"
			::= { extremeWingStatsRfdWlClientEntry 5 }

		
		-- 1.3.6.1.4.1.1916.2.131.50.1.4.3.2.3.1.1.6
		extremeWingStatsRfdWlClientRadioNum OBJECT-TYPE
			SYNTAX Unsigned32
			MAX-ACCESS read-only
			STATUS current
			DESCRIPTION
				"Radio number on AP where the client is associated
				
				XPath: /extremeWing-stats/rf_domain[name=key1]/wireless/client[mac=key2]/radio_num"
			::= { extremeWingStatsRfdWlClientEntry 6 }

		
		-- 1.3.6.1.4.1.1916.2.131.50.1.4.3.2.3.1.1.7
		extremeWingStatsRfdWlClientRadioType OBJECT-TYPE
			SYNTAX DisplayString
			MAX-ACCESS read-only
			STATUS current
			DESCRIPTION
				"802.11 radio-type of the client
				
				XPath: /extremeWing-stats/rf_domain[name=key1]/wireless/client[mac=key2]/radio_type"
			::= { extremeWingStatsRfdWlClientEntry 7 }

		
		-- 1.3.6.1.4.1.1916.2.131.50.1.4.3.2.3.1.1.8
		extremeWingStatsRfdWlClientRadioEnc OBJECT-TYPE
			SYNTAX DisplayString
			MAX-ACCESS read-only
			STATUS current
			DESCRIPTION
				"Encryption type
				
				XPath: /extremeWing-stats/rf_domain[name=key1]/wireless/client[mac=key2]/enc"
			::= { extremeWingStatsRfdWlClientEntry 8 }

		
		-- 1.3.6.1.4.1.1916.2.131.50.1.4.3.2.3.1.1.9
		extremeWingStatsRfdWlClientRadioAuth OBJECT-TYPE
			SYNTAX DisplayString
			MAX-ACCESS read-only
			STATUS current
			DESCRIPTION
				"Authentication type
				
				XPath: /extremeWing-stats/rf_domain[name=key1]/wireless/client[mac=key2]/auth"
			::= { extremeWingStatsRfdWlClientEntry 9 }

		
		-- 1.3.6.1.4.1.1916.2.131.50.1.4.3.2.3.1.1.10
		extremeWingStatsRfdWlClientWlan OBJECT-TYPE
			SYNTAX DisplayString
			MAX-ACCESS read-only
			STATUS current
			DESCRIPTION
				"WLAN where the client is associated
				
				XPath: /extremeWing-stats/rf_domain[name=key1]/wireless/client[mac=key2]/wlan"
			::= { extremeWingStatsRfdWlClientEntry 10 }

		
		-- 1.3.6.1.4.1.1916.2.131.50.1.4.3.2.3.1.1.11
		extremeWingStatsRfdWlClientState OBJECT-TYPE
			SYNTAX DisplayString
			MAX-ACCESS read-only
			STATUS current
			DESCRIPTION
				"Current state of the client
				
				XPath: /extremeWing-stats/rf_domain[name=key1]/wireless/client[mac=key2]/state"
			::= { extremeWingStatsRfdWlClientEntry 11 }

		
		-- 1.3.6.1.4.1.1916.2.131.50.1.4.3.2.3.1.1.12
		extremeWingStatsRfdWlClientHotspotAuthed OBJECT-TYPE
			SYNTAX TruthValue
			MAX-ACCESS read-only
			STATUS current
			DESCRIPTION
				"Whether the client has succeeded in guest access
				authentication.
				
				XPath: /extremeWing-stats/rf_domain[name=key1]/wireless/client[mac=key2]/hotspot_authed"
			::= { extremeWingStatsRfdWlClientEntry 12 }

		
		-- 1.3.6.1.4.1.1916.2.131.50.1.4.3.2.3.1.1.13
		extremeWingStatsRfdWlClientVlan OBJECT-TYPE
			SYNTAX Unsigned32
			MAX-ACCESS read-only
			STATUS current
			DESCRIPTION
				"The VLAN assigned to the client
				
				XPath: /extremeWing-stats/rf_domain[name=key1]/wireless/client[mac=key2]/vlan"
			::= { extremeWingStatsRfdWlClientEntry 13 }

		
		-- 1.3.6.1.4.1.1916.2.131.50.1.4.3.2.3.1.1.14
		extremeWingStatsRfdWlClientUserName OBJECT-TYPE
			SYNTAX DisplayString
			MAX-ACCESS read-only
			STATUS current
			DESCRIPTION
				"Username of the client, if available
				
				XPath: /extremeWing-stats/rf_domain[name=key1]/wireless/client[mac=key2]/username"
			::= { extremeWingStatsRfdWlClientEntry 14 }

		
		-- 1.3.6.1.4.1.1916.2.131.50.1.4.3.2.3.1.1.15
		extremeWingStatsRfdWlClientIp OBJECT-TYPE
			SYNTAX DisplayString
			MAX-ACCESS read-only
			STATUS current
			DESCRIPTION
				"IP address of the client (if known)
				
				XPath: /extremeWing-stats/rf_domain[name=key1]/wireless/client[mac=key2]/ip"
			::= { extremeWingStatsRfdWlClientEntry 15 }

		
		-- 1.3.6.1.4.1.1916.2.131.50.1.4.3.2.3.1.1.16
		extremeWingStatsRfdWlClientRfdName OBJECT-TYPE
			SYNTAX DisplayString
			MAX-ACCESS read-only
			STATUS current
			DESCRIPTION
				"RF Domain that the client is in
				
				XPath: /extremeWing-stats/rf_domain[name=key1]/wireless/client[mac=key2]/rf_domain_name"
			::= { extremeWingStatsRfdWlClientEntry 16 }

		
		-- 1.3.6.1.4.1.1916.2.131.50.1.4.3.2.3.1.1.17
		extremeWingStatsRfdWlClientHostname OBJECT-TYPE
			SYNTAX DisplayString
			MAX-ACCESS read-only
			STATUS current
			DESCRIPTION
				"Hostname of the AP the client is associated to
				
				XPath: /extremeWing-stats/rf_domain[name=key1]/wireless/client[mac=key2]/ap_hostname"
			::= { extremeWingStatsRfdWlClientEntry 17 }

		
		-- 1.3.6.1.4.1.1916.2.131.50.1.4.3.2.3.1.1.18
		extremeWingStatsRfdWlClientLocation OBJECT-TYPE
			SYNTAX DisplayString
			MAX-ACCESS read-only
			STATUS current
			DESCRIPTION
				"Location of the AP the client is associated to.
				
				XPath: /extremeWing-stats/rf_domain[name=key1]/wireless/client[mac=key2]/location"
			::= { extremeWingStatsRfdWlClientEntry 18 }

		
		-- 1.3.6.1.4.1.1916.2.131.50.1.4.3.2.3.1.1.19
		extremeWingStatsRfdWlClientRadioId OBJECT-TYPE
			SYNTAX DisplayString
			MAX-ACCESS read-only
			STATUS current
			DESCRIPTION
				"Unique ID for its associated radio in the form of
				AP-MAC:R%d. E.g., 00-A0-F8-00-00-00:R1
				
				XPath: /extremeWing-stats/rf_domain[name=key1]/wireless/client[mac=key2]/radio_id"
			::= { extremeWingStatsRfdWlClientEntry 19 }

		
		-- 1.3.6.1.4.1.1916.2.131.50.1.4.3.2.3.1.1.20
		extremeWingStatsRfdWlClientRadioAlias OBJECT-TYPE
			SYNTAX DisplayString
			MAX-ACCESS read-only
			STATUS current
			DESCRIPTION
				"A radio ID alias of its associated radio in the form of
				hostname:R%d. E.g., wm3400-22A24E:R1
				
				XPath: /extremeWing-stats/rf_domain[name=key1]/wireless/client[mac=key2]/radio_alias"
			::= { extremeWingStatsRfdWlClientEntry 20 }

		
-- /extremeWing-stats/rf_domain/wireless/client-details
		-- 1.3.6.1.4.1.1916.2.131.50.1.4.3.2.4
		extremeWingStatsRfdWlClientDetail OBJECT IDENTIFIER ::= { extremeWingStatsRfdWl 4 }

		
		-- 1.3.6.1.4.1.1916.2.131.50.1.4.3.2.4.1
		extremeWingStatsRfdWlClientDetailTable OBJECT-TYPE
			SYNTAX SEQUENCE OF ExtremeWingStatsRfdWlClientDetailEntry
			MAX-ACCESS not-accessible
			STATUS current
			DESCRIPTION
				"Detailed status of wireless clients associated currently
				on RF Domain.
				
				/extremeWing-stats/rf_domain/wireless/client-details"
			::= { extremeWingStatsRfdWlClientDetail 1 }

		
		-- 1.3.6.1.4.1.1916.2.131.50.1.4.3.2.4.1.1
		extremeWingStatsRfdWlClientDetailEntry OBJECT-TYPE
			SYNTAX ExtremeWingStatsRfdWlClientDetailEntry
			MAX-ACCESS not-accessible
			STATUS current
			DESCRIPTION
				"An entry in the table"
			INDEX { extremeWingStatsRfdName, extremeWingStatsRfdWlClientDetailMac }
			::= { extremeWingStatsRfdWlClientDetailTable 1 }

		
		ExtremeWingStatsRfdWlClientDetailEntry ::=
			SEQUENCE { 
				extremeWingStatsRfdWlClientDetailMac
					MacAddress,
				extremeWingStatsRfdWlClientDetailMacName
					DisplayString,
				extremeWingStatsRfdWlClientDetailVendor
					DisplayString,
				extremeWingStatsRfdWlClientDetailBss
					MacAddress,
				extremeWingStatsRfdWlClientDetailAp
					MacAddress,
				extremeWingStatsRfdWlClientDetailRadioNum
					Unsigned32,
				extremeWingStatsRfdWlClientDetailRadioType
					DisplayString,
				extremeWingStatsRfdWlClientDetailEnc
					DisplayString,
				extremeWingStatsRfdWlClientDetailAuth
					DisplayString,
				extremeWingStatsRfdWlClientDetailWlan
					DisplayString,
				extremeWingStatsRfdWlClientDetailState
					DisplayString,
				extremeWingStatsRfdWlClientDetailHotspotAuthed
					TruthValue,
				extremeWingStatsRfdWlClientDetailVlan
					Unsigned32,
				extremeWingStatsRfdWlClientDetailUsername
					DisplayString,
				extremeWingStatsRfdWlClientDetailIp
					DisplayString,
				extremeWingStatsRfdWlClientDetailRfDomainName
					DisplayString,
				extremeWingStatsRfdWlClientDetailMc2ucStreams
					DisplayString,
				extremeWingStatsRfdWlClientDetailHostname
					DisplayString,
				extremeWingStatsRfdWlClientDetailLocation
					DisplayString,
				extremeWingStatsRfdWlClientDetailRadioId
					DisplayString,
				extremeWingStatsRfdWlClientDetailRadioAlias
					DisplayString,
				extremeWingStatsRfdWlClientDetailSsid
					DisplayString,
				extremeWingStatsRfdWlClientDetailAid
					Unsigned32,
				extremeWingStatsRfdWlClientDetailRates
					DisplayString,
				extremeWingStatsRfdWlClientDetailInPsp
					TruthValue,
				extremeWingStatsRfdWlClientDetailIsWmm
					TruthValue,
				extremeWingStatsRfdWlClientDetailUapsd
					DisplayString,
				extremeWingStatsRfdWlClientDetailSmPowersave
					DisplayString,
				extremeWingStatsRfdWlClientDetailHtCapable
					TruthValue,
				extremeWingStatsRfdWlClientDetailShortGi
					TruthValue,
				extremeWingStatsRfdWlClientDetailCurWidth40
					TruthValue,
				extremeWingStatsRfdWlClientDetailAmsduSize
					Unsigned32,
				extremeWingStatsRfdWlClientDetailAmpduSize
					Unsigned32,
				extremeWingStatsRfdWlClientDetailAmpduSpacing
					Unsigned32,
				extremeWingStatsRfdWlClientDetailRifs
					TruthValue,
				extremeWingStatsRfdWlClientDetailLastActive
					Unsigned32,
				extremeWingStatsRfdWlClientDetailLastAssoc
					Unsigned32,
				extremeWingStatsRfdWlClientDetailSessTime
					Unsigned32,
				extremeWingStatsRfdWlClientDetailIdleTime
					Unsigned32,
				extremeWingStatsRfdWlClientDetailMaxPhyRate
					Unsigned32,
				extremeWingStatsRfdWlClientDetailMaxUserRate
					Unsigned32,
				extremeWingStatsRfdWlClientDetailIsVoice
					TruthValue,
				extremeWingStatsRfdWlClientDetailIsCallActive
					TruthValue
			 }

		-- 1.3.6.1.4.1.1916.2.131.50.1.4.3.2.4.1.1.1
		extremeWingStatsRfdWlClientDetailMac OBJECT-TYPE
			SYNTAX MacAddress
			MAX-ACCESS read-only
			STATUS current
			DESCRIPTION
				"Client MAC
				
				XPath: /extremeWing-stats/rf_domain[name=key1]/wireless/client-details[mac=key2]/mac"
			::= { extremeWingStatsRfdWlClientDetailEntry 1 }

		
		-- 1.3.6.1.4.1.1916.2.131.50.1.4.3.2.4.1.1.2
		extremeWingStatsRfdWlClientDetailMacName OBJECT-TYPE
			SYNTAX DisplayString
			MAX-ACCESS read-only
			STATUS current
			DESCRIPTION
				"Hostname of the client which could be obtained from
				packet sniffing or by manually configured via
				mac-name configuration.
				
				XPath: /extremeWing-stats/rf_domain[name=key1]/wireless/client-details[mac=key2]/hostname"
			::= { extremeWingStatsRfdWlClientDetailEntry 2 }

		
		-- 1.3.6.1.4.1.1916.2.131.50.1.4.3.2.4.1.1.3
		extremeWingStatsRfdWlClientDetailVendor OBJECT-TYPE
			SYNTAX DisplayString
			MAX-ACCESS read-only
			STATUS current
			DESCRIPTION
				"Client vendor name based on the MAC OUI lookup
				
				XPath: /extremeWing-stats/rf_domain[name=key1]/wireless/client-details[mac=key2]/vendor"
			::= { extremeWingStatsRfdWlClientDetailEntry 3 }

		
		-- 1.3.6.1.4.1.1916.2.131.50.1.4.3.2.4.1.1.4
		extremeWingStatsRfdWlClientDetailBss OBJECT-TYPE
			SYNTAX MacAddress
			MAX-ACCESS read-only
			STATUS current
			DESCRIPTION
				"BSSID where the client is associated
				
				XPath: /extremeWing-stats/rf_domain[name=key1]/wireless/client-details[mac=key2]/bss"
			::= { extremeWingStatsRfdWlClientDetailEntry 4 }

		
		-- 1.3.6.1.4.1.1916.2.131.50.1.4.3.2.4.1.1.5
		extremeWingStatsRfdWlClientDetailAp OBJECT-TYPE
			SYNTAX MacAddress
			MAX-ACCESS read-only
			STATUS current
			DESCRIPTION
				"MAC address of the AP where the client is associated
				
				XPath: /extremeWing-stats/rf_domain[name=key1]/wireless/client-details[mac=key2]/ap"
			::= { extremeWingStatsRfdWlClientDetailEntry 5 }

		
		-- 1.3.6.1.4.1.1916.2.131.50.1.4.3.2.4.1.1.6
		extremeWingStatsRfdWlClientDetailRadioNum OBJECT-TYPE
			SYNTAX Unsigned32
			MAX-ACCESS read-only
			STATUS current
			DESCRIPTION
				"Radio number on AP where the client is associated
				
				XPath: /extremeWing-stats/rf_domain[name=key1]/wireless/client-details[mac=key2]/radio_num"
			::= { extremeWingStatsRfdWlClientDetailEntry 6 }

		
		-- 1.3.6.1.4.1.1916.2.131.50.1.4.3.2.4.1.1.7
		extremeWingStatsRfdWlClientDetailRadioType OBJECT-TYPE
			SYNTAX DisplayString
			MAX-ACCESS read-only
			STATUS current
			DESCRIPTION
				"802.11 radio-type of the client
				
				XPath: /extremeWing-stats/rf_domain[name=key1]/wireless/client-details[mac=key2]/radio_type"
			::= { extremeWingStatsRfdWlClientDetailEntry 7 }

		
		-- 1.3.6.1.4.1.1916.2.131.50.1.4.3.2.4.1.1.8
		extremeWingStatsRfdWlClientDetailEnc OBJECT-TYPE
			SYNTAX DisplayString
			MAX-ACCESS read-only
			STATUS current
			DESCRIPTION
				"Encryption type
				
				XPath: /extremeWing-stats/rf_domain[name=key1]/wireless/client-details[mac=key2]/enc"
			::= { extremeWingStatsRfdWlClientDetailEntry 8 }

		
		-- 1.3.6.1.4.1.1916.2.131.50.1.4.3.2.4.1.1.9
		extremeWingStatsRfdWlClientDetailAuth OBJECT-TYPE
			SYNTAX DisplayString
			MAX-ACCESS read-only
			STATUS current
			DESCRIPTION
				"Authentication type
				
				XPath: /extremeWing-stats/rf_domain[name=key1]/wireless/client-details[mac=key2]/auth"
			::= { extremeWingStatsRfdWlClientDetailEntry 9 }

		
		-- 1.3.6.1.4.1.1916.2.131.50.1.4.3.2.4.1.1.10
		extremeWingStatsRfdWlClientDetailWlan OBJECT-TYPE
			SYNTAX DisplayString
			MAX-ACCESS read-only
			STATUS current
			DESCRIPTION
				"WLAN where the client is associated
				
				XPath: /extremeWing-stats/rf_domain[name=key1]/wireless/client-details[mac=key2]/wlan"
			::= { extremeWingStatsRfdWlClientDetailEntry 10 }

		
		-- 1.3.6.1.4.1.1916.2.131.50.1.4.3.2.4.1.1.11
		extremeWingStatsRfdWlClientDetailState OBJECT-TYPE
			SYNTAX DisplayString
			MAX-ACCESS read-only
			STATUS current
			DESCRIPTION
				"Current state of the client
				
				XPath: /extremeWing-stats/rf_domain[name=key1]/wireless/client-details[mac=key2]/state"
			::= { extremeWingStatsRfdWlClientDetailEntry 11 }

		
		-- 1.3.6.1.4.1.1916.2.131.50.1.4.3.2.4.1.1.12
		extremeWingStatsRfdWlClientDetailHotspotAuthed OBJECT-TYPE
			SYNTAX TruthValue
			MAX-ACCESS read-only
			STATUS current
			DESCRIPTION
				"Whether the client has succeeded in guest access
				authentication.
				
				XPath: /extremeWing-stats/rf_domain[name=key1]/wireless/client-details[mac=key2]/hotspot_authed"
			::= { extremeWingStatsRfdWlClientDetailEntry 12 }

		
		-- 1.3.6.1.4.1.1916.2.131.50.1.4.3.2.4.1.1.13
		extremeWingStatsRfdWlClientDetailVlan OBJECT-TYPE
			SYNTAX Unsigned32
			MAX-ACCESS read-only
			STATUS current
			DESCRIPTION
				"The VLAN assigned to the client
				
				XPath: /extremeWing-stats/rf_domain[name=key1]/wireless/client-details[mac=key2]/vlan"
			::= { extremeWingStatsRfdWlClientDetailEntry 13 }

		
		-- 1.3.6.1.4.1.1916.2.131.50.1.4.3.2.4.1.1.14
		extremeWingStatsRfdWlClientDetailUsername OBJECT-TYPE
			SYNTAX DisplayString
			MAX-ACCESS read-only
			STATUS current
			DESCRIPTION
				"Username of the client, if available
				
				XPath: /extremeWing-stats/rf_domain[name=key1]/wireless/client-details[mac=key2]/username"
			::= { extremeWingStatsRfdWlClientDetailEntry 14 }

		
		-- 1.3.6.1.4.1.1916.2.131.50.1.4.3.2.4.1.1.15
		extremeWingStatsRfdWlClientDetailIp OBJECT-TYPE
			SYNTAX DisplayString
			MAX-ACCESS read-only
			STATUS current
			DESCRIPTION
				"IP address of the client (if known)
				
				XPath: /extremeWing-stats/rf_domain[name=key1]/wireless/client-details[mac=key2]/ip"
			::= { extremeWingStatsRfdWlClientDetailEntry 15 }

		
		-- 1.3.6.1.4.1.1916.2.131.50.1.4.3.2.4.1.1.16
		extremeWingStatsRfdWlClientDetailRfDomainName OBJECT-TYPE
			SYNTAX DisplayString
			MAX-ACCESS read-only
			STATUS current
			DESCRIPTION
				"RF Domain that the client is in
				
				XPath: /extremeWing-stats/rf_domain[name=key1]/wireless/client-details[mac=key2]/rf_domain_name"
			::= { extremeWingStatsRfdWlClientDetailEntry 16 }

		
		-- 1.3.6.1.4.1.1916.2.131.50.1.4.3.2.4.1.1.17
		extremeWingStatsRfdWlClientDetailMc2ucStreams OBJECT-TYPE
			SYNTAX DisplayString
			MAX-ACCESS read-only
			STATUS current
			DESCRIPTION
				"Accelerated multicast streams the client is registered for.
				
				XPath: /extremeWing-stats/rf_domain[name=key1]/wireless/client-details[mac=key2]/mc2uc_streams"
			::= { extremeWingStatsRfdWlClientDetailEntry 17 }

		
		-- 1.3.6.1.4.1.1916.2.131.50.1.4.3.2.4.1.1.18
		extremeWingStatsRfdWlClientDetailHostname OBJECT-TYPE
			SYNTAX DisplayString
			MAX-ACCESS read-only
			STATUS current
			DESCRIPTION
				"Hostname of the AP the client is associated to
				
				XPath: /extremeWing-stats/rf_domain[name=key1]/wireless/client-details[mac=key2]/ap_hostname"
			::= { extremeWingStatsRfdWlClientDetailEntry 18 }

		
		-- 1.3.6.1.4.1.1916.2.131.50.1.4.3.2.4.1.1.19
		extremeWingStatsRfdWlClientDetailLocation OBJECT-TYPE
			SYNTAX DisplayString
			MAX-ACCESS read-only
			STATUS current
			DESCRIPTION
				"Location of the AP the client is associated to
				
				XPath: /extremeWing-stats/rf_domain[name=key1]/wireless/client-details[mac=key2]/location"
			::= { extremeWingStatsRfdWlClientDetailEntry 19 }

		
		-- 1.3.6.1.4.1.1916.2.131.50.1.4.3.2.4.1.1.20
		extremeWingStatsRfdWlClientDetailRadioId OBJECT-TYPE
			SYNTAX DisplayString
			MAX-ACCESS read-only
			STATUS current
			DESCRIPTION
				"Unique ID for its associated radio in the form of
				AP-MAC:R%d. E.g., 00-A0-F8-00-00-00:R1
				
				XPath: /extremeWing-stats/rf_domain[name=key1]/wireless/client-details[mac=key2]/radio_id"
			::= { extremeWingStatsRfdWlClientDetailEntry 20 }

		
		-- 1.3.6.1.4.1.1916.2.131.50.1.4.3.2.4.1.1.21
		extremeWingStatsRfdWlClientDetailRadioAlias OBJECT-TYPE
			SYNTAX DisplayString
			MAX-ACCESS read-only
			STATUS current
			DESCRIPTION
				"A radio ID alias of its associated radio in the form of
				hostname:R%d. E.g., wm3400-22A24E:R1
				
				XPath: /extremeWing-stats/rf_domain[name=key1]/wireless/client-details[mac=key2]/radio_alias"
			::= { extremeWingStatsRfdWlClientDetailEntry 21 }

		
		-- 1.3.6.1.4.1.1916.2.131.50.1.4.3.2.4.1.1.22
		extremeWingStatsRfdWlClientDetailSsid OBJECT-TYPE
			SYNTAX DisplayString
			MAX-ACCESS read-only
			STATUS current
			DESCRIPTION
				"SSID of the WLAN where the client is associated
				
				XPath: /extremeWing-stats/rf_domain[name=key1]/wireless/client-details[mac=key2]/ssid"
			::= { extremeWingStatsRfdWlClientDetailEntry 22 }

		
		-- 1.3.6.1.4.1.1916.2.131.50.1.4.3.2.4.1.1.23
		extremeWingStatsRfdWlClientDetailAid OBJECT-TYPE
			SYNTAX Unsigned32
			MAX-ACCESS read-only
			STATUS current
			DESCRIPTION
				"802.11 association index of the client
				
				XPath: /extremeWing-stats/rf_domain[name=key1]/wireless/client-details[mac=key2]/aid"
			::= { extremeWingStatsRfdWlClientDetailEntry 23 }

		
		-- 1.3.6.1.4.1.1916.2.131.50.1.4.3.2.4.1.1.24
		extremeWingStatsRfdWlClientDetailRates OBJECT-TYPE
			SYNTAX DisplayString
			MAX-ACCESS read-only
			STATUS current
			DESCRIPTION
				"Data rates supported by the client
				
				XPath: /extremeWing-stats/rf_domain[name=key1]/wireless/client-details[mac=key2]/rates"
			::= { extremeWingStatsRfdWlClientDetailEntry 24 }

		
		-- 1.3.6.1.4.1.1916.2.131.50.1.4.3.2.4.1.1.25
		extremeWingStatsRfdWlClientDetailInPsp OBJECT-TYPE
			SYNTAX TruthValue
			MAX-ACCESS read-only
			STATUS current
			DESCRIPTION
				"Whether the client is currently in a power save mode
				
				XPath: /extremeWing-stats/rf_domain[name=key1]/wireless/client-details[mac=key2]/in_psp"
			::= { extremeWingStatsRfdWlClientDetailEntry 25 }

		
		-- 1.3.6.1.4.1.1916.2.131.50.1.4.3.2.4.1.1.26
		extremeWingStatsRfdWlClientDetailIsWmm OBJECT-TYPE
			SYNTAX TruthValue
			MAX-ACCESS read-only
			STATUS current
			DESCRIPTION
				"Whether the client is associated with support for WMM
				
				XPath: /extremeWing-stats/rf_domain[name=key1]/wireless/client-details[mac=key2]/is_wmm"
			::= { extremeWingStatsRfdWlClientDetailEntry 26 }

		
		-- 1.3.6.1.4.1.1916.2.131.50.1.4.3.2.4.1.1.27
		extremeWingStatsRfdWlClientDetailUapsd OBJECT-TYPE
			SYNTAX DisplayString
			MAX-ACCESS read-only
			STATUS current
			DESCRIPTION
				"Unscheduled APSD support by the client
				
				XPath: /extremeWing-stats/rf_domain[name=key1]/wireless/client-details[mac=key2]/uapsd"
			::= { extremeWingStatsRfdWlClientDetailEntry 27 }

		
		-- 1.3.6.1.4.1.1916.2.131.50.1.4.3.2.4.1.1.28
		extremeWingStatsRfdWlClientDetailSmPowersave OBJECT-TYPE
			SYNTAX DisplayString
			MAX-ACCESS read-only
			STATUS current
			DESCRIPTION
				"SM Powersave mode of this client (static|dynamic|off)
				
				XPath: /extremeWing-stats/rf_domain[name=key1]/wireless/client-details[mac=key2]/sm_powersave"
			::= { extremeWingStatsRfdWlClientDetailEntry 28 }

		
		-- 1.3.6.1.4.1.1916.2.131.50.1.4.3.2.4.1.1.29
		extremeWingStatsRfdWlClientDetailHtCapable OBJECT-TYPE
			SYNTAX TruthValue
			MAX-ACCESS read-only
			STATUS current
			DESCRIPTION
				"Whether this client supports 802.11n High-Throughput
				data-rates.
				
				XPath: /extremeWing-stats/rf_domain[name=key1]/wireless/client-details[mac=key2]/ht_capable"
			::= { extremeWingStatsRfdWlClientDetailEntry 29 }

		
		-- 1.3.6.1.4.1.1916.2.131.50.1.4.3.2.4.1.1.30
		extremeWingStatsRfdWlClientDetailShortGi OBJECT-TYPE
			SYNTAX TruthValue
			MAX-ACCESS read-only
			STATUS current
			DESCRIPTION
				"Whether short-guard interval is supported by the client.
				
				XPath: /extremeWing-stats/rf_domain[name=key1]/wireless/client-details[mac=key2]/short_gi"
			::= { extremeWingStatsRfdWlClientDetailEntry 30 }

		
		-- 1.3.6.1.4.1.1916.2.131.50.1.4.3.2.4.1.1.31
		extremeWingStatsRfdWlClientDetailCurWidth40 OBJECT-TYPE
			SYNTAX TruthValue
			MAX-ACCESS read-only
			STATUS current
			DESCRIPTION
				"Whether the client is 40MHz capable, or 20-only
				
				XPath: /extremeWing-stats/rf_domain[name=key1]/wireless/client-details[mac=key2]/current_width_40"
			::= { extremeWingStatsRfdWlClientDetailEntry 31 }

		
		-- 1.3.6.1.4.1.1916.2.131.50.1.4.3.2.4.1.1.32
		extremeWingStatsRfdWlClientDetailAmsduSize OBJECT-TYPE
			SYNTAX Unsigned32
			MAX-ACCESS read-only
			STATUS current
			DESCRIPTION
				"Maximum size of amsdu supported by the client
				
				XPath: /extremeWing-stats/rf_domain[name=key1]/wireless/client-details[mac=key2]/amsdu_size"
			::= { extremeWingStatsRfdWlClientDetailEntry 32 }

		
		-- 1.3.6.1.4.1.1916.2.131.50.1.4.3.2.4.1.1.33
		extremeWingStatsRfdWlClientDetailAmpduSize OBJECT-TYPE
			SYNTAX Unsigned32
			MAX-ACCESS read-only
			STATUS current
			DESCRIPTION
				"Maximum size of ampdu supported by the client
				
				XPath: /extremeWing-stats/rf_domain[name=key1]/wireless/client-details[mac=key2]/ampdu_size"
			::= { extremeWingStatsRfdWlClientDetailEntry 33 }

		
		-- 1.3.6.1.4.1.1916.2.131.50.1.4.3.2.4.1.1.34
		extremeWingStatsRfdWlClientDetailAmpduSpacing OBJECT-TYPE
			SYNTAX Unsigned32
			UNITS "microSeconds"
			MAX-ACCESS read-only
			STATUS current
			DESCRIPTION
				"Interframe spacing of 802.11n aggregate MPDUs
				
				XPath: /extremeWing-stats/rf_domain[name=key1]/wireless/client-details[mac=key2]/ampdu_spacing"
			::= { extremeWingStatsRfdWlClientDetailEntry 34 }

		
		-- 1.3.6.1.4.1.1916.2.131.50.1.4.3.2.4.1.1.35
		extremeWingStatsRfdWlClientDetailRifs OBJECT-TYPE
			SYNTAX TruthValue
			MAX-ACCESS read-only
			STATUS current
			DESCRIPTION
				"Whether RIFS (Reduced InterFrame Spacing) supported
				by the client.
				
				XPath: /extremeWing-stats/rf_domain[name=key1]/wireless/client-details[mac=key2]/rifs"
			::= { extremeWingStatsRfdWlClientDetailEntry 35 }

		
		-- 1.3.6.1.4.1.1916.2.131.50.1.4.3.2.4.1.1.36
		extremeWingStatsRfdWlClientDetailLastActive OBJECT-TYPE
			SYNTAX Unsigned32
			MAX-ACCESS read-only
			STATUS current
			DESCRIPTION
				"The seconds ago the last packet was received from the client.
				
				XPath: /extremeWing-stats/rf_domain[name=key1]/wireless/client-details[mac=key2]/last_active"
			::= { extremeWingStatsRfdWlClientDetailEntry 36 }

		
		-- 1.3.6.1.4.1.1916.2.131.50.1.4.3.2.4.1.1.37
		extremeWingStatsRfdWlClientDetailLastAssoc OBJECT-TYPE
			SYNTAX Unsigned32
			MAX-ACCESS read-only
			STATUS current
			DESCRIPTION
				"The seconds ago the last association of the client to AP.
				
				XPath: /extremeWing-stats/rf_domain[name=key1]/wireless/client-details[mac=key2]/last_assoc"
			::= { extremeWingStatsRfdWlClientDetailEntry 37 }

		
		-- 1.3.6.1.4.1.1916.2.131.50.1.4.3.2.4.1.1.38
		extremeWingStatsRfdWlClientDetailSessTime OBJECT-TYPE
			SYNTAX Unsigned32
			MAX-ACCESS read-only
			STATUS current
			DESCRIPTION
				"The time in seconds for which this session was made active
				
				XPath: /extremeWing-stats/rf_domain[name=key1]/wireless/client-details[mac=key2]/sess_time"
			::= { extremeWingStatsRfdWlClientDetailEntry 38 }

		
		-- 1.3.6.1.4.1.1916.2.131.50.1.4.3.2.4.1.1.39
		extremeWingStatsRfdWlClientDetailIdleTime OBJECT-TYPE
			SYNTAX Unsigned32
			MAX-ACCESS read-only
			STATUS current
			DESCRIPTION
				"The number of seconds of inactivity after which the client
				will be disassociated.
				
				XPath: /extremeWing-stats/rf_domain[name=key1]/wireless/client-details[mac=key2]/idle_time"
			::= { extremeWingStatsRfdWlClientDetailEntry 39 }

		
		-- 1.3.6.1.4.1.1916.2.131.50.1.4.3.2.4.1.1.40
		extremeWingStatsRfdWlClientDetailMaxPhyRate OBJECT-TYPE
			SYNTAX Unsigned32
			UNITS "kbps"
			MAX-ACCESS read-only
			STATUS current
			DESCRIPTION
				"Maximum physical data rate
				
				XPath: /extremeWing-stats/rf_domain[name=key1]/wireless/client-details[mac=key2]/max_phy_rate"
			::= { extremeWingStatsRfdWlClientDetailEntry 40 }

		
		-- 1.3.6.1.4.1.1916.2.131.50.1.4.3.2.4.1.1.41
		extremeWingStatsRfdWlClientDetailMaxUserRate OBJECT-TYPE
			SYNTAX Unsigned32
			UNITS "kbps"
			MAX-ACCESS read-only
			STATUS current
			DESCRIPTION
				"Theoretic maximum user-level data rate
				
				XPath: /extremeWing-stats/rf_domain[name=key1]/wireless/client-details[mac=key2]/max_user_rate"
			::= { extremeWingStatsRfdWlClientDetailEntry 41 }

		
		-- 1.3.6.1.4.1.1916.2.131.50.1.4.3.2.4.1.1.42
		extremeWingStatsRfdWlClientDetailIsVoice OBJECT-TYPE
			SYNTAX TruthValue
			MAX-ACCESS read-only
			STATUS current
			DESCRIPTION
				"Whether client is classified as voice device or not
				
				XPath: /extremeWing-stats/rf_domain[name=key1]/wireless/client-details[mac=key2]/is_voice"
			::= { extremeWingStatsRfdWlClientDetailEntry 42 }

		
		-- 1.3.6.1.4.1.1916.2.131.50.1.4.3.2.4.1.1.43
		extremeWingStatsRfdWlClientDetailIsCallActive OBJECT-TYPE
			SYNTAX TruthValue
			MAX-ACCESS read-only
			STATUS current
			DESCRIPTION
				"Whether the client is currently on active voice call,
				applicable to voice client only.
				
				XPath: /extremeWing-stats/rf_domain[name=key1]/wireless/client-details[mac=key2]/is_call_active"
			::= { extremeWingStatsRfdWlClientDetailEntry 43 }

		
-- /extremeWing-stats/rf_domain/wireless/client-stats
		-- 1.3.6.1.4.1.1916.2.131.50.1.4.3.2.5
		extremeWingStatsRfdWlClientStat OBJECT IDENTIFIER ::= { extremeWingStatsRfdWl 5 }

		
		-- 1.3.6.1.4.1.1916.2.131.50.1.4.3.2.5.1
		extremeWingStatsRfdWlClientStatTable OBJECT-TYPE
			SYNTAX SEQUENCE OF ExtremeWingStatsRfdWlClientStatEntry
			MAX-ACCESS not-accessible
			STATUS current
			DESCRIPTION
				"Statistical information of wireless clients associated
				currently on RF Domain
				
				/extremeWing-stats/rf_domain/wireless/client-stats"
			::= { extremeWingStatsRfdWlClientStat 1 }

		
		-- 1.3.6.1.4.1.1916.2.131.50.1.4.3.2.5.1.1
		extremeWingStatsRfdWlClientStatEntry OBJECT-TYPE
			SYNTAX ExtremeWingStatsRfdWlClientStatEntry
			MAX-ACCESS not-accessible
			STATUS current
			DESCRIPTION
				"An entry in the table"
			INDEX { extremeWingStatsRfdName, extremeWingStatsRfdWlClientStatMac }
			::= { extremeWingStatsRfdWlClientStatTable 1 }

		
		ExtremeWingStatsRfdWlClientStatEntry ::=
			SEQUENCE { 
				extremeWingStatsRfdWlClientStatMac
					MacAddress,
				extremeWingStatsRfdWlClientStatMacName
					DisplayString,
				extremeWingStatsRfdWlClientStatVendor
					DisplayString,
				extremeWingStatsRfdWlClientStatAp
					MacAddress,
				extremeWingStatsRfdWlClientStatTxBytes
					Counter64,
				extremeWingStatsRfdWlClientStatRxBytes
					Counter64,
				extremeWingStatsRfdWlClientStatTxPkts
					Counter64,
				extremeWingStatsRfdWlClientStatRxPkts
					Counter64,
				extremeWingStatsRfdWlClientStatTxDropped
					Counter64,
				extremeWingStatsRfdWlClientStatRxErrors
					Counter64,
				extremeWingStatsRfdWlClientStatTIndex
					Integer32,
				extremeWingStatsRfdWlClientStatTxBps
					Unsigned32,
				extremeWingStatsRfdWlClientStatRxBps
					Unsigned32,
				extremeWingStatsRfdWlClientStatSignal
					Integer32,
				extremeWingStatsRfdWlClientStatNoise
					Integer32,
				extremeWingStatsRfdWlClientStatSnr
					Integer32,
				extremeWingStatsRfdWlClientStatTxRate
					Unsigned32,
				extremeWingStatsRfdWlClientStatRxRate
					Unsigned32,
				extremeWingStatsRfdWlClientStatErrorRate
					Unsigned32,
				extremeWingStatsRfdWlClientStatQIndex
					Integer32
			 }

		-- 1.3.6.1.4.1.1916.2.131.50.1.4.3.2.5.1.1.1
		extremeWingStatsRfdWlClientStatMac OBJECT-TYPE
			SYNTAX MacAddress
			MAX-ACCESS read-only
			STATUS current
			DESCRIPTION
				"Client MAC
				
				XPath: /extremeWing-stats/rf_domain[name=key1]/wireless/client-stats[mac=key2]/mac"
			::= { extremeWingStatsRfdWlClientStatEntry 1 }

		
		-- 1.3.6.1.4.1.1916.2.131.50.1.4.3.2.5.1.1.2
		extremeWingStatsRfdWlClientStatMacName OBJECT-TYPE
			SYNTAX DisplayString
			MAX-ACCESS read-only
			STATUS current
			DESCRIPTION
				"Hostname of the client which could be obtained from
				packet sniffing or by manually configured via
				mac-name configuration.
				
				XPath: /extremeWing-stats/rf_domain[name=key1]/wireless/client-stats[mac=key2]/hostname"
			::= { extremeWingStatsRfdWlClientStatEntry 2 }

		
		-- 1.3.6.1.4.1.1916.2.131.50.1.4.3.2.5.1.1.3
		extremeWingStatsRfdWlClientStatVendor OBJECT-TYPE
			SYNTAX DisplayString
			MAX-ACCESS read-only
			STATUS current
			DESCRIPTION
				"Client vendor name based on the MAC OUI lookup
				
				XPath: /extremeWing-stats/rf_domain[name=key1]/wireless/client-stats[mac=key2]/vendor"
			::= { extremeWingStatsRfdWlClientStatEntry 3 }

		
		-- 1.3.6.1.4.1.1916.2.131.50.1.4.3.2.5.1.1.4
		extremeWingStatsRfdWlClientStatAp OBJECT-TYPE
			SYNTAX MacAddress
			MAX-ACCESS read-only
			STATUS current
			DESCRIPTION
				"MAC address of AP where the client is associated.
				
				XPath: /extremeWing-stats/rf_domain[name=key1]/wireless/client-stats[mac=key2]/ap"
			::= { extremeWingStatsRfdWlClientStatEntry 4 }

		
		-- 1.3.6.1.4.1.1916.2.131.50.1.4.3.2.5.1.1.5
		extremeWingStatsRfdWlClientStatTxBytes OBJECT-TYPE
			SYNTAX Counter64
			MAX-ACCESS read-only
			STATUS current
			DESCRIPTION
				"Number of data bytes transmitted from AP to client
				
				XPath: /extremeWing-stats/rf_domain[name=key1]/wireless/client-stats[mac=key2]/tx_bytes"
			::= { extremeWingStatsRfdWlClientStatEntry 5 }

		
		-- 1.3.6.1.4.1.1916.2.131.50.1.4.3.2.5.1.1.6
		extremeWingStatsRfdWlClientStatRxBytes OBJECT-TYPE
			SYNTAX Counter64
			MAX-ACCESS read-only
			STATUS current
			DESCRIPTION
				"Number of data bytes received from client to AP
				
				XPath: /extremeWing-stats/rf_domain[name=key1]/wireless/client-stats[mac=key2]/rx_bytes"
			::= { extremeWingStatsRfdWlClientStatEntry 6 }

		
		-- 1.3.6.1.4.1.1916.2.131.50.1.4.3.2.5.1.1.7
		extremeWingStatsRfdWlClientStatTxPkts OBJECT-TYPE
			SYNTAX Counter64
			MAX-ACCESS read-only
			STATUS current
			DESCRIPTION
				"Number of packets of data transmitted from AP to client
				
				XPath: /extremeWing-stats/rf_domain[name=key1]/wireless/client-stats[mac=key2]/tx_pkts"
			::= { extremeWingStatsRfdWlClientStatEntry 7 }

		
		-- 1.3.6.1.4.1.1916.2.131.50.1.4.3.2.5.1.1.8
		extremeWingStatsRfdWlClientStatRxPkts OBJECT-TYPE
			SYNTAX Counter64
			MAX-ACCESS read-only
			STATUS current
			DESCRIPTION
				"Number of packets of data received from client to AP
				
				XPath: /extremeWing-stats/rf_domain[name=key1]/wireless/client-stats[mac=key2]/rx_pkts"
			::= { extremeWingStatsRfdWlClientStatEntry 8 }

		
		-- 1.3.6.1.4.1.1916.2.131.50.1.4.3.2.5.1.1.9
		extremeWingStatsRfdWlClientStatTxDropped OBJECT-TYPE
			SYNTAX Counter64
			MAX-ACCESS read-only
			STATUS current
			DESCRIPTION
				"Number of packets of data dropped on transmission
				
				XPath: /extremeWing-stats/rf_domain[name=key1]/wireless/client-stats[mac=key2]/tx_dropped"
			::= { extremeWingStatsRfdWlClientStatEntry 9 }

		
		-- 1.3.6.1.4.1.1916.2.131.50.1.4.3.2.5.1.1.10
		extremeWingStatsRfdWlClientStatRxErrors OBJECT-TYPE
			SYNTAX Counter64
			MAX-ACCESS read-only
			STATUS current
			DESCRIPTION
				"Number of packets of data received with errors
				
				XPath: /extremeWing-stats/rf_domain[name=key1]/wireless/client-stats[mac=key2]/rx_errors"
			::= { extremeWingStatsRfdWlClientStatEntry 10 }

		
		-- 1.3.6.1.4.1.1916.2.131.50.1.4.3.2.5.1.1.11
		extremeWingStatsRfdWlClientStatTIndex OBJECT-TYPE
			SYNTAX Integer32
			MAX-ACCESS read-only
			STATUS current
			DESCRIPTION
				"Traffic Utilization Index
				
				Measures the efficiency the medium under consideration
				is used. It is the percentage of the current data throughput
				over the theoretical data rate limit, which is derived
				the current maximum physical rate configured over the medium
				based on past empirical data. This index could assist end user
				in site planning and expansion. The numerical value might be
				further classified as:
				  -1: no data available ( e.g. radio is not in wlan operation
				                          mode )
				  0-20 : very low utilization
				  20-40: low utilization
				  40-60: moderate utilization
				  60 and above: high utilization
				
				XPath: /extremeWing-stats/rf_domain[name=key1]/wireless/client-stats[mac=key2]/t_index"
			::= { extremeWingStatsRfdWlClientStatEntry 11 }

		
		-- 1.3.6.1.4.1.1916.2.131.50.1.4.3.2.5.1.1.12
		extremeWingStatsRfdWlClientStatTxBps OBJECT-TYPE
			SYNTAX Unsigned32
			UNITS "kbps"
			MAX-ACCESS read-only
			STATUS current
			DESCRIPTION
				"User data transmit rate
				
				XPath: /extremeWing-stats/rf_domain[name=key1]/wireless/client-stats[mac=key2]/tx_bps"
			::= { extremeWingStatsRfdWlClientStatEntry 12 }

		
		-- 1.3.6.1.4.1.1916.2.131.50.1.4.3.2.5.1.1.13
		extremeWingStatsRfdWlClientStatRxBps OBJECT-TYPE
			SYNTAX Unsigned32
			UNITS "kbps"
			MAX-ACCESS read-only
			STATUS current
			DESCRIPTION
				"User data receive rate
				
				XPath: /extremeWing-stats/rf_domain[name=key1]/wireless/client-stats[mac=key2]/rx_bps"
			::= { extremeWingStatsRfdWlClientStatEntry 13 }

		
		-- 1.3.6.1.4.1.1916.2.131.50.1.4.3.2.5.1.1.14
		extremeWingStatsRfdWlClientStatSignal OBJECT-TYPE
			SYNTAX Integer32
			UNITS "dbm"
			MAX-ACCESS read-only
			STATUS current
			DESCRIPTION
				"Signal strength
				
				XPath: /extremeWing-stats/rf_domain[name=key1]/wireless/client-stats[mac=key2]/signal"
			::= { extremeWingStatsRfdWlClientStatEntry 14 }

		
		-- 1.3.6.1.4.1.1916.2.131.50.1.4.3.2.5.1.1.15
		extremeWingStatsRfdWlClientStatNoise OBJECT-TYPE
			SYNTAX Integer32
			UNITS "dbm"
			MAX-ACCESS read-only
			STATUS current
			DESCRIPTION
				"Noise level in units of dbm
				
				XPath: /extremeWing-stats/rf_domain[name=key1]/wireless/client-stats[mac=key2]/noise"
			::= { extremeWingStatsRfdWlClientStatEntry 15 }

		
		-- 1.3.6.1.4.1.1916.2.131.50.1.4.3.2.5.1.1.16
		extremeWingStatsRfdWlClientStatSnr OBJECT-TYPE
			SYNTAX Integer32
			UNITS "db"
			MAX-ACCESS read-only
			STATUS current
			DESCRIPTION
				"Signal to noise ratio in units of db
				
				XPath: /extremeWing-stats/rf_domain[name=key1]/wireless/client-stats[mac=key2]/snr"
			::= { extremeWingStatsRfdWlClientStatEntry 16 }

		
		-- 1.3.6.1.4.1.1916.2.131.50.1.4.3.2.5.1.1.17
		extremeWingStatsRfdWlClientStatTxRate OBJECT-TYPE
			SYNTAX Unsigned32
			UNITS "Mbps"
			MAX-ACCESS read-only
			STATUS current
			DESCRIPTION
				"The effective phy-layer transmit rate
				
				XPath: /extremeWing-stats/rf_domain[name=key1]/wireless/client-stats[mac=key2]/tx_rate"
			::= { extremeWingStatsRfdWlClientStatEntry 17 }

		
		-- 1.3.6.1.4.1.1916.2.131.50.1.4.3.2.5.1.1.18
		extremeWingStatsRfdWlClientStatRxRate OBJECT-TYPE
			SYNTAX Unsigned32
			UNITS "Mbps"
			MAX-ACCESS read-only
			STATUS current
			DESCRIPTION
				"The effective phy-layer receive rate
				
				XPath: /extremeWing-stats/rf_domain[name=key1]/wireless/client-stats[mac=key2]/rx_rate"
			::= { extremeWingStatsRfdWlClientStatEntry 18 }

		
		-- 1.3.6.1.4.1.1916.2.131.50.1.4.3.2.5.1.1.19
		extremeWingStatsRfdWlClientStatErrorRate OBJECT-TYPE
			SYNTAX Unsigned32
			MAX-ACCESS read-only
			STATUS current
			DESCRIPTION
				"Ratio of errors to rx-packets in percentage
				
				XPath: /extremeWing-stats/rf_domain[name=key1]/wireless/client-stats[mac=key2]/error_rate"
			::= { extremeWingStatsRfdWlClientStatEntry 19 }

		
		-- 1.3.6.1.4.1.1916.2.131.50.1.4.3.2.5.1.1.20
		extremeWingStatsRfdWlClientStatQIndex OBJECT-TYPE
			SYNTAX Integer32
			MAX-ACCESS read-only
			STATUS current
			DESCRIPTION
				"RF quality Index
				
				Measure the quality of the medium in percentage. It is a
				function of average retries and error rate. Its range is from
				0-100. Typically:
				  -1: no data available ( e.g. radio is not in wlan operation
				                          mode )
				  0-20: very poor quality
				  20-40: poor quality
				  40-60: average quality
				  60-100: good quality
				
				XPath: /extremeWing-stats/rf_domain[name=key1]/wireless/client-stats[mac=key2]/q_index"
			::= { extremeWingStatsRfdWlClientStatEntry 20 }

		
-- /extremeWing-stats/rf_domain/wireless/client-stats-details
		-- 1.3.6.1.4.1.1916.2.131.50.1.4.3.2.6
		extremeWingStatsRfdWlClientStatDetail OBJECT IDENTIFIER ::= { extremeWingStatsRfdWl 6 }

		
		-- 1.3.6.1.4.1.1916.2.131.50.1.4.3.2.6.1
		extremeWingStatsRfdWlClientStatDetailTable OBJECT-TYPE
			SYNTAX SEQUENCE OF ExtremeWingStatsRfdWlClientStatDetailEntry
			MAX-ACCESS not-accessible
			STATUS current
			DESCRIPTION
				"Detailed statistical information of wireless clients
				associated currently on RF Domain
				
				/extremeWing-stats/rf_domain/wireless/client-stats-details"
			::= { extremeWingStatsRfdWlClientStatDetail 1 }

		
		-- 1.3.6.1.4.1.1916.2.131.50.1.4.3.2.6.1.1
		extremeWingStatsRfdWlClientStatDetailEntry OBJECT-TYPE
			SYNTAX ExtremeWingStatsRfdWlClientStatDetailEntry
			MAX-ACCESS not-accessible
			STATUS current
			DESCRIPTION
				"An entry in the table."
			INDEX { extremeWingStatsRfdName, extremeWingStatsRfdWlClientStatDetailMac }
			::= { extremeWingStatsRfdWlClientStatDetailTable 1 }

		
		ExtremeWingStatsRfdWlClientStatDetailEntry ::=
			SEQUENCE { 
				extremeWingStatsRfdWlClientStatDetailMac
					MacAddress,
				extremeWingStatsRfdWlClientStatDetailMacName
					DisplayString,
				extremeWingStatsRfdWlClientStatDetailVendor
					DisplayString,
				extremeWingStatsRfdWlClientStatDetailTxBytes
					Counter64,
				extremeWingStatsRfdWlClientStatDetailRxBytes
					Counter64,
				extremeWingStatsRfdWlClientStatDetailTxPkts
					Counter64,
				extremeWingStatsRfdWlClientStatDetailRxPkts
					Counter64,
				extremeWingStatsRfdWlClientStatDetailTxDropped
					Counter64,
				extremeWingStatsRfdWlClientStatDetailRxErrors
					Counter64,
				extremeWingStatsRfdWlClientStatDetailTIndex
					Integer32,
				extremeWingStatsRfdWlClientStatDetailTxBps
					Unsigned32,
				extremeWingStatsRfdWlClientStatDetailRxBps
					Unsigned32,
				extremeWingStatsRfdWlClientStatDetailSignal
					Integer32,
				extremeWingStatsRfdWlClientStatDetailNoise
					Integer32,
				extremeWingStatsRfdWlClientStatDetailSnr
					Integer32,
				extremeWingStatsRfdWlClientStatDetailTxRate
					Unsigned32,
				extremeWingStatsRfdWlClientStatDetailRxRate
					Unsigned32,
				extremeWingStatsRfdWlClientStatDetailErrorRate
					Unsigned32,
				extremeWingStatsRfdWlClientStatDetailQIndex
					Integer32,
				extremeWingStatsRfdWlClientStatDetailRawTxBytes
					Counter64,
				extremeWingStatsRfdWlClientStatDetailRawRxBytes
					Counter64,
				extremeWingStatsRfdWlClientStatDetailRawTotalBytes
					Counter64,
				extremeWingStatsRfdWlClientStatDetailRawTxPkts
					Counter64,
				extremeWingStatsRfdWlClientStatDetailRawRxPkts
					Counter64,
				extremeWingStatsRfdWlClientStatDetailRawTotalPkts
					Counter64,
				extremeWingStatsRfdWlClientStatDetailRawTxBps
					Unsigned32,
				extremeWingStatsRfdWlClientStatDetailRawRxBps
					Unsigned32,
				extremeWingStatsRfdWlClientStatDetailRawTotalBps
					Unsigned32,
				extremeWingStatsRfdWlClientStatDetailRawTxPps
					Unsigned32,
				extremeWingStatsRfdWlClientStatDetailRawRxPps
					Unsigned32,
				extremeWingStatsRfdWlClientStatDetailRawTotalPps
					Unsigned32,
				extremeWingStatsRfdWlClientStatDetailRawTxRate
					Unsigned32,
				extremeWingStatsRfdWlClientStatDetailRawRxRate
					Unsigned32,
				extremeWingStatsRfdWlClientStatDetailRawOverallRate
					Unsigned32,
				extremeWingStatsRfdWlClientStatDetailTxBcmcPkts
					Counter64,
				extremeWingStatsRfdWlClientStatDetailRxBcmcPkts
					Counter64,
				extremeWingStatsRfdWlClientStatDetailTotalBcmcPkts
					Counter64,
				extremeWingStatsRfdWlClientStatDetailTxPps
					Unsigned32,
				extremeWingStatsRfdWlClientStatDetailRxPps
					Unsigned32,
				extremeWingStatsRfdWlClientStatDetailTotalPps
					Unsigned32,
				extremeWingStatsRfdWlClientStatDetailTxMgmtPkts
					Counter64,
				extremeWingStatsRfdWlClientStatDetailRxMgmtPkts
					Counter64,
				extremeWingStatsRfdWlClientStatDetailTotalMgmtPkts
					Counter64,
				extremeWingStatsRfdWlClientStatDetailTxRetries
					Counter64,
				extremeWingStatsRfdWlClientStatDetailRxProbes
					Counter64,
				extremeWingStatsRfdWlClientStatDetailRxActions
					Counter64,
				extremeWingStatsRfdWlClientStatDetailRxPsPoll
					Counter64,
				extremeWingStatsRfdWlClientStatDetailLastCallStatus
					DisplayString,
				extremeWingStatsRfdWlClientStatDetailCallTotal
					Unsigned32,
				extremeWingStatsRfdWlClientStatDetailCallStatOk
					Unsigned32,
				extremeWingStatsRfdWlClientStatDetailCallStatBusy
					Unsigned32,
				extremeWingStatsRfdWlClientStatDetailCallStatNoAnswer
					Unsigned32,
				extremeWingStatsRfdWlClientStatDetailCallStatUnknownDest
					Unsigned32,
				extremeWingStatsRfdWlClientStatDetailCallStatAdmDenied
					Unsigned32,
				extremeWingStatsRfdWlClientStatDetailCallStatDeclined
					Unsigned32,
				extremeWingStatsRfdWlClientStatDetailCallStatUnauth
					Unsigned32,
				extremeWingStatsRfdWlClientStatDetailCallStatUnsuppMedia
					Unsigned32,
				extremeWingStatsRfdWlClientStatDetailCallStatTempUnavail
					Unsigned32,
				extremeWingStatsRfdWlClientStatDetailCallStatNoForkAllowed
					Unsigned32,
				extremeWingStatsRfdWlClientStatDetailCallStatSessInactive
					Unsigned32,
				extremeWingStatsRfdWlClientStatDetailCallStatOther
					Unsigned32,
				extremeWingStatsRfdWlClientStatDetailTotalBytes
					Counter64,
				extremeWingStatsRfdWlClientStatDetailTotalPkts
					Counter64,
				extremeWingStatsRfdWlClientStatDetailTxRetriedBytes
					Counter64
			 }

		-- 1.3.6.1.4.1.1916.2.131.50.1.4.3.2.6.1.1.1
		extremeWingStatsRfdWlClientStatDetailMac OBJECT-TYPE
			SYNTAX MacAddress
			MAX-ACCESS read-only
			STATUS current
			DESCRIPTION
				"Client MAC
				
				XPath: /extremeWing-stats/rf_domain[name=key1]/wireless/client-stats-details[mac=key2]/mac"
			::= { extremeWingStatsRfdWlClientStatDetailEntry 1 }

		
		-- 1.3.6.1.4.1.1916.2.131.50.1.4.3.2.6.1.1.2
		extremeWingStatsRfdWlClientStatDetailMacName OBJECT-TYPE
			SYNTAX DisplayString
			MAX-ACCESS read-only
			STATUS current
			DESCRIPTION
				"Hostname of the client which could be obtained from
				packet sniffing or by manually configured via
				mac-name configuration.
				
				XPath: /extremeWing-stats/rf_domain[name=key1]/wireless/client-stats-details[mac=key2]/hostname"
			::= { extremeWingStatsRfdWlClientStatDetailEntry 2 }

		
		-- 1.3.6.1.4.1.1916.2.131.50.1.4.3.2.6.1.1.3
		extremeWingStatsRfdWlClientStatDetailVendor OBJECT-TYPE
			SYNTAX DisplayString
			MAX-ACCESS read-only
			STATUS current
			DESCRIPTION
				"Client vendor name based on the MAC OUI lookup
				
				XPath: /extremeWing-stats/rf_domain[name=key1]/wireless/client-stats-details[mac=key2]/vendor"
			::= { extremeWingStatsRfdWlClientStatDetailEntry 3 }

		
		-- 1.3.6.1.4.1.1916.2.131.50.1.4.3.2.6.1.1.4
		extremeWingStatsRfdWlClientStatDetailTxBytes OBJECT-TYPE
			SYNTAX Counter64
			MAX-ACCESS read-only
			STATUS current
			DESCRIPTION
				"Number of data bytes transmitted from AP to client
				
				XPath: /extremeWing-stats/rf_domain[name=key1]/wireless/client-stats-details[mac=key2]/tx_bytes"
			::= { extremeWingStatsRfdWlClientStatDetailEntry 4 }

		
		-- 1.3.6.1.4.1.1916.2.131.50.1.4.3.2.6.1.1.5
		extremeWingStatsRfdWlClientStatDetailRxBytes OBJECT-TYPE
			SYNTAX Counter64
			MAX-ACCESS read-only
			STATUS current
			DESCRIPTION
				"Number of data bytes received from client to AP
				
				XPath: /extremeWing-stats/rf_domain[name=key1]/wireless/client-stats-details[mac=key2]/rx_bytes"
			::= { extremeWingStatsRfdWlClientStatDetailEntry 5 }

		
		-- 1.3.6.1.4.1.1916.2.131.50.1.4.3.2.6.1.1.6
		extremeWingStatsRfdWlClientStatDetailTxPkts OBJECT-TYPE
			SYNTAX Counter64
			MAX-ACCESS read-only
			STATUS current
			DESCRIPTION
				"Number of packets of data transmitted from AP to client
				
				XPath: /extremeWing-stats/rf_domain[name=key1]/wireless/client-stats-details[mac=key2]/tx_pkts"
			::= { extremeWingStatsRfdWlClientStatDetailEntry 6 }

		
		-- 1.3.6.1.4.1.1916.2.131.50.1.4.3.2.6.1.1.7
		extremeWingStatsRfdWlClientStatDetailRxPkts OBJECT-TYPE
			SYNTAX Counter64
			MAX-ACCESS read-only
			STATUS current
			DESCRIPTION
				"Number of packets of data received from client to AP
				
				XPath: /extremeWing-stats/rf_domain[name=key1]/wireless/client-stats-details[mac=key2]/rx_pkts"
			::= { extremeWingStatsRfdWlClientStatDetailEntry 7 }

		
		-- 1.3.6.1.4.1.1916.2.131.50.1.4.3.2.6.1.1.8
		extremeWingStatsRfdWlClientStatDetailTxDropped OBJECT-TYPE
			SYNTAX Counter64
			MAX-ACCESS read-only
			STATUS current
			DESCRIPTION
				"Number of packets of data dropped on transmission
				
				XPath: /extremeWing-stats/rf_domain[name=key1]/wireless/client-stats-details[mac=key2]/tx_dropped"
			::= { extremeWingStatsRfdWlClientStatDetailEntry 8 }

		
		-- 1.3.6.1.4.1.1916.2.131.50.1.4.3.2.6.1.1.9
		extremeWingStatsRfdWlClientStatDetailRxErrors OBJECT-TYPE
			SYNTAX Counter64
			MAX-ACCESS read-only
			STATUS current
			DESCRIPTION
				"Number of packets of data received with errors
				
				XPath: /extremeWing-stats/rf_domain[name=key1]/wireless/client-stats-details[mac=key2]/rx_errors"
			::= { extremeWingStatsRfdWlClientStatDetailEntry 9 }

		
		-- 1.3.6.1.4.1.1916.2.131.50.1.4.3.2.6.1.1.10
		extremeWingStatsRfdWlClientStatDetailTIndex OBJECT-TYPE
			SYNTAX Integer32
			MAX-ACCESS read-only
			STATUS current
			DESCRIPTION
				"Traffic Utilization Index
				
				Measures the efficiency the medium under consideration
				is used. It is the percentage of the current data throughput
				over the theoretical data rate limit, which is derived
				the current maximum physical rate configured over the medium
				based on past empirical data. This index could assist end user
				in site planning and expansion. The numerical value might be
				further classified as:
				  -1: no data available ( e.g. radio is not in wlan operation
				                          mode )
				  0-20 : very low utilization
				  20-40: low utilization
				  40-60: moderate utilization
				  60 and above: high utilization
				
				XPath: /extremeWing-stats/rf_domain[name=key1]/wireless/client-stats-details[mac=key2]/t_index"
			::= { extremeWingStatsRfdWlClientStatDetailEntry 10 }

		
		-- 1.3.6.1.4.1.1916.2.131.50.1.4.3.2.6.1.1.11
		extremeWingStatsRfdWlClientStatDetailTxBps OBJECT-TYPE
			SYNTAX Unsigned32
			UNITS "kbps"
			MAX-ACCESS read-only
			STATUS current
			DESCRIPTION
				"User data transmit rate
				
				XPath: /extremeWing-stats/rf_domain[name=key1]/wireless/client-stats-details[mac=key2]/tx_bps"
			::= { extremeWingStatsRfdWlClientStatDetailEntry 11 }

		
		-- 1.3.6.1.4.1.1916.2.131.50.1.4.3.2.6.1.1.12
		extremeWingStatsRfdWlClientStatDetailRxBps OBJECT-TYPE
			SYNTAX Unsigned32
			UNITS "kbps"
			MAX-ACCESS read-only
			STATUS current
			DESCRIPTION
				"User data receive rate
				
				XPath: /extremeWing-stats/rf_domain[name=key1]/wireless/client-stats-details[mac=key2]/rx_bps"
			::= { extremeWingStatsRfdWlClientStatDetailEntry 12 }

		
		-- 1.3.6.1.4.1.1916.2.131.50.1.4.3.2.6.1.1.13
		extremeWingStatsRfdWlClientStatDetailSignal OBJECT-TYPE
			SYNTAX Integer32
			UNITS "dbm"
			MAX-ACCESS read-only
			STATUS current
			DESCRIPTION
				"Signal strength in units of dbm
				
				XPath: /extremeWing-stats/rf_domain[name=key1]/wireless/client-stats-details[mac=key2]/signal"
			::= { extremeWingStatsRfdWlClientStatDetailEntry 13 }

		
		-- 1.3.6.1.4.1.1916.2.131.50.1.4.3.2.6.1.1.14
		extremeWingStatsRfdWlClientStatDetailNoise OBJECT-TYPE
			SYNTAX Integer32
			UNITS "dbm"
			MAX-ACCESS read-only
			STATUS current
			DESCRIPTION
				"Noise level in units of dbm
				
				XPath: /extremeWing-stats/rf_domain[name=key1]/wireless/client-stats-details[mac=key2]/noise"
			::= { extremeWingStatsRfdWlClientStatDetailEntry 14 }

		
		-- 1.3.6.1.4.1.1916.2.131.50.1.4.3.2.6.1.1.15
		extremeWingStatsRfdWlClientStatDetailSnr OBJECT-TYPE
			SYNTAX Integer32
			UNITS "db"
			MAX-ACCESS read-only
			STATUS current
			DESCRIPTION
				"Signal to noise ratio in units of db
				
				XPath: /extremeWing-stats/rf_domain[name=key1]/wireless/client-stats-details[mac=key2]/snr"
			::= { extremeWingStatsRfdWlClientStatDetailEntry 15 }

		
		-- 1.3.6.1.4.1.1916.2.131.50.1.4.3.2.6.1.1.16
		extremeWingStatsRfdWlClientStatDetailTxRate OBJECT-TYPE
			SYNTAX Unsigned32
			UNITS "Mbps"
			MAX-ACCESS read-only
			STATUS current
			DESCRIPTION
				"The effective phy-layer transmit rate
				
				XPath: /extremeWing-stats/rf_domain[name=key1]/wireless/client-stats-details[mac=key2]/tx_rate"
			::= { extremeWingStatsRfdWlClientStatDetailEntry 16 }

		
		-- 1.3.6.1.4.1.1916.2.131.50.1.4.3.2.6.1.1.17
		extremeWingStatsRfdWlClientStatDetailRxRate OBJECT-TYPE
			SYNTAX Unsigned32
			UNITS "Mbps"
			MAX-ACCESS read-only
			STATUS current
			DESCRIPTION
				"The effective phy-layer receive rate
				
				XPath: /extremeWing-stats/rf_domain[name=key1]/wireless/client-stats-details[mac=key2]/rx_rate"
			::= { extremeWingStatsRfdWlClientStatDetailEntry 17 }

		
		-- 1.3.6.1.4.1.1916.2.131.50.1.4.3.2.6.1.1.18
		extremeWingStatsRfdWlClientStatDetailErrorRate OBJECT-TYPE
			SYNTAX Unsigned32
			MAX-ACCESS read-only
			STATUS current
			DESCRIPTION
				"Ratio of errors to rx-packets in percentage
				
				XPath: /extremeWing-stats/rf_domain[name=key1]/wireless/client-stats-details[mac=key2]/error_rate"
			::= { extremeWingStatsRfdWlClientStatDetailEntry 18 }

		
		-- 1.3.6.1.4.1.1916.2.131.50.1.4.3.2.6.1.1.19
		extremeWingStatsRfdWlClientStatDetailQIndex OBJECT-TYPE
			SYNTAX Integer32
			MAX-ACCESS read-only
			STATUS current
			DESCRIPTION
				"RF quality Index
				
				Measure the quality of the medium in percentage. It is a
				function of average retries and error rate. Its range is from
				0-100. Typically:
				  -1: no data available ( e.g. radio is not in wlan operation
				                          mode )
				  0-20: very poor quality
				  20-40: poor quality
				  40-60: average quality
				  60-100: good quality
				
				XPath: /extremeWing-stats/rf_domain[name=key1]/wireless/client-stats-details[mac=key2]/q_index"
			::= { extremeWingStatsRfdWlClientStatDetailEntry 19 }

		
		-- 1.3.6.1.4.1.1916.2.131.50.1.4.3.2.6.1.1.20
		extremeWingStatsRfdWlClientStatDetailRawTxBytes OBJECT-TYPE
			SYNTAX Counter64
			MAX-ACCESS read-only
			STATUS current
			DESCRIPTION
				"Number of raw (data + management) bytes transmitted
				from AP to client
				
				XPath: /extremeWing-stats/rf_domain[name=key1]/wireless/client-stats-details[mac=key2]/raw_tx_bytes"
			::= { extremeWingStatsRfdWlClientStatDetailEntry 20 }

		
		-- 1.3.6.1.4.1.1916.2.131.50.1.4.3.2.6.1.1.21
		extremeWingStatsRfdWlClientStatDetailRawRxBytes OBJECT-TYPE
			SYNTAX Counter64
			MAX-ACCESS read-only
			STATUS current
			DESCRIPTION
				"Number of raw (data + management) bytes received
				from client to AP
				
				XPath: /extremeWing-stats/rf_domain[name=key1]/wireless/client-stats-details[mac=key2]/raw_rx_bytes"
			::= { extremeWingStatsRfdWlClientStatDetailEntry 21 }

		
		-- 1.3.6.1.4.1.1916.2.131.50.1.4.3.2.6.1.1.22
		extremeWingStatsRfdWlClientStatDetailRawTotalBytes OBJECT-TYPE
			SYNTAX Counter64
			MAX-ACCESS read-only
			STATUS current
			DESCRIPTION
				"Total mumber of raw (data + management) bytes
				through the AP to/from the client
				
				XPath: /extremeWing-stats/rf_domain[name=key1]/wireless/client-stats-details[mac=key2]/raw_total_bytes"
			::= { extremeWingStatsRfdWlClientStatDetailEntry 22 }

		
		-- 1.3.6.1.4.1.1916.2.131.50.1.4.3.2.6.1.1.23
		extremeWingStatsRfdWlClientStatDetailRawTxPkts OBJECT-TYPE
			SYNTAX Counter64
			MAX-ACCESS read-only
			STATUS current
			DESCRIPTION
				"Number of packets of raw (data + management) transmitted
				from AP to client
				
				XPath: /extremeWing-stats/rf_domain[name=key1]/wireless/client-stats-details[mac=key2]/raw_tx_pkts"
			::= { extremeWingStatsRfdWlClientStatDetailEntry 23 }

		
		-- 1.3.6.1.4.1.1916.2.131.50.1.4.3.2.6.1.1.24
		extremeWingStatsRfdWlClientStatDetailRawRxPkts OBJECT-TYPE
			SYNTAX Counter64
			MAX-ACCESS read-only
			STATUS current
			DESCRIPTION
				"Number of packets of raw (data + management) received
				from client to AP
				
				XPath: /extremeWing-stats/rf_domain[name=key1]/wireless/client-stats-details[mac=key2]/raw_rx_pkts"
			::= { extremeWingStatsRfdWlClientStatDetailEntry 24 }

		
		-- 1.3.6.1.4.1.1916.2.131.50.1.4.3.2.6.1.1.25
		extremeWingStatsRfdWlClientStatDetailRawTotalPkts OBJECT-TYPE
			SYNTAX Counter64
			MAX-ACCESS read-only
			STATUS current
			DESCRIPTION
				"Total number of raw packets through the AP for the client
				
				XPath: /extremeWing-stats/rf_domain[name=key1]/wireless/client-stats-details[mac=key2]/raw_total_pkts"
			::= { extremeWingStatsRfdWlClientStatDetailEntry 25 }

		
		-- 1.3.6.1.4.1.1916.2.131.50.1.4.3.2.6.1.1.26
		extremeWingStatsRfdWlClientStatDetailRawTxBps OBJECT-TYPE
			SYNTAX Unsigned32
			UNITS "kbps"
			MAX-ACCESS read-only
			STATUS current
			DESCRIPTION
				"User raw (data + management) transmit rate
				
				XPath: /extremeWing-stats/rf_domain[name=key1]/wireless/client-stats-details[mac=key2]/raw_tx_bps"
			::= { extremeWingStatsRfdWlClientStatDetailEntry 26 }

		
		-- 1.3.6.1.4.1.1916.2.131.50.1.4.3.2.6.1.1.27
		extremeWingStatsRfdWlClientStatDetailRawRxBps OBJECT-TYPE
			SYNTAX Unsigned32
			UNITS "kbps"
			MAX-ACCESS read-only
			STATUS current
			DESCRIPTION
				"User raw (data + management) receive rate
				
				XPath: /extremeWing-stats/rf_domain[name=key1]/wireless/client-stats-details[mac=key2]/raw_rx_bps"
			::= { extremeWingStatsRfdWlClientStatDetailEntry 27 }

		
		-- 1.3.6.1.4.1.1916.2.131.50.1.4.3.2.6.1.1.28
		extremeWingStatsRfdWlClientStatDetailRawTotalBps OBJECT-TYPE
			SYNTAX Unsigned32
			UNITS "kbps"
			MAX-ACCESS read-only
			STATUS current
			DESCRIPTION
				"Total user raw (data + management) rate
				
				XPath: /extremeWing-stats/rf_domain[name=key1]/wireless/client-stats-details[mac=key2]/raw_total_bps"
			::= { extremeWingStatsRfdWlClientStatDetailEntry 28 }

		
		-- 1.3.6.1.4.1.1916.2.131.50.1.4.3.2.6.1.1.29
		extremeWingStatsRfdWlClientStatDetailRawTxPps OBJECT-TYPE
			SYNTAX Unsigned32
			MAX-ACCESS read-only
			STATUS current
			DESCRIPTION
				"Raw packet rate per second transmitted by AP to client
				
				XPath: /extremeWing-stats/rf_domain[name=key1]/wireless/client-stats-details[mac=key2]/raw_tx_pps"
			::= { extremeWingStatsRfdWlClientStatDetailEntry 29 }

		
		-- 1.3.6.1.4.1.1916.2.131.50.1.4.3.2.6.1.1.30
		extremeWingStatsRfdWlClientStatDetailRawRxPps OBJECT-TYPE
			SYNTAX Unsigned32
			MAX-ACCESS read-only
			STATUS current
			DESCRIPTION
				"Raw packet rate per second received by AP from client
				
				XPath: /extremeWing-stats/rf_domain[name=key1]/wireless/client-stats-details[mac=key2]/raw_rx_pps"
			::= { extremeWingStatsRfdWlClientStatDetailEntry 30 }

		
		-- 1.3.6.1.4.1.1916.2.131.50.1.4.3.2.6.1.1.31
		extremeWingStatsRfdWlClientStatDetailRawTotalPps OBJECT-TYPE
			SYNTAX Unsigned32
			MAX-ACCESS read-only
			STATUS current
			DESCRIPTION
				"Raw packet rate per second through the AP for the client
				
				XPath: /extremeWing-stats/rf_domain[name=key1]/wireless/client-stats-details[mac=key2]/raw_total_pps"
			::= { extremeWingStatsRfdWlClientStatDetailEntry 31 }

		
		-- 1.3.6.1.4.1.1916.2.131.50.1.4.3.2.6.1.1.32
		extremeWingStatsRfdWlClientStatDetailRawTxRate OBJECT-TYPE
			SYNTAX Unsigned32
			UNITS "Mbps"
			MAX-ACCESS read-only
			STATUS current
			DESCRIPTION
				"The effective phy-layer transmit rate for raw data
				
				XPath: /extremeWing-stats/rf_domain[name=key1]/wireless/client-stats-details[mac=key2]/raw_tx_rate"
			::= { extremeWingStatsRfdWlClientStatDetailEntry 32 }

		
		-- 1.3.6.1.4.1.1916.2.131.50.1.4.3.2.6.1.1.33
		extremeWingStatsRfdWlClientStatDetailRawRxRate OBJECT-TYPE
			SYNTAX Unsigned32
			UNITS "Mbps"
			MAX-ACCESS read-only
			STATUS current
			DESCRIPTION
				"The effective phy-layer receive rate for raw data
				
				XPath: /extremeWing-stats/rf_domain[name=key1]/wireless/client-stats-details[mac=key2]/raw_rx_rate"
			::= { extremeWingStatsRfdWlClientStatDetailEntry 33 }

		
		-- 1.3.6.1.4.1.1916.2.131.50.1.4.3.2.6.1.1.34
		extremeWingStatsRfdWlClientStatDetailRawOverallRate OBJECT-TYPE
			SYNTAX Unsigned32
			UNITS "Mbps"
			MAX-ACCESS read-only
			STATUS current
			DESCRIPTION
				"The effective phy-layer overall rate, averaged on transmit and
				receive for raw data
				
				XPath: /extremeWing-stats/rf_domain[name=key1]/wireless/client-stats-details[mac=key2]/raw_overall_rate"
			::= { extremeWingStatsRfdWlClientStatDetailEntry 34 }

		
		-- 1.3.6.1.4.1.1916.2.131.50.1.4.3.2.6.1.1.35
		extremeWingStatsRfdWlClientStatDetailTxBcmcPkts OBJECT-TYPE
			SYNTAX Counter64
			MAX-ACCESS read-only
			STATUS current
			DESCRIPTION
				"Number of broadcast packets transmitted from AP to client
				
				XPath: /extremeWing-stats/rf_domain[name=key1]/wireless/client-stats-details[mac=key2]/tx_bcmc_pkts"
			::= { extremeWingStatsRfdWlClientStatDetailEntry 35 }

		
		-- 1.3.6.1.4.1.1916.2.131.50.1.4.3.2.6.1.1.36
		extremeWingStatsRfdWlClientStatDetailRxBcmcPkts OBJECT-TYPE
			SYNTAX Counter64
			MAX-ACCESS read-only
			STATUS current
			DESCRIPTION
				"Number of broadcast packets received by the AP from client
				
				XPath: /extremeWing-stats/rf_domain[name=key1]/wireless/client-stats-details[mac=key2]/rx_bcmc_pkts"
			::= { extremeWingStatsRfdWlClientStatDetailEntry 36 }

		
		-- 1.3.6.1.4.1.1916.2.131.50.1.4.3.2.6.1.1.37
		extremeWingStatsRfdWlClientStatDetailTotalBcmcPkts OBJECT-TYPE
			SYNTAX Counter64
			MAX-ACCESS read-only
			STATUS current
			DESCRIPTION
				"Total Number of broadcast packets through the AP
				for the client
				
				XPath: /extremeWing-stats/rf_domain[name=key1]/wireless/client-stats-details[mac=key2]/total_bcmc_pkts"
			::= { extremeWingStatsRfdWlClientStatDetailEntry 37 }

		
		-- 1.3.6.1.4.1.1916.2.131.50.1.4.3.2.6.1.1.38
		extremeWingStatsRfdWlClientStatDetailTxPps OBJECT-TYPE
			SYNTAX Unsigned32
			MAX-ACCESS read-only
			STATUS current
			DESCRIPTION
				"Packet rate per second transmitted by the AP to client
				
				XPath: /extremeWing-stats/rf_domain[name=key1]/wireless/client-stats-details[mac=key2]/tx_pps"
			::= { extremeWingStatsRfdWlClientStatDetailEntry 38 }

		
		-- 1.3.6.1.4.1.1916.2.131.50.1.4.3.2.6.1.1.39
		extremeWingStatsRfdWlClientStatDetailRxPps OBJECT-TYPE
			SYNTAX Unsigned32
			MAX-ACCESS read-only
			STATUS current
			DESCRIPTION
				"Packet rate per second received by the AP from client
				
				XPath: /extremeWing-stats/rf_domain[name=key1]/wireless/client-stats-details[mac=key2]/rx_pps"
			::= { extremeWingStatsRfdWlClientStatDetailEntry 39 }

		
		-- 1.3.6.1.4.1.1916.2.131.50.1.4.3.2.6.1.1.40
		extremeWingStatsRfdWlClientStatDetailTotalPps OBJECT-TYPE
			SYNTAX Unsigned32
			MAX-ACCESS read-only
			STATUS current
			DESCRIPTION
				"Packet rate per second through the AP for the client
				
				XPath: /extremeWing-stats/rf_domain[name=key1]/wireless/client-stats-details[mac=key2]/total_pps"
			::= { extremeWingStatsRfdWlClientStatDetailEntry 40 }

		
		-- 1.3.6.1.4.1.1916.2.131.50.1.4.3.2.6.1.1.41
		extremeWingStatsRfdWlClientStatDetailTxMgmtPkts OBJECT-TYPE
			SYNTAX Counter64
			MAX-ACCESS read-only
			STATUS current
			DESCRIPTION
				"Number of management packets of transmitted
				by the AP to client
				
				XPath: /extremeWing-stats/rf_domain[name=key1]/wireless/client-stats-details[mac=key2]/tx_mgmt_pkts"
			::= { extremeWingStatsRfdWlClientStatDetailEntry 41 }

		
		-- 1.3.6.1.4.1.1916.2.131.50.1.4.3.2.6.1.1.42
		extremeWingStatsRfdWlClientStatDetailRxMgmtPkts OBJECT-TYPE
			SYNTAX Counter64
			MAX-ACCESS read-only
			STATUS current
			DESCRIPTION
				"Number of management packets received by the AP from client
				
				XPath: /extremeWing-stats/rf_domain[name=key1]/wireless/client-stats-details[mac=key2]/rx_mgmt_pkts"
			::= { extremeWingStatsRfdWlClientStatDetailEntry 42 }

		
		-- 1.3.6.1.4.1.1916.2.131.50.1.4.3.2.6.1.1.43
		extremeWingStatsRfdWlClientStatDetailTotalMgmtPkts OBJECT-TYPE
			SYNTAX Counter64
			MAX-ACCESS read-only
			STATUS current
			DESCRIPTION
				"Number of management packets through the AP for the client
				
				XPath: /extremeWing-stats/rf_domain[name=key1]/wireless/client-stats-details[mac=key2]/total_mgmt_pkts"
			::= { extremeWingStatsRfdWlClientStatDetailEntry 43 }

		
		-- 1.3.6.1.4.1.1916.2.131.50.1.4.3.2.6.1.1.44
		extremeWingStatsRfdWlClientStatDetailTxRetries OBJECT-TYPE
			SYNTAX Counter64
			MAX-ACCESS read-only
			STATUS current
			DESCRIPTION
				"Total number of retries
				
				XPath: /extremeWing-stats/rf_domain[name=key1]/wireless/client-stats-details[mac=key2]/tx_retries"
			::= { extremeWingStatsRfdWlClientStatDetailEntry 44 }

		
		-- 1.3.6.1.4.1.1916.2.131.50.1.4.3.2.6.1.1.45
		extremeWingStatsRfdWlClientStatDetailRxProbes OBJECT-TYPE
			SYNTAX Counter64
			MAX-ACCESS read-only
			STATUS current
			DESCRIPTION
				"Total number of probe-request packets received
				
				XPath: /extremeWing-stats/rf_domain[name=key1]/wireless/client-stats-details[mac=key2]/rx_probes"
			::= { extremeWingStatsRfdWlClientStatDetailEntry 45 }

		
		-- 1.3.6.1.4.1.1916.2.131.50.1.4.3.2.6.1.1.46
		extremeWingStatsRfdWlClientStatDetailRxActions OBJECT-TYPE
			SYNTAX Counter64
			MAX-ACCESS read-only
			STATUS current
			DESCRIPTION
				"Total number of action packets received
				
				XPath: /extremeWing-stats/rf_domain[name=key1]/wireless/client-stats-details[mac=key2]/rx_actions"
			::= { extremeWingStatsRfdWlClientStatDetailEntry 46 }

		
		-- 1.3.6.1.4.1.1916.2.131.50.1.4.3.2.6.1.1.47
		extremeWingStatsRfdWlClientStatDetailRxPsPoll OBJECT-TYPE
			SYNTAX Counter64
			MAX-ACCESS read-only
			STATUS current
			DESCRIPTION
				"Total number of PS-Poll packets received
				
				XPath: /extremeWing-stats/rf_domain[name=key1]/wireless/client-stats-details[mac=key2]/rx_ps_poll"
			::= { extremeWingStatsRfdWlClientStatDetailEntry 47 }

		
		-- 1.3.6.1.4.1.1916.2.131.50.1.4.3.2.6.1.1.48
		extremeWingStatsRfdWlClientStatDetailLastCallStatus OBJECT-TYPE
			SYNTAX DisplayString
			MAX-ACCESS read-only
			STATUS current
			DESCRIPTION
				"Last voice call status
				
				XPath: /extremeWing-stats/rf_domain[name=key1]/wireless/client-stats-details[mac=key2]/last_call_status"
			::= { extremeWingStatsRfdWlClientStatDetailEntry 48 }

		
		-- 1.3.6.1.4.1.1916.2.131.50.1.4.3.2.6.1.1.49
		extremeWingStatsRfdWlClientStatDetailCallTotal OBJECT-TYPE
			SYNTAX Unsigned32
			MAX-ACCESS read-only
			STATUS current
			DESCRIPTION
				"Total number of voice calls attempted
				
				XPath: /extremeWing-stats/rf_domain[name=key1]/wireless/client-stats-details[mac=key2]/call_total"
			::= { extremeWingStatsRfdWlClientStatDetailEntry 49 }

		
		-- 1.3.6.1.4.1.1916.2.131.50.1.4.3.2.6.1.1.50
		extremeWingStatsRfdWlClientStatDetailCallStatOk OBJECT-TYPE
			SYNTAX Unsigned32
			MAX-ACCESS read-only
			STATUS current
			DESCRIPTION
				"Voice calls successfully made
				
				XPath: /extremeWing-stats/rf_domain[name=key1]/wireless/client-stats-details[mac=key2]/call_status_ok"
			::= { extremeWingStatsRfdWlClientStatDetailEntry 50 }

		
		-- 1.3.6.1.4.1.1916.2.131.50.1.4.3.2.6.1.1.51
		extremeWingStatsRfdWlClientStatDetailCallStatBusy OBJECT-TYPE
			SYNTAX Unsigned32
			MAX-ACCESS read-only
			STATUS current
			DESCRIPTION
				"Voice calls failed because of busy
				
				XPath: /extremeWing-stats/rf_domain[name=key1]/wireless/client-stats-details[mac=key2]/call_status_busy"
			::= { extremeWingStatsRfdWlClientStatDetailEntry 51 }

		
		-- 1.3.6.1.4.1.1916.2.131.50.1.4.3.2.6.1.1.52
		extremeWingStatsRfdWlClientStatDetailCallStatNoAnswer OBJECT-TYPE
			SYNTAX Unsigned32
			MAX-ACCESS read-only
			STATUS current
			DESCRIPTION
				"Voice calls failed because of no-answer
				
				XPath: /extremeWing-stats/rf_domain[name=key1]/wireless/client-stats-details[mac=key2]/call_status_no_answer"
			::= { extremeWingStatsRfdWlClientStatDetailEntry 52 }

		
		-- 1.3.6.1.4.1.1916.2.131.50.1.4.3.2.6.1.1.53
		extremeWingStatsRfdWlClientStatDetailCallStatUnknownDest OBJECT-TYPE
			SYNTAX Unsigned32
			MAX-ACCESS read-only
			STATUS current
			DESCRIPTION
				"Voice calls failed because of unknown destination
				
				XPath: /extremeWing-stats/rf_domain[name=key1]/wireless/client-stats-details[mac=key2]/call_status_unknown_dest"
			::= { extremeWingStatsRfdWlClientStatDetailEntry 53 }

		
		-- 1.3.6.1.4.1.1916.2.131.50.1.4.3.2.6.1.1.54
		extremeWingStatsRfdWlClientStatDetailCallStatAdmDenied OBJECT-TYPE
			SYNTAX Unsigned32
			MAX-ACCESS read-only
			STATUS current
			DESCRIPTION
				"Voice calls failed because of admission denied
				
				XPath: /extremeWing-stats/rf_domain[name=key1]/wireless/client-stats-details[mac=key2]/call_status_admission_denied"
			::= { extremeWingStatsRfdWlClientStatDetailEntry 54 }

		
		-- 1.3.6.1.4.1.1916.2.131.50.1.4.3.2.6.1.1.55
		extremeWingStatsRfdWlClientStatDetailCallStatDeclined OBJECT-TYPE
			SYNTAX Unsigned32
			MAX-ACCESS read-only
			STATUS current
			DESCRIPTION
				"Voice calls failed because of being declined
				
				XPath: /extremeWing-stats/rf_domain[name=key1]/wireless/client-stats-details[mac=key2]/call_status_declined"
			::= { extremeWingStatsRfdWlClientStatDetailEntry 55 }

		
		-- 1.3.6.1.4.1.1916.2.131.50.1.4.3.2.6.1.1.56
		extremeWingStatsRfdWlClientStatDetailCallStatUnauth OBJECT-TYPE
			SYNTAX Unsigned32
			MAX-ACCESS read-only
			STATUS current
			DESCRIPTION
				"Voice calls failed because of being unauthorized
				
				XPath: /extremeWing-stats/rf_domain[name=key1]/wireless/client-stats-details[mac=key2]/call_status_unauthorized"
			::= { extremeWingStatsRfdWlClientStatDetailEntry 56 }

		
		-- 1.3.6.1.4.1.1916.2.131.50.1.4.3.2.6.1.1.57
		extremeWingStatsRfdWlClientStatDetailCallStatUnsuppMedia OBJECT-TYPE
			SYNTAX Unsigned32
			MAX-ACCESS read-only
			STATUS current
			DESCRIPTION
				"Voice calls failed because of unsupported media
				
				XPath: /extremeWing-stats/rf_domain[name=key1]/wireless/client-stats-details[mac=key2]/call_status_unsupported_media"
			::= { extremeWingStatsRfdWlClientStatDetailEntry 57 }

		
		-- 1.3.6.1.4.1.1916.2.131.50.1.4.3.2.6.1.1.58
		extremeWingStatsRfdWlClientStatDetailCallStatTempUnavail OBJECT-TYPE
			SYNTAX Unsigned32
			MAX-ACCESS read-only
			STATUS current
			DESCRIPTION
				"Voice calls failed because of temporarily unavailable
				resources
				
				XPath: /extremeWing-stats/rf_domain[name=key1]/wireless/client-stats-details[mac=key2]/call_status_temporarily_unavailable"
			::= { extremeWingStatsRfdWlClientStatDetailEntry 58 }

		
		-- 1.3.6.1.4.1.1916.2.131.50.1.4.3.2.6.1.1.59
		extremeWingStatsRfdWlClientStatDetailCallStatNoForkAllowed OBJECT-TYPE
			SYNTAX Unsigned32
			MAX-ACCESS read-only
			STATUS current
			DESCRIPTION
				"Voice calls failed because of no-fork-allowed
				
				XPath: /extremeWing-stats/rf_domain[name=key1]/wireless/client-stats-details[mac=key2]/call_status_no_fork_allowed"
			::= { extremeWingStatsRfdWlClientStatDetailEntry 59 }

		
		-- 1.3.6.1.4.1.1916.2.131.50.1.4.3.2.6.1.1.60
		extremeWingStatsRfdWlClientStatDetailCallStatSessInactive OBJECT-TYPE
			SYNTAX Unsigned32
			MAX-ACCESS read-only
			STATUS current
			DESCRIPTION
				"Voice calls ended because of session-inactive
				
				XPath: /extremeWing-stats/rf_domain[name=key1]/wireless/client-stats-details[mac=key2]/call_status_session_inactive"
			::= { extremeWingStatsRfdWlClientStatDetailEntry 60 }

		
		-- 1.3.6.1.4.1.1916.2.131.50.1.4.3.2.6.1.1.61
		extremeWingStatsRfdWlClientStatDetailCallStatOther OBJECT-TYPE
			SYNTAX Unsigned32
			MAX-ACCESS read-only
			STATUS current
			DESCRIPTION
				"Voice calls ended for unknown reason
				
				XPath: /extremeWing-stats/rf_domain[name=key1]/wireless/client-stats-details[mac=key2]/call_status_other"
			::= { extremeWingStatsRfdWlClientStatDetailEntry 61 }

		
		-- 1.3.6.1.4.1.1916.2.131.50.1.4.3.2.6.1.1.62
		extremeWingStatsRfdWlClientStatDetailTotalBytes OBJECT-TYPE
			SYNTAX Counter64
			MAX-ACCESS read-only
			STATUS current
			DESCRIPTION
				"Total mumber of data bytes through the AP for the client
				
				XPath: /extremeWing-stats/rf_domain[name=key1]/wireless/client-stats-details[mac=key2]/total_bytes"
			::= { extremeWingStatsRfdWlClientStatDetailEntry 62 }

		
		-- 1.3.6.1.4.1.1916.2.131.50.1.4.3.2.6.1.1.63
		extremeWingStatsRfdWlClientStatDetailTotalPkts OBJECT-TYPE
			SYNTAX Counter64
			MAX-ACCESS read-only
			STATUS current
			DESCRIPTION
				"Total number of packets through the AP for the client
				
				XPath: /extremeWing-stats/rf_domain[name=key1]/wireless/client-stats-details[mac=key2]/total_pkts"
			::= { extremeWingStatsRfdWlClientStatDetailEntry 63 }

		
		-- 1.3.6.1.4.1.1916.2.131.50.1.4.3.2.6.1.1.64
		extremeWingStatsRfdWlClientStatDetailTxRetriedBytes OBJECT-TYPE
			SYNTAX Counter64
			MAX-ACCESS read-only
			STATUS current
			DESCRIPTION
				"Total retried bytes excluding bytes sent.								 	
				XPath: /extremeWing-stats/rf_domain[name=key1]/wireless/client-stats-details[mac=key2]/tx_retried_bytes."
			::= { extremeWingStatsRfdWlClientStatDetailEntry 64 }

		
-- /extremeWing-stats/rf_domain/wireless/radio
		-- 1.3.6.1.4.1.1916.2.131.50.1.4.3.2.8
		extremeWingStatsRfdWlRadio OBJECT IDENTIFIER ::= { extremeWingStatsRfdWl 8 }

		
		-- 1.3.6.1.4.1.1916.2.131.50.1.4.3.2.8.1
		extremeWingStatsRfdWlRadioTable OBJECT-TYPE
			SYNTAX SEQUENCE OF ExtremeWingStatsRfdWlRadioEntry
			MAX-ACCESS not-accessible
			STATUS current
			DESCRIPTION
				"Status of radios on RF Domain
				
				/extremeWing-stats/rf_domain/wireless/radio"
			::= { extremeWingStatsRfdWlRadio 1 }

		
		-- 1.3.6.1.4.1.1916.2.131.50.1.4.3.2.8.1.1
		extremeWingStatsRfdWlRadioEntry OBJECT-TYPE
			SYNTAX ExtremeWingStatsRfdWlRadioEntry
			MAX-ACCESS not-accessible
			STATUS current
			DESCRIPTION
				"An entry in the table."
			INDEX { extremeWingStatsRfdName, extremeWingStatsRfdWlRadioId }
			::= { extremeWingStatsRfdWlRadioTable 1 }

		
		ExtremeWingStatsRfdWlRadioEntry ::=
			SEQUENCE { 
				extremeWingStatsRfdWlRadioId
					ExtremeWingIdentifier,
				extremeWingStatsRfdWlRadioDeviceMac
					MacAddress,
				extremeWingStatsRfdWlRadioAlias
					DisplayString,
				extremeWingStatsRfdWlRadioMac
					MacAddress,
				extremeWingStatsRfdWlRadioType
					DisplayString,
				extremeWingStatsRfdWlRadioHostname
					DisplayString,
				extremeWingStatsRfdWlRadioRfdName
					DisplayString,
				extremeWingStatsRfdWlRadioLocation
					DisplayString,
				extremeWingStatsRfdWlRadioState
					DisplayString,
				extremeWingStatsRfdWlRadioCurChannel
					DisplayString,
				extremeWingStatsRfdWlRadioConfigChannel
					DisplayString,
				extremeWingStatsRfdWlRadioCurPower
					Unsigned32,
				extremeWingStatsRfdWlRadioConfigPower
					DisplayString,
				extremeWingStatsRfdWlRadioMaxUserRate
					Counter64,
				extremeWingStatsRfdWlRadioNumClient
					Unsigned32,
				extremeWingStatsRfdWlRadioProtocol
					Unsigned32
			 }

		-- 1.3.6.1.4.1.1916.2.131.50.1.4.3.2.8.1.1.1
		extremeWingStatsRfdWlRadioId OBJECT-TYPE
			SYNTAX ExtremeWingIdentifier
			MAX-ACCESS read-only
			STATUS current
			DESCRIPTION
				"Unique ID for each radio interface in the form of
				AP-MAC:R%d. E.g., 00-A0-F8-00-00-00:R1
				
				XPath: /extremeWing-stats/rf_domain[name=key1]/wireless/radio[radio_id=key2]/radio_id"
			::= { extremeWingStatsRfdWlRadioEntry 1 }

		
		-- 1.3.6.1.4.1.1916.2.131.50.1.4.3.2.8.1.1.2
		extremeWingStatsRfdWlRadioDeviceMac OBJECT-TYPE
			SYNTAX MacAddress
			MAX-ACCESS read-only
			STATUS current
			DESCRIPTION
				"MAC address of the AP the radio belongs to.
				
				XPath: /extremeWing-stats/rf_domain[name=key1]/wireless/radio[radio_id=key2]/device_mac"
			::= { extremeWingStatsRfdWlRadioEntry 2 }

		
		-- 1.3.6.1.4.1.1916.2.131.50.1.4.3.2.8.1.1.3
		extremeWingStatsRfdWlRadioAlias OBJECT-TYPE
			SYNTAX DisplayString
			MAX-ACCESS read-only
			STATUS current
			DESCRIPTION
				"An alias to radio id in the form of hostname:R%d.
				E.g., wm3400-22A24E:R1
				
				XPath: /extremeWing-stats/rf_domain[name=key1]/wireless/radio[radio_id=key2]/radio_alias"
			::= { extremeWingStatsRfdWlRadioEntry 3 }

		
		-- 1.3.6.1.4.1.1916.2.131.50.1.4.3.2.8.1.1.4
		extremeWingStatsRfdWlRadioMac OBJECT-TYPE
			SYNTAX MacAddress
			MAX-ACCESS read-only
			STATUS current
			DESCRIPTION
				"MAC address of the radio interface
				
				XPath: /extremeWing-stats/rf_domain[name=key1]/wireless/radio[radio_id=key2]/radio_mac"
			::= { extremeWingStatsRfdWlRadioEntry 4 }

		
		-- 1.3.6.1.4.1.1916.2.131.50.1.4.3.2.8.1.1.5
		extremeWingStatsRfdWlRadioType OBJECT-TYPE
			SYNTAX DisplayString
			MAX-ACCESS read-only
			STATUS current
			DESCRIPTION
				"802.11 radio-type
				
				XPath: /extremeWing-stats/rf_domain[name=key1]/wireless/radio[radio_id=key2]/radio_type"
			::= { extremeWingStatsRfdWlRadioEntry 5 }

		
		-- 1.3.6.1.4.1.1916.2.131.50.1.4.3.2.8.1.1.6
		extremeWingStatsRfdWlRadioHostname OBJECT-TYPE
			SYNTAX DisplayString
			MAX-ACCESS read-only
			STATUS current
			DESCRIPTION
				"Hostname of the AP device
				
				XPath: /extremeWing-stats/rf_domain[name=key1]/wireless/radio[radio_id=key2]/hostname"
			::= { extremeWingStatsRfdWlRadioEntry 6 }

		
		-- 1.3.6.1.4.1.1916.2.131.50.1.4.3.2.8.1.1.7
		extremeWingStatsRfdWlRadioRfdName OBJECT-TYPE
			SYNTAX DisplayString
			MAX-ACCESS read-only
			STATUS current
			DESCRIPTION
				"RF Domain name of the AP device
				
				XPath: /extremeWing-stats/rf_domain[name=key1]/wireless/radio[radio_id=key2]/rf_domain_name"
			::= { extremeWingStatsRfdWlRadioEntry 7 }

		
		-- 1.3.6.1.4.1.1916.2.131.50.1.4.3.2.8.1.1.8
		extremeWingStatsRfdWlRadioLocation OBJECT-TYPE
			SYNTAX DisplayString
			MAX-ACCESS read-only
			STATUS current
			DESCRIPTION
				"Location description of the AP device
				
				XPath: /extremeWing-stats/rf_domain[name=key1]/wireless/radio[radio_id=key2]/location"
			::= { extremeWingStatsRfdWlRadioEntry 8 }

		
		-- 1.3.6.1.4.1.1916.2.131.50.1.4.3.2.8.1.1.9
		extremeWingStatsRfdWlRadioState OBJECT-TYPE
			SYNTAX DisplayString
			MAX-ACCESS read-only
			STATUS current
			DESCRIPTION
				"Radio state
				
				XPath: /extremeWing-stats/rf_domain[name=key1]/wireless/radio[radio_id=key2]/state"
			::= { extremeWingStatsRfdWlRadioEntry 9 }

		
		-- 1.3.6.1.4.1.1916.2.131.50.1.4.3.2.8.1.1.10
		extremeWingStatsRfdWlRadioCurChannel OBJECT-TYPE
			SYNTAX DisplayString
			MAX-ACCESS read-only
			STATUS current
			DESCRIPTION
				"Current channel the radio is operating at
				
				XPath: /extremeWing-stats/rf_domain[name=key1]/wireless/radio[radio_id=key2]/current_channel"
			::= { extremeWingStatsRfdWlRadioEntry 10 }

		
		-- 1.3.6.1.4.1.1916.2.131.50.1.4.3.2.8.1.1.11
		extremeWingStatsRfdWlRadioConfigChannel OBJECT-TYPE
			SYNTAX DisplayString
			MAX-ACCESS read-only
			STATUS current
			DESCRIPTION
				"Configured channel for the radio
				
				XPath: /extremeWing-stats/rf_domain[name=key1]/wireless/radio[radio_id=key2]/config_channel"
			::= { extremeWingStatsRfdWlRadioEntry 11 }

		
		-- 1.3.6.1.4.1.1916.2.131.50.1.4.3.2.8.1.1.12
		extremeWingStatsRfdWlRadioCurPower OBJECT-TYPE
			SYNTAX Unsigned32
			UNITS "dBm"
			MAX-ACCESS read-only
			STATUS current
			DESCRIPTION
				"Current power the radio is operating at
				
				XPath: /extremeWing-stats/rf_domain[name=key1]/wireless/radio[radio_id=key2]/current_power"
			::= { extremeWingStatsRfdWlRadioEntry 12 }

		
		-- 1.3.6.1.4.1.1916.2.131.50.1.4.3.2.8.1.1.13
		extremeWingStatsRfdWlRadioConfigPower OBJECT-TYPE
			SYNTAX DisplayString
			MAX-ACCESS read-only
			STATUS current
			DESCRIPTION
				"Configured power for the radio
				
				XPath: /extremeWing-stats/rf_domain[name=key1]/wireless/radio[radio_id=key2]/config_power"
			::= { extremeWingStatsRfdWlRadioEntry 13 }

		
		-- 1.3.6.1.4.1.1916.2.131.50.1.4.3.2.8.1.1.14
		extremeWingStatsRfdWlRadioMaxUserRate OBJECT-TYPE
			SYNTAX Counter64
			UNITS "kbps"
			MAX-ACCESS read-only
			STATUS current
			DESCRIPTION
				"Theoretic maximum user-level data rate
				
				XPath: /extremeWing-stats/rf_domain[name=key1]/wireless/radio[radio_id=key2]/max_user_rate"
			::= { extremeWingStatsRfdWlRadioEntry 14 }

		
		-- 1.3.6.1.4.1.1916.2.131.50.1.4.3.2.8.1.1.15
		extremeWingStatsRfdWlRadioNumClient OBJECT-TYPE
			SYNTAX Unsigned32
			MAX-ACCESS read-only
			STATUS current
			DESCRIPTION
				"Number of clients associated to the radio
				
				XPath: /extremeWing-stats/rf_domain[name=key1]/wireless/radio[radio_id=key2]/num_clients"
			::= { extremeWingStatsRfdWlRadioEntry 15 }

		
		-- 1.3.6.1.4.1.1916.2.131.50.1.4.3.2.8.1.1.16
		extremeWingStatsRfdWlRadioProtocol OBJECT-TYPE
			SYNTAX Unsigned32
			MAX-ACCESS read-only
			STATUS current
			DESCRIPTION
				"Bit map of protocols currently enabled on the radio.
				
				Bit position:
				The Least Significant Bit corresponds to the first bit
				in the map. The next bit corresponds to the second bit
				and so on. Unused bits are ignored.
				
				bit position  meaning
				============  =======
				0             dot11a
				1             dot11b
				2             dot11g
				3             dot11an
				4             dot11gn
				
				Bit values:
				1 - enabled
				0 - disabled
				
				XPath: /extremeWing-stats/rf_domain[name=key1]/wireless/radio[radio_id=key2]/protocol"
			::= { extremeWingStatsRfdWlRadioEntry 16 }

		
-- /extremeWing-stats/rf_domain/wireless/radio-stats
		-- 1.3.6.1.4.1.1916.2.131.50.1.4.3.2.9
		extremeWingStatsRfdWlRadioStat OBJECT IDENTIFIER ::= { extremeWingStatsRfdWl 9 }

		
		-- 1.3.6.1.4.1.1916.2.131.50.1.4.3.2.9.1
		extremeWingStatsRfdWlRadioStatTable OBJECT-TYPE
			SYNTAX SEQUENCE OF ExtremeWingStatsRfdWlRadioStatEntry
			MAX-ACCESS not-accessible
			STATUS current
			DESCRIPTION
				"Traffic and RF statistics of radios on RF Domain
				
				/extremeWing-stats/rf_domain/wireless/radio-stats"
			::= { extremeWingStatsRfdWlRadioStat 1 }

		
		-- 1.3.6.1.4.1.1916.2.131.50.1.4.3.2.9.1.1
		extremeWingStatsRfdWlRadioStatEntry OBJECT-TYPE
			SYNTAX ExtremeWingStatsRfdWlRadioStatEntry
			MAX-ACCESS not-accessible
			STATUS current
			DESCRIPTION
				"An entry in the table."
			INDEX { extremeWingStatsRfdName, extremeWingStatsRfdWlRadioStatId }
			::= { extremeWingStatsRfdWlRadioStatTable 1 }

		
		ExtremeWingStatsRfdWlRadioStatEntry ::=
			SEQUENCE { 
				extremeWingStatsRfdWlRadioStatId
					ExtremeWingIdentifier,
				extremeWingStatsRfdWlRadioStatDeviceMac
					MacAddress,
				extremeWingStatsRfdWlRadioStatAlias
					DisplayString,
				extremeWingStatsRfdWlRadioStatMac
					MacAddress,
				extremeWingStatsRfdWlRadioStatType
					DisplayString,
				extremeWingStatsRfdWlRadioStatTxBytes
					Counter64,
				extremeWingStatsRfdWlRadioStatRxBytes
					Counter64,
				extremeWingStatsRfdWlRadioStatTxPkts
					Counter64,
				extremeWingStatsRfdWlRadioStatRxPkts
					Counter64,
				extremeWingStatsRfdWlRadioStatTxDropped
					Counter64,
				extremeWingStatsRfdWlRadioStatRxErrors
					Counter64,
				extremeWingStatsRfdWlRadioStatTIndex
					Integer32,
				extremeWingStatsRfdWlRadioStatTxBps
					Unsigned32,
				extremeWingStatsRfdWlRadioStatRxBps
					Unsigned32,
				extremeWingStatsRfdWlRadioStatSignal
					Integer32,
				extremeWingStatsRfdWlRadioStatNoise
					Integer32,
				extremeWingStatsRfdWlRadioStatSnr
					Integer32,
				extremeWingStatsRfdWlRadioStatTxRate
					Unsigned32,
				extremeWingStatsRfdWlRadioStatRxRate
					Unsigned32,
				extremeWingStatsRfdWlRadioStatErrorRate
					Unsigned32,
				extremeWingStatsRfdWlRadioStatQIndex
					Integer32,
				extremeWingStatsRfdWlRadioStatNumClients
					Unsigned32,
				extremeWingStatsRfdWlRadioStatNumBClients
					Unsigned32,
				extremeWingStatsRfdWlRadioStatNumBgClients
					Unsigned32,
				extremeWingStatsRfdWlRadioStatNumBgnClients
					Unsigned32,
				extremeWingStatsRfdWlRadioStatNumAClients
					Unsigned32,
				extremeWingStatsRfdWlRadioStatNumAnClients
					Unsigned32,
				extremeWingStatsRfdWlRadioStatMediumErrorRate
					Unsigned32,
				extremeWingStatsRfdWlRadioStatTxRetries
					Counter64,
				extremeWingStatsRfdWlRadioStatTxRetriedBytes
					Counter64
			 }

		-- 1.3.6.1.4.1.1916.2.131.50.1.4.3.2.9.1.1.1
		extremeWingStatsRfdWlRadioStatId OBJECT-TYPE
			SYNTAX ExtremeWingIdentifier
			MAX-ACCESS read-only
			STATUS current
			DESCRIPTION
				"Unique ID for each radio interface in the form of
				AP-MAC:R%d. E.g., 00-A0-F8-00-00-00:R1
				
				XPath: /extremeWing-stats/rf_domain[name=key1]/wireless/radio-stats[radio_id=key2]/radio_id"
			::= { extremeWingStatsRfdWlRadioStatEntry 1 }

		
		-- 1.3.6.1.4.1.1916.2.131.50.1.4.3.2.9.1.1.2
		extremeWingStatsRfdWlRadioStatDeviceMac OBJECT-TYPE
			SYNTAX MacAddress
			MAX-ACCESS read-only
			STATUS current
			DESCRIPTION
				"MAC address of AP the radio belongs to
				
				XPath: /extremeWing-stats/rf_domain[name=key1]/wireless/radio-stats[radio_id=key2]/device_mac"
			::= { extremeWingStatsRfdWlRadioStatEntry 2 }

		
		-- 1.3.6.1.4.1.1916.2.131.50.1.4.3.2.9.1.1.3
		extremeWingStatsRfdWlRadioStatAlias OBJECT-TYPE
			SYNTAX DisplayString
			MAX-ACCESS read-only
			STATUS current
			DESCRIPTION
				"An alias to radio id in the form of hostname:R%d.
				E.g., wm3400-22A24E:R1
				
				XPath: /extremeWing-stats/rf_domain[name=key1]/wireless/radio-stats[radio_id=key2]/radio_alias"
			::= { extremeWingStatsRfdWlRadioStatEntry 3 }

		
		-- 1.3.6.1.4.1.1916.2.131.50.1.4.3.2.9.1.1.4
		extremeWingStatsRfdWlRadioStatMac OBJECT-TYPE
			SYNTAX MacAddress
			MAX-ACCESS read-only
			STATUS current
			DESCRIPTION
				"MAC address of the radio
				
				XPath: /extremeWing-stats/rf_domain[name=key1]/wireless/radio-stats[radio_id=key2]/radio_mac"
			::= { extremeWingStatsRfdWlRadioStatEntry 4 }

		
		-- 1.3.6.1.4.1.1916.2.131.50.1.4.3.2.9.1.1.5
		extremeWingStatsRfdWlRadioStatType OBJECT-TYPE
			SYNTAX DisplayString
			MAX-ACCESS read-only
			STATUS current
			DESCRIPTION
				"802.11 radio-type
				
				XPath: /extremeWing-stats/rf_domain[name=key1]/wireless/radio-stats[radio_id=key2]/radio_type"
			::= { extremeWingStatsRfdWlRadioStatEntry 5 }

		
		-- 1.3.6.1.4.1.1916.2.131.50.1.4.3.2.9.1.1.6
		extremeWingStatsRfdWlRadioStatTxBytes OBJECT-TYPE
			SYNTAX Counter64
			MAX-ACCESS read-only
			STATUS current
			DESCRIPTION
				"Number of data bytes transmitted from radio to clients
				
				XPath: /extremeWing-stats/rf_domain[name=key1]/wireless/radio-stats[radio_id=key2]/tx_bytes"
			::= { extremeWingStatsRfdWlRadioStatEntry 6 }

		
		-- 1.3.6.1.4.1.1916.2.131.50.1.4.3.2.9.1.1.7
		extremeWingStatsRfdWlRadioStatRxBytes OBJECT-TYPE
			SYNTAX Counter64
			MAX-ACCESS read-only
			STATUS current
			DESCRIPTION
				"Number of data bytes received from clients to radio
				
				XPath: /extremeWing-stats/rf_domain[name=key1]/wireless/radio-stats[radio_id=key2]/rx_bytes"
			::= { extremeWingStatsRfdWlRadioStatEntry 7 }

		
		-- 1.3.6.1.4.1.1916.2.131.50.1.4.3.2.9.1.1.8
		extremeWingStatsRfdWlRadioStatTxPkts OBJECT-TYPE
			SYNTAX Counter64
			MAX-ACCESS read-only
			STATUS current
			DESCRIPTION
				"Number of packets of data transmitted from radio to clients
				
				XPath: /extremeWing-stats/rf_domain[name=key1]/wireless/radio-stats[radio_id=key2]/tx_pkts"
			::= { extremeWingStatsRfdWlRadioStatEntry 8 }

		
		-- 1.3.6.1.4.1.1916.2.131.50.1.4.3.2.9.1.1.9
		extremeWingStatsRfdWlRadioStatRxPkts OBJECT-TYPE
			SYNTAX Counter64
			MAX-ACCESS read-only
			STATUS current
			DESCRIPTION
				"Number of packets of data received from clients to radio
				
				XPath: /extremeWing-stats/rf_domain[name=key1]/wireless/radio-stats[radio_id=key2]/rx_pkts"
			::= { extremeWingStatsRfdWlRadioStatEntry 9 }

		
		-- 1.3.6.1.4.1.1916.2.131.50.1.4.3.2.9.1.1.10
		extremeWingStatsRfdWlRadioStatTxDropped OBJECT-TYPE
			SYNTAX Counter64
			MAX-ACCESS read-only
			STATUS current
			DESCRIPTION
				"Number of packets of data dropped on transmission
				
				XPath: /extremeWing-stats/rf_domain[name=key1]/wireless/radio-stats[radio_id=key2]/tx_dropped"
			::= { extremeWingStatsRfdWlRadioStatEntry 10 }

		
		-- 1.3.6.1.4.1.1916.2.131.50.1.4.3.2.9.1.1.11
		extremeWingStatsRfdWlRadioStatRxErrors OBJECT-TYPE
			SYNTAX Counter64
			MAX-ACCESS read-only
			STATUS current
			DESCRIPTION
				"Number of packets of data received with errors
				
				XPath: /extremeWing-stats/rf_domain[name=key1]/wireless/radio-stats[radio_id=key2]/rx_errors"
			::= { extremeWingStatsRfdWlRadioStatEntry 11 }

		
		-- 1.3.6.1.4.1.1916.2.131.50.1.4.3.2.9.1.1.12
		extremeWingStatsRfdWlRadioStatTIndex OBJECT-TYPE
			SYNTAX Integer32
			MAX-ACCESS read-only
			STATUS current
			DESCRIPTION
				"Traffic Utilization Index
				
				Measures the efficiency the medium under consideration
				is used. It is the percentage of the current data throughput
				over the theoretical data rate limit, which is derived
				the current maximum physical rate configured over the medium
				based on past empirical data. This index could assist end user
				in site planning and expansion. The numerical value might be
				further classified as:
				  -1: no data available ( e.g. radio is not in wlan operation
				                          mode )
				  0-20 : very low utilization
				  20-40: low utilization
				  40-60: moderate utilization
				  60 and above: high utilization
				
				XPath: /extremeWing-stats/rf_domain[name=key1]/wireless/radio-stats[radio_id=key2]/t_index"
			::= { extremeWingStatsRfdWlRadioStatEntry 12 }

		
		-- 1.3.6.1.4.1.1916.2.131.50.1.4.3.2.9.1.1.13
		extremeWingStatsRfdWlRadioStatTxBps OBJECT-TYPE
			SYNTAX Unsigned32
			UNITS "kbps"
			MAX-ACCESS read-only
			STATUS current
			DESCRIPTION
				"User data transmit rate
				
				XPath: /extremeWing-stats/rf_domain[name=key1]/wireless/radio-stats[radio_id=key2]/tx_bps"
			::= { extremeWingStatsRfdWlRadioStatEntry 13 }

		
		-- 1.3.6.1.4.1.1916.2.131.50.1.4.3.2.9.1.1.14
		extremeWingStatsRfdWlRadioStatRxBps OBJECT-TYPE
			SYNTAX Unsigned32
			UNITS "kbps"
			MAX-ACCESS read-only
			STATUS current
			DESCRIPTION
				"User data receive rate
				
				XPath: /extremeWing-stats/rf_domain[name=key1]/wireless/radio-stats[radio_id=key2]/rx_bps"
			::= { extremeWingStatsRfdWlRadioStatEntry 14 }

		
		-- 1.3.6.1.4.1.1916.2.131.50.1.4.3.2.9.1.1.15
		extremeWingStatsRfdWlRadioStatSignal OBJECT-TYPE
			SYNTAX Integer32
			UNITS "dbm"
			MAX-ACCESS read-only
			STATUS current
			DESCRIPTION
				"Signal strength in units of dbm
				
				XPath: /extremeWing-stats/rf_domain[name=key1]/wireless/radio-stats[radio_id=key2]/signal"
			::= { extremeWingStatsRfdWlRadioStatEntry 15 }

		
		-- 1.3.6.1.4.1.1916.2.131.50.1.4.3.2.9.1.1.16
		extremeWingStatsRfdWlRadioStatNoise OBJECT-TYPE
			SYNTAX Integer32
			UNITS "dbm"
			MAX-ACCESS read-only
			STATUS current
			DESCRIPTION
				"Noise level in units of dbm
				
				XPath: /extremeWing-stats/rf_domain[name=key1]/wireless/radio-stats[radio_id=key2]/noise"
			::= { extremeWingStatsRfdWlRadioStatEntry 16 }

		
		-- 1.3.6.1.4.1.1916.2.131.50.1.4.3.2.9.1.1.17
		extremeWingStatsRfdWlRadioStatSnr OBJECT-TYPE
			SYNTAX Integer32
			UNITS "db"
			MAX-ACCESS read-only
			STATUS current
			DESCRIPTION
				"Signal to noise ratio in units of db
				
				XPath: /extremeWing-stats/rf_domain[name=key1]/wireless/radio-stats[radio_id=key2]/snr"
			::= { extremeWingStatsRfdWlRadioStatEntry 17 }

		
		-- 1.3.6.1.4.1.1916.2.131.50.1.4.3.2.9.1.1.18
		extremeWingStatsRfdWlRadioStatTxRate OBJECT-TYPE
			SYNTAX Unsigned32
			UNITS "Mbps"
			MAX-ACCESS read-only
			STATUS current
			DESCRIPTION
				"The effective phy-layer transmit rate
				
				XPath: /extremeWing-stats/rf_domain[name=key1]/wireless/radio-stats[radio_id=key2]/tx_rate"
			::= { extremeWingStatsRfdWlRadioStatEntry 18 }

		
		-- 1.3.6.1.4.1.1916.2.131.50.1.4.3.2.9.1.1.19
		extremeWingStatsRfdWlRadioStatRxRate OBJECT-TYPE
			SYNTAX Unsigned32
			UNITS "Mbps"
			MAX-ACCESS read-only
			STATUS current
			DESCRIPTION
				"The effective phy-layer receive rate
				
				XPath: /extremeWing-stats/rf_domain[name=key1]/wireless/radio-stats[radio_id=key2]/rx_rate"
			::= { extremeWingStatsRfdWlRadioStatEntry 19 }

		
		-- 1.3.6.1.4.1.1916.2.131.50.1.4.3.2.9.1.1.20
		extremeWingStatsRfdWlRadioStatErrorRate OBJECT-TYPE
			SYNTAX Unsigned32
			MAX-ACCESS read-only
			STATUS current
			DESCRIPTION
				"Ratio of errors to rx-packets in percentage
				
				XPath: /extremeWing-stats/rf_domain[name=key1]/wireless/radio-stats[radio_id=key2]/error_rate"
			::= { extremeWingStatsRfdWlRadioStatEntry 20 }

		
		-- 1.3.6.1.4.1.1916.2.131.50.1.4.3.2.9.1.1.21
		extremeWingStatsRfdWlRadioStatQIndex OBJECT-TYPE
			SYNTAX Integer32
			MAX-ACCESS read-only
			STATUS current
			DESCRIPTION
				"RF quality Index
				
				Measure the quality of the medium in percentage. It is a
				function of average retries and error rate. Its range is from
				0-100. Typically:
				  -1: no data available ( e.g. radio is not in wlan operation
				                          mode )
				  0-20: very poor quality
				  20-40: poor quality
				  40-60: average quality
				  60-100: good quality
				
				XPath: /extremeWing-stats/rf_domain[name=key1]/wireless/radio-stats[radio_id=key2]/q_index"
			::= { extremeWingStatsRfdWlRadioStatEntry 21 }

		
		-- 1.3.6.1.4.1.1916.2.131.50.1.4.3.2.9.1.1.22
		extremeWingStatsRfdWlRadioStatNumClients OBJECT-TYPE
			SYNTAX Unsigned32
			MAX-ACCESS read-only
			STATUS current
			DESCRIPTION
				"Total number of clients
				
				XPath: /extremeWing-stats/rf_domain[name=key1]/wireless/radio-stats[radio_id=key2]/num_clients"
			::= { extremeWingStatsRfdWlRadioStatEntry 22 }

		
		-- 1.3.6.1.4.1.1916.2.131.50.1.4.3.2.9.1.1.23
		extremeWingStatsRfdWlRadioStatNumBClients OBJECT-TYPE
			SYNTAX Unsigned32
			MAX-ACCESS read-only
			STATUS current
			DESCRIPTION
				"Number of 11b clients
				
				XPath: /extremeWing-stats/rf_domain[name=key1]/wireless/radio-stats[radio_id=key2]/num_b_clients"
			::= { extremeWingStatsRfdWlRadioStatEntry 23 }

		
		-- 1.3.6.1.4.1.1916.2.131.50.1.4.3.2.9.1.1.24
		extremeWingStatsRfdWlRadioStatNumBgClients OBJECT-TYPE
			SYNTAX Unsigned32
			MAX-ACCESS read-only
			STATUS current
			DESCRIPTION
				"Number of 11bg clients
				
				XPath: /extremeWing-stats/rf_domain[name=key1]/wireless/radio-stats[radio_id=key2]/num_bg_clients"
			::= { extremeWingStatsRfdWlRadioStatEntry 24 }

		
		-- 1.3.6.1.4.1.1916.2.131.50.1.4.3.2.9.1.1.25
		extremeWingStatsRfdWlRadioStatNumBgnClients OBJECT-TYPE
			SYNTAX Unsigned32
			MAX-ACCESS read-only
			STATUS current
			DESCRIPTION
				"Number of 11bgn clients
				
				XPath: /extremeWing-stats/rf_domain[name=key1]/wireless/radio-stats[radio_id=key2]/num_bgn_clients"
			::= { extremeWingStatsRfdWlRadioStatEntry 25 }

		
		-- 1.3.6.1.4.1.1916.2.131.50.1.4.3.2.9.1.1.26
		extremeWingStatsRfdWlRadioStatNumAClients OBJECT-TYPE
			SYNTAX Unsigned32
			MAX-ACCESS read-only
			STATUS current
			DESCRIPTION
				"Number of 11a clients
				
				XPath: /extremeWing-stats/rf_domain[name=key1]/wireless/radio-stats[radio_id=key2]/num_a_clients"
			::= { extremeWingStatsRfdWlRadioStatEntry 26 }

		
		-- 1.3.6.1.4.1.1916.2.131.50.1.4.3.2.9.1.1.27
		extremeWingStatsRfdWlRadioStatNumAnClients OBJECT-TYPE
			SYNTAX Unsigned32
			MAX-ACCESS read-only
			STATUS current
			DESCRIPTION
				"Number of 11an clients
				
				XPath: /extremeWing-stats/rf_domain[name=key1]/wireless/radio-stats[radio_id=key2]/num_an_clients"
			::= { extremeWingStatsRfdWlRadioStatEntry 27 }

		
		-- 1.3.6.1.4.1.1916.2.131.50.1.4.3.2.9.1.1.28
		extremeWingStatsRfdWlRadioStatMediumErrorRate OBJECT-TYPE
			SYNTAX Unsigned32
			MAX-ACCESS read-only
			STATUS current
			DESCRIPTION
				"Ratio of medium errors and rx-retries to rx-packets
				in percentage
				
				XPath: /extremeWing-stats/rf_domain[name=key1]/wireless/radio-stats[radio_id=key2]/medium_error_rate"
			::= { extremeWingStatsRfdWlRadioStatEntry 28 }

		
		-- 1.3.6.1.4.1.1916.2.131.50.1.4.3.2.9.1.1.29
		extremeWingStatsRfdWlRadioStatTxRetries OBJECT-TYPE
			SYNTAX Counter64
			MAX-ACCESS read-only
			STATUS current
			DESCRIPTION
				"Total number of retries
				
				XPath: /extremeWing-stats/rf_domain[name=key1]/wireless/radio-stats[radio_id=key2]/tx_retries"
			::= { extremeWingStatsRfdWlRadioStatEntry 29 }

		
		-- 1.3.6.1.4.1.1916.2.131.50.1.4.3.2.9.1.1.30
		extremeWingStatsRfdWlRadioStatTxRetriedBytes OBJECT-TYPE
			SYNTAX Counter64
			MAX-ACCESS read-only
			STATUS current
			DESCRIPTION
				"Total retried bytes excluding bytes sent.				    
				
				XPath: /extremeWing-stats/rf_domain[name=key1]/wireless/radio-stats[radio_id=key2]/tx_retried_bytes."
			::= { extremeWingStatsRfdWlRadioStatEntry 30 }

		
-- /extremeWing-stats/rf_domain/wireless/radio-details
		-- 1.3.6.1.4.1.1916.2.131.50.1.4.3.2.10
		extremeWingStatsRfdWlRadioDetail OBJECT IDENTIFIER ::= { extremeWingStatsRfdWl 10 }

		
		-- 1.3.6.1.4.1.1916.2.131.50.1.4.3.2.10.1
		extremeWingStatsRfdWlRadioDetailTable OBJECT-TYPE
			SYNTAX SEQUENCE OF ExtremeWingStatsRfdWlRadioDetailEntry
			MAX-ACCESS not-accessible
			STATUS current
			DESCRIPTION
				"Detailed status of radios on RF Domain
				
				/extremeWing-stats/rf_domain/wireless/radio-details"
			::= { extremeWingStatsRfdWlRadioDetail 1 }

		
		-- 1.3.6.1.4.1.1916.2.131.50.1.4.3.2.10.1.1
		extremeWingStatsRfdWlRadioDetailEntry OBJECT-TYPE
			SYNTAX ExtremeWingStatsRfdWlRadioDetailEntry
			MAX-ACCESS not-accessible
			STATUS current
			DESCRIPTION
				"An entry in the table."
			INDEX { extremeWingStatsRfdName, extremeWingStatsRfdWlRadioDetailId }
			::= { extremeWingStatsRfdWlRadioDetailTable 1 }

		
		ExtremeWingStatsRfdWlRadioDetailEntry ::=
			SEQUENCE { 
				extremeWingStatsRfdWlRadioDetailId
					ExtremeWingIdentifier,
				extremeWingStatsRfdWlRadioDetailDeviceMac
					MacAddress,
				extremeWingStatsRfdWlRadioDetailAlias
					DisplayString,
				extremeWingStatsRfdWlRadioDetailMac
					MacAddress,
				extremeWingStatsRfdWlRadioDetailType
					DisplayString,
				extremeWingStatsRfdWlRadioDetailHostname
					DisplayString,
				extremeWingStatsRfdWlRadioDetailRfdName
					DisplayString,
				extremeWingStatsRfdWlRadioDetailLocation
					DisplayString,
				extremeWingStatsRfdWlRadioDetailState
					DisplayString,
				extremeWingStatsRfdWlRadioDetailCurChannel
					DisplayString,
				extremeWingStatsRfdWlRadioDetailConfigChannel
					DisplayString,
				extremeWingStatsRfdWlRadioDetailCurPower
					Unsigned32,
				extremeWingStatsRfdWlRadioDetailConfigPower
					DisplayString,
				extremeWingStatsRfdWlRadioDetailMaxUserRate
					Counter64,
				extremeWingStatsRfdWlRadioDetailNumClient
					Unsigned32,
				extremeWingStatsRfdWlRadioDetailSpectrumMgmt
					TruthValue,
				extremeWingStatsRfdWlRadioDetailShortPreamble
					TruthValue,
				extremeWingStatsRfdWlRadioDetailNonErpPresent
					TruthValue,
				extremeWingStatsRfdWlRadioDetailErpProtectionOn
					TruthValue,
				extremeWingStatsRfdWlRadioDetailNonErpDetected
					TruthValue,
				extremeWingStatsRfdWlRadioDetailHtProtectionOn
					TruthValue,
				extremeWingStatsRfdWlRadioDetailHt20Present
					TruthValue,
				extremeWingStatsRfdWlRadioDetailNonHtDetected
					TruthValue,
				extremeWingStatsRfdWlRadioDetailDualChannelOn
					TruthValue,
				extremeWingStatsRfdWlRadioDetailTxAntennaUsed
					Unsigned32,
				extremeWingStatsRfdWlRadioDetailRxAntennaUsed
					Unsigned32,
				extremeWingStatsRfdWlRadioDetailMaxPhyRate
					Unsigned32,
				extremeWingStatsRfdWlRadioDetailCurMcastStreams
					Unsigned32,
				extremeWingStatsRfdWlRadioDetailMaxMcastStreams
					Unsigned32,
				extremeWingStatsRfdWlRadioDetailMcastStreams
					DisplayString,
				extremeWingStatsRfdWlRadioDetailLastError
					DisplayString
			 }

		-- 1.3.6.1.4.1.1916.2.131.50.1.4.3.2.10.1.1.1
		extremeWingStatsRfdWlRadioDetailId OBJECT-TYPE
			SYNTAX ExtremeWingIdentifier
			MAX-ACCESS read-only
			STATUS current
			DESCRIPTION
				"Unique ID for each radio interface in the form of
				AP-MAC:R%d. E.g., 00-A0-F8-00-00-00:R1
				
				XPath: /extremeWing-stats/rf_domain[name=key1]/wireless/radio-details[radio_id=key2]/radio_id"
			::= { extremeWingStatsRfdWlRadioDetailEntry 1 }

		
		-- 1.3.6.1.4.1.1916.2.131.50.1.4.3.2.10.1.1.2
		extremeWingStatsRfdWlRadioDetailDeviceMac OBJECT-TYPE
			SYNTAX MacAddress
			MAX-ACCESS read-only
			STATUS current
			DESCRIPTION
				"MAC address of AP the radio belongs to
				
				XPath: /extremeWing-stats/rf_domain[name=key1]/wireless/radio-details[radio_id=key2]/device_mac"
			::= { extremeWingStatsRfdWlRadioDetailEntry 2 }

		
		-- 1.3.6.1.4.1.1916.2.131.50.1.4.3.2.10.1.1.3
		extremeWingStatsRfdWlRadioDetailAlias OBJECT-TYPE
			SYNTAX DisplayString
			MAX-ACCESS read-only
			STATUS current
			DESCRIPTION
				"An alias to radio id in the form of hostname:R%d.
				E.g., wm3400-22A24E:R1
				
				XPath: /extremeWing-stats/rf_domain[name=key1]/wireless/radio-details[radio_id=key2]/radio_alias"
			::= { extremeWingStatsRfdWlRadioDetailEntry 3 }

		
		-- 1.3.6.1.4.1.1916.2.131.50.1.4.3.2.10.1.1.4
		extremeWingStatsRfdWlRadioDetailMac OBJECT-TYPE
			SYNTAX MacAddress
			MAX-ACCESS read-only
			STATUS current
			DESCRIPTION
				"MAC address of the radio interface
				
				XPath: /extremeWing-stats/rf_domain[name=key1]/wireless/radio-details[radio_id=key2]/radio_mac"
			::= { extremeWingStatsRfdWlRadioDetailEntry 4 }

		
		-- 1.3.6.1.4.1.1916.2.131.50.1.4.3.2.10.1.1.5
		extremeWingStatsRfdWlRadioDetailType OBJECT-TYPE
			SYNTAX DisplayString
			MAX-ACCESS read-only
			STATUS current
			DESCRIPTION
				"802.11 radio-type
				
				XPath: /extremeWing-stats/rf_domain[name=key1]/wireless/radio-details[radio_id=key2]/radio_type"
			::= { extremeWingStatsRfdWlRadioDetailEntry 5 }

		
		-- 1.3.6.1.4.1.1916.2.131.50.1.4.3.2.10.1.1.6
		extremeWingStatsRfdWlRadioDetailHostname OBJECT-TYPE
			SYNTAX DisplayString
			MAX-ACCESS read-only
			STATUS current
			DESCRIPTION
				"Hostname of the AP device
				
				XPath: /extremeWing-stats/rf_domain[name=key1]/wireless/radio-details[radio_id=key2]/hostname"
			::= { extremeWingStatsRfdWlRadioDetailEntry 6 }

		
		-- 1.3.6.1.4.1.1916.2.131.50.1.4.3.2.10.1.1.7
		extremeWingStatsRfdWlRadioDetailRfdName OBJECT-TYPE
			SYNTAX DisplayString
			MAX-ACCESS read-only
			STATUS current
			DESCRIPTION
				"RF Domain name of the AP device
				
				XPath: /extremeWing-stats/rf_domain[name=key1]/wireless/radio-details[radio_id=key2]/rf_domain_name"
			::= { extremeWingStatsRfdWlRadioDetailEntry 7 }

		
		-- 1.3.6.1.4.1.1916.2.131.50.1.4.3.2.10.1.1.8
		extremeWingStatsRfdWlRadioDetailLocation OBJECT-TYPE
			SYNTAX DisplayString
			MAX-ACCESS read-only
			STATUS current
			DESCRIPTION
				"Location description of the AP device
				
				XPath: /extremeWing-stats/rf_domain[name=key1]/wireless/radio-details[radio_id=key2]/location"
			::= { extremeWingStatsRfdWlRadioDetailEntry 8 }

		
		-- 1.3.6.1.4.1.1916.2.131.50.1.4.3.2.10.1.1.9
		extremeWingStatsRfdWlRadioDetailState OBJECT-TYPE
			SYNTAX DisplayString
			MAX-ACCESS read-only
			STATUS current
			DESCRIPTION
				"Radio state
				
				XPath: /extremeWing-stats/rf_domain[name=key1]/wireless/radio-details[radio_id=key2]/state"
			::= { extremeWingStatsRfdWlRadioDetailEntry 9 }

		
		-- 1.3.6.1.4.1.1916.2.131.50.1.4.3.2.10.1.1.10
		extremeWingStatsRfdWlRadioDetailCurChannel OBJECT-TYPE
			SYNTAX DisplayString
			MAX-ACCESS read-only
			STATUS current
			DESCRIPTION
				"Current channel the radio is operating at
				
				XPath: /extremeWing-stats/rf_domain[name=key1]/wireless/radio-details[radio_id=key2]/current_channel"
			::= { extremeWingStatsRfdWlRadioDetailEntry 10 }

		
		-- 1.3.6.1.4.1.1916.2.131.50.1.4.3.2.10.1.1.11
		extremeWingStatsRfdWlRadioDetailConfigChannel OBJECT-TYPE
			SYNTAX DisplayString
			MAX-ACCESS read-only
			STATUS current
			DESCRIPTION
				"Configured channel for the radio
				
				XPath: /extremeWing-stats/rf_domain[name=key1]/wireless/radio-details[radio_id=key2]/config_channel"
			::= { extremeWingStatsRfdWlRadioDetailEntry 11 }

		
		-- 1.3.6.1.4.1.1916.2.131.50.1.4.3.2.10.1.1.12
		extremeWingStatsRfdWlRadioDetailCurPower OBJECT-TYPE
			SYNTAX Unsigned32
			UNITS "dBm"
			MAX-ACCESS read-only
			STATUS current
			DESCRIPTION
				"Current power the radio is operating at
				
				XPath: /extremeWing-stats/rf_domain[name=key1]/wireless/radio-details[radio_id=key2]/current_power"
			::= { extremeWingStatsRfdWlRadioDetailEntry 12 }

		
		-- 1.3.6.1.4.1.1916.2.131.50.1.4.3.2.10.1.1.13
		extremeWingStatsRfdWlRadioDetailConfigPower OBJECT-TYPE
			SYNTAX DisplayString
			MAX-ACCESS read-only
			STATUS current
			DESCRIPTION
				"Configured power for the radio
				
				XPath: /extremeWing-stats/rf_domain[name=key1]/wireless/radio-details[radio_id=key2]/config_power"
			::= { extremeWingStatsRfdWlRadioDetailEntry 13 }

		
		-- 1.3.6.1.4.1.1916.2.131.50.1.4.3.2.10.1.1.14
		extremeWingStatsRfdWlRadioDetailMaxUserRate OBJECT-TYPE
			SYNTAX Counter64
			UNITS "kbps"
			MAX-ACCESS read-only
			STATUS current
			DESCRIPTION
				"Theoretic maximum user-level data rate
				
				XPath: /extremeWing-stats/rf_domain[name=key1]/wireless/radio-details[radio_id=key2]/max_user_rate"
			::= { extremeWingStatsRfdWlRadioDetailEntry 14 }

		
		-- 1.3.6.1.4.1.1916.2.131.50.1.4.3.2.10.1.1.15
		extremeWingStatsRfdWlRadioDetailNumClient OBJECT-TYPE
			SYNTAX Unsigned32
			MAX-ACCESS read-only
			STATUS current
			DESCRIPTION
				"Number of clients associated to the radio
				
				XPath: /extremeWing-stats/rf_domain[name=key1]/wireless/radio-details[radio_id=key2]/num_clients"
			::= { extremeWingStatsRfdWlRadioDetailEntry 15 }

		
		-- 1.3.6.1.4.1.1916.2.131.50.1.4.3.2.10.1.1.16
		extremeWingStatsRfdWlRadioDetailSpectrumMgmt OBJECT-TYPE
			SYNTAX TruthValue
			MAX-ACCESS read-only
			STATUS current
			DESCRIPTION
				"Whether spectrum management is enabled
				
				XPath: /extremeWing-stats/rf_domain[name=key1]/wireless/radio-details[radio_id=key2]/spectrum_mgmt"
			::= { extremeWingStatsRfdWlRadioDetailEntry 16 }

		
		-- 1.3.6.1.4.1.1916.2.131.50.1.4.3.2.10.1.1.17
		extremeWingStatsRfdWlRadioDetailShortPreamble OBJECT-TYPE
			SYNTAX TruthValue
			MAX-ACCESS read-only
			STATUS current
			DESCRIPTION
				"Whether short preamble mode is enabled
				
				XPath: /extremeWing-stats/rf_domain[name=key1]/wireless/radio-details[radio_id=key2]/short_preamble"
			::= { extremeWingStatsRfdWlRadioDetailEntry 17 }

		
		-- 1.3.6.1.4.1.1916.2.131.50.1.4.3.2.10.1.1.18
		extremeWingStatsRfdWlRadioDetailNonErpPresent OBJECT-TYPE
			SYNTAX TruthValue
			MAX-ACCESS read-only
			STATUS current
			DESCRIPTION
				"Whether non-ERP (Extended Rate PHY) clients are present
				
				XPath: /extremeWing-stats/rf_domain[name=key1]/wireless/radio-details[radio_id=key2]/non_erp_present"
			::= { extremeWingStatsRfdWlRadioDetailEntry 18 }

		
		-- 1.3.6.1.4.1.1916.2.131.50.1.4.3.2.10.1.1.19
		extremeWingStatsRfdWlRadioDetailErpProtectionOn OBJECT-TYPE
			SYNTAX TruthValue
			MAX-ACCESS read-only
			STATUS current
			DESCRIPTION
				"Whether ERP Protection is on
				
				XPath: /extremeWing-stats/rf_domain[name=key1]/wireless/radio-details[radio_id=key2]/erp_protection_on"
			::= { extremeWingStatsRfdWlRadioDetailEntry 19 }

		
		-- 1.3.6.1.4.1.1916.2.131.50.1.4.3.2.10.1.1.20
		extremeWingStatsRfdWlRadioDetailNonErpDetected OBJECT-TYPE
			SYNTAX TruthValue
			MAX-ACCESS read-only
			STATUS current
			DESCRIPTION
				"Whether non-ERP (Extended Rate PHY, 11g) clients
				are detected
				
				XPath: /extremeWing-stats/rf_domain[name=key1]/wireless/radio-details[radio_id=key2]/non_erp_detected"
			::= { extremeWingStatsRfdWlRadioDetailEntry 20 }

		
		-- 1.3.6.1.4.1.1916.2.131.50.1.4.3.2.10.1.1.21
		extremeWingStatsRfdWlRadioDetailHtProtectionOn OBJECT-TYPE
			SYNTAX TruthValue
			MAX-ACCESS read-only
			STATUS current
			DESCRIPTION
				"Whether HT (High Throughput, i.e. 11n) Protection is on
				
				XPath: /extremeWing-stats/rf_domain[name=key1]/wireless/radio-details[radio_id=key2]/ht_protection_on"
			::= { extremeWingStatsRfdWlRadioDetailEntry 21 }

		
		-- 1.3.6.1.4.1.1916.2.131.50.1.4.3.2.10.1.1.22
		extremeWingStatsRfdWlRadioDetailHt20Present OBJECT-TYPE
			SYNTAX TruthValue
			MAX-ACCESS read-only
			STATUS current
			DESCRIPTION
				"Whether HT single channel (20Mhz) clients are present
				
				XPath: /extremeWing-stats/rf_domain[name=key1]/wireless/radio-details[radio_id=key2]/ht_20_present"
			::= { extremeWingStatsRfdWlRadioDetailEntry 22 }

		
		-- 1.3.6.1.4.1.1916.2.131.50.1.4.3.2.10.1.1.23
		extremeWingStatsRfdWlRadioDetailNonHtDetected OBJECT-TYPE
			SYNTAX TruthValue
			MAX-ACCESS read-only
			STATUS current
			DESCRIPTION
				"Whether non-HT devices are present
				
				XPath: /extremeWing-stats/rf_domain[name=key1]/wireless/radio-details[radio_id=key2]/non_ht_detected"
			::= { extremeWingStatsRfdWlRadioDetailEntry 23 }

		
		-- 1.3.6.1.4.1.1916.2.131.50.1.4.3.2.10.1.1.24
		extremeWingStatsRfdWlRadioDetailDualChannelOn OBJECT-TYPE
			SYNTAX TruthValue
			MAX-ACCESS read-only
			STATUS current
			DESCRIPTION
				"Whether dual channel mode is on
				
				XPath: /extremeWing-stats/rf_domain[name=key1]/wireless/radio-details[radio_id=key2]/dual_channel_on"
			::= { extremeWingStatsRfdWlRadioDetailEntry 24 }

		
		-- 1.3.6.1.4.1.1916.2.131.50.1.4.3.2.10.1.1.25
		extremeWingStatsRfdWlRadioDetailTxAntennaUsed OBJECT-TYPE
			SYNTAX Unsigned32
			MAX-ACCESS read-only
			STATUS current
			DESCRIPTION
				"Number of antennas used in transmit chain
				
				XPath: /extremeWing-stats/rf_domain[name=key1]/wireless/radio-details[radio_id=key2]/tx_antenna_used"
			::= { extremeWingStatsRfdWlRadioDetailEntry 25 }

		
		-- 1.3.6.1.4.1.1916.2.131.50.1.4.3.2.10.1.1.26
		extremeWingStatsRfdWlRadioDetailRxAntennaUsed OBJECT-TYPE
			SYNTAX Unsigned32
			MAX-ACCESS read-only
			STATUS current
			DESCRIPTION
				"Number of antennas used in receive chain
				
				XPath: /extremeWing-stats/rf_domain[name=key1]/wireless/radio-details[radio_id=key2]/rx_antenna_used"
			::= { extremeWingStatsRfdWlRadioDetailEntry 26 }

		
		-- 1.3.6.1.4.1.1916.2.131.50.1.4.3.2.10.1.1.27
		extremeWingStatsRfdWlRadioDetailMaxPhyRate OBJECT-TYPE
			SYNTAX Unsigned32
			UNITS "kbps"
			MAX-ACCESS read-only
			STATUS current
			DESCRIPTION
				"Maximum physical data rate
				
				XPath: /extremeWing-stats/rf_domain[name=key1]/wireless/radio-details[radio_id=key2]/max_phy_rate"
			::= { extremeWingStatsRfdWlRadioDetailEntry 27 }

		
		-- 1.3.6.1.4.1.1916.2.131.50.1.4.3.2.10.1.1.28
		extremeWingStatsRfdWlRadioDetailCurMcastStreams OBJECT-TYPE
			SYNTAX Unsigned32
			MAX-ACCESS read-only
			STATUS current
			DESCRIPTION
				"Number of active accelerated multicast streams
				
				XPath: /extremeWing-stats/rf_domain[name=key1]/wireless/radio-details[radio_id=key2]/cur_mcast_streams"
			::= { extremeWingStatsRfdWlRadioDetailEntry 28 }

		
		-- 1.3.6.1.4.1.1916.2.131.50.1.4.3.2.10.1.1.29
		extremeWingStatsRfdWlRadioDetailMaxMcastStreams OBJECT-TYPE
			SYNTAX Unsigned32
			MAX-ACCESS read-only
			STATUS current
			DESCRIPTION
				"Maximum number of accelerated multicast streams
				
				XPath: /extremeWing-stats/rf_domain[name=key1]/wireless/radio-details[radio_id=key2]/max_mcast_streams"
			::= { extremeWingStatsRfdWlRadioDetailEntry 29 }

		
		-- 1.3.6.1.4.1.1916.2.131.50.1.4.3.2.10.1.1.30
		extremeWingStatsRfdWlRadioDetailMcastStreams OBJECT-TYPE
			SYNTAX DisplayString
			MAX-ACCESS read-only
			STATUS current
			DESCRIPTION
				"IP addresses and number of registered clients for
				accelerated multicast streams
				
				XPath: /extremeWing-stats/rf_domain[name=key1]/wireless/radio-details[radio_id=key2]/mcast_streams"
			::= { extremeWingStatsRfdWlRadioDetailEntry 30 }

		
		-- 1.3.6.1.4.1.1916.2.131.50.1.4.3.2.10.1.1.31
		extremeWingStatsRfdWlRadioDetailLastError OBJECT-TYPE
			SYNTAX DisplayString
			MAX-ACCESS read-only
			STATUS current
			DESCRIPTION
				"The last run-time error encountered when applying a
				configuration to this radio or its AP
				
				XPath: /extremeWing-stats/rf_domain[name=key1]/wireless/radio-details[radio_id=key2]/last_error"
			::= { extremeWingStatsRfdWlRadioDetailEntry 31 }

		
		-- 1.3.6.1.4.1.1916.2.131.50.1.4.3.2.10.2
		extremeWingStatsRfdWlRadioDetailWlanMapTable OBJECT-TYPE
			SYNTAX SEQUENCE OF ExtremeWingStatsRfdWlRadioDetailWlanMapEntry
			MAX-ACCESS not-accessible
			STATUS current
			DESCRIPTION
				"Wireless LANs mapped on this radio interface.
				
				/extremeWing-stats/rf_domain/wireless/radio-details/wlan_map"
			::= { extremeWingStatsRfdWlRadioDetail 2 }

		
		-- 1.3.6.1.4.1.1916.2.131.50.1.4.3.2.10.2.1
		extremeWingStatsRfdWlRadioDetailWlanMapEntry OBJECT-TYPE
			SYNTAX ExtremeWingStatsRfdWlRadioDetailWlanMapEntry
			MAX-ACCESS not-accessible
			STATUS current
			DESCRIPTION
				"An entry in the table."
			INDEX { extremeWingStatsRfdName, extremeWingStatsRfdWlRadioDetailId, extremeWingStatsRfdWlRadioDetailWlanMapWlanName }
			::= { extremeWingStatsRfdWlRadioDetailWlanMapTable 1 }

		
		ExtremeWingStatsRfdWlRadioDetailWlanMapEntry ::=
			SEQUENCE { 
				extremeWingStatsRfdWlRadioDetailWlanMapWlanName
					ExtremeWingIdentifier,
				extremeWingStatsRfdWlRadioDetailWlanMapBssIndex
					Unsigned32,
				extremeWingStatsRfdWlRadioDetailWlanMapIsPrimary
					TruthValue
			 }

		-- 1.3.6.1.4.1.1916.2.131.50.1.4.3.2.10.2.1.1
		extremeWingStatsRfdWlRadioDetailWlanMapWlanName OBJECT-TYPE
			SYNTAX ExtremeWingIdentifier
			MAX-ACCESS read-only
			STATUS current
			DESCRIPTION
				"The name of the WLAN.
				
				XPath: /extremeWing-stats/rf_domain[name=key1]/wireless/radio-details[radio_id=key2]/wlan_map[wlan_name=key3]/wlan_name"
			::= { extremeWingStatsRfdWlRadioDetailWlanMapEntry 1 }

		
		-- 1.3.6.1.4.1.1916.2.131.50.1.4.3.2.10.2.1.2
		extremeWingStatsRfdWlRadioDetailWlanMapBssIndex OBJECT-TYPE
			SYNTAX Unsigned32
			MAX-ACCESS read-only
			STATUS current
			DESCRIPTION
				"The BSS Index on the radio that this WLAN is mapped upon.
				
				XPath: /extremeWing-stats/rf_domain[name=key1]/wireless/radio-details[radio_id=key2]/wlan_map[wlan_name=key3]/bss_index"
			::= { extremeWingStatsRfdWlRadioDetailWlanMapEntry 2 }

		
		-- 1.3.6.1.4.1.1916.2.131.50.1.4.3.2.10.2.1.3
		extremeWingStatsRfdWlRadioDetailWlanMapIsPrimary OBJECT-TYPE
			SYNTAX TruthValue
			MAX-ACCESS read-only
			STATUS current
			DESCRIPTION
				"Whether this WLAN is the primary WLAN on the bss_index.
				Only the primary WLAN on a bss_index would have
				beacons advertised.
				
				XPath: /extremeWing-stats/rf_domain[name=key1]/wireless/radio-details[radio_id=key2]/wlan_map[wlan_name=key3]/is_primary"
			::= { extremeWingStatsRfdWlRadioDetailWlanMapEntry 3 }

		
		-- 1.3.6.1.4.1.1916.2.131.50.1.4.3.2.10.3
		extremeWingStatsRfdWlRadioDetailBssMapTable OBJECT-TYPE
			SYNTAX SEQUENCE OF ExtremeWingStatsRfdWlRadioDetailBssMapEntry
			MAX-ACCESS not-accessible
			STATUS current
			DESCRIPTION
				"BSS radio details.
				
				/extremeWing-stats/rf_domain/wireless/radio-details/bss_map"
			::= { extremeWingStatsRfdWlRadioDetail 3 }

		
		-- 1.3.6.1.4.1.1916.2.131.50.1.4.3.2.10.3.1
		extremeWingStatsRfdWlRadioDetailBssMapEntry OBJECT-TYPE
			SYNTAX ExtremeWingStatsRfdWlRadioDetailBssMapEntry
			MAX-ACCESS not-accessible
			STATUS current
			DESCRIPTION
				"An entry in the table."
			INDEX { extremeWingStatsRfdName, extremeWingStatsRfdWlRadioDetailId, extremeWingStatsRfdWlRadioDetailBssMapBssIndex }
			::= { extremeWingStatsRfdWlRadioDetailBssMapTable 1 }

		
		ExtremeWingStatsRfdWlRadioDetailBssMapEntry ::=
			SEQUENCE { 
				extremeWingStatsRfdWlRadioDetailBssMapBssIndex
					ExtremeWingIdentifier,
				extremeWingStatsRfdWlRadioDetailBssMapBasicRates
					DisplayString,
				extremeWingStatsRfdWlRadioDetailBssMapSupportedRates
					DisplayString
			 }

		-- 1.3.6.1.4.1.1916.2.131.50.1.4.3.2.10.3.1.1
		extremeWingStatsRfdWlRadioDetailBssMapBssIndex OBJECT-TYPE
			SYNTAX ExtremeWingIdentifier
			MAX-ACCESS read-only
			STATUS current
			DESCRIPTION
				"The BSS index
				
				Values:
				1
				2
				3
				4
				5
				6
				7
				8
				
				XPath: /extremeWing-stats/rf_domain[name=key1]/wireless/radio-details[radio_id=key2]/bss_map[bss_index=key3]/bss_index"
			::= { extremeWingStatsRfdWlRadioDetailBssMapEntry 1 }

		
		-- 1.3.6.1.4.1.1916.2.131.50.1.4.3.2.10.3.1.2
		extremeWingStatsRfdWlRadioDetailBssMapBasicRates OBJECT-TYPE
			SYNTAX DisplayString
			MAX-ACCESS read-only
			STATUS current
			DESCRIPTION
				"Basic rate set on this BSS.
				
				XPath: /extremeWing-stats/rf_domain[name=key1]/wireless/radio-details[radio_id=key2]/bss_map[bss_index=key3]/basic_rates"
			::= { extremeWingStatsRfdWlRadioDetailBssMapEntry 2 }

		
		-- 1.3.6.1.4.1.1916.2.131.50.1.4.3.2.10.3.1.3
		extremeWingStatsRfdWlRadioDetailBssMapSupportedRates OBJECT-TYPE
			SYNTAX DisplayString
			MAX-ACCESS read-only
			STATUS current
			DESCRIPTION
				"Supported rate set on this BSS.
				
				XPath: /extremeWing-stats/rf_domain[name=key1]/wireless/radio-details[radio_id=key2]/bss_map[bss_index=key3]/supported_rates"
			::= { extremeWingStatsRfdWlRadioDetailBssMapEntry 3 }

		
-- /extremeWing-stats/rf_domain/wireless/radio-stats-details
		-- 1.3.6.1.4.1.1916.2.131.50.1.4.3.2.11
		extremeWingStatsRfdWlRadioStatDetail OBJECT IDENTIFIER ::= { extremeWingStatsRfdWl 11 }

		
		-- 1.3.6.1.4.1.1916.2.131.50.1.4.3.2.11.1
		extremeWingStatsRfdWlRadioStatDetailTable OBJECT-TYPE
			SYNTAX SEQUENCE OF ExtremeWingStatsRfdWlRadioStatDetailEntry
			MAX-ACCESS not-accessible
			STATUS current
			DESCRIPTION
				"Detailed Traffic and RF statistics of radios on RF Domain
				
				/extremeWing-stats/rf_domain/wireless/radio-stats-details"
			::= { extremeWingStatsRfdWlRadioStatDetail 1 }

		
		-- 1.3.6.1.4.1.1916.2.131.50.1.4.3.2.11.1.1
		extremeWingStatsRfdWlRadioStatDetailEntry OBJECT-TYPE
			SYNTAX ExtremeWingStatsRfdWlRadioStatDetailEntry
			MAX-ACCESS not-accessible
			STATUS current
			DESCRIPTION
				"An entry in the table."
			INDEX { extremeWingStatsRfdName, extremeWingStatsRfdWlRadioStatDetailId }
			::= { extremeWingStatsRfdWlRadioStatDetailTable 1 }

		
		ExtremeWingStatsRfdWlRadioStatDetailEntry ::=
			SEQUENCE { 
				extremeWingStatsRfdWlRadioStatDetailId
					ExtremeWingIdentifier,
				extremeWingStatsRfdWlRadioStatDetailDeviceMac
					MacAddress,
				extremeWingStatsRfdWlRadioStatDetailAlias
					DisplayString,
				extremeWingStatsRfdWlRadioStatDetailMac
					MacAddress,
				extremeWingStatsRfdWlRadioStatDetailType
					DisplayString,
				extremeWingStatsRfdWlRadioStatDetailTxBytes
					Counter64,
				extremeWingStatsRfdWlRadioStatDetailRxBytes
					Counter64,
				extremeWingStatsRfdWlRadioStatDetailTxPkts
					Counter64,
				extremeWingStatsRfdWlRadioStatDetailRxPkts
					Counter64,
				extremeWingStatsRfdWlRadioStatDetailTxDropped
					Counter64,
				extremeWingStatsRfdWlRadioStatDetailRxErrors
					Counter64,
				extremeWingStatsRfdWlRadioStatDetailTIndex
					Integer32,
				extremeWingStatsRfdWlRadioStatDetailTxBps
					Unsigned32,
				extremeWingStatsRfdWlRadioStatDetailRxBps
					Unsigned32,
				extremeWingStatsRfdWlRadioStatDetailSignal
					Integer32,
				extremeWingStatsRfdWlRadioStatDetailNoise
					Integer32,
				extremeWingStatsRfdWlRadioStatDetailSnr
					Integer32,
				extremeWingStatsRfdWlRadioStatDetailTxRate
					Unsigned32,
				extremeWingStatsRfdWlRadioStatDetailRxRate
					Unsigned32,
				extremeWingStatsRfdWlRadioStatDetailErrorRate
					Unsigned32,
				extremeWingStatsRfdWlRadioStatDetailQIndex
					Integer32,
				extremeWingStatsRfdWlRadioStatDetailNumClients
					Unsigned32,
				extremeWingStatsRfdWlRadioStatDetailNumBClients
					Unsigned32,
				extremeWingStatsRfdWlRadioStatDetailNumBgClients
					Unsigned32,
				extremeWingStatsRfdWlRadioStatDetailNumBgnClients
					Unsigned32,
				extremeWingStatsRfdWlRadioStatDetailNumAClients
					Unsigned32,
				extremeWingStatsRfdWlRadioStatDetailNumAnClients
					Unsigned32,
				extremeWingStatsRfdWlRadioStatDetailMediumErrorRate
					Unsigned32,
				extremeWingStatsRfdWlRadioStatDetailRawTxBytes
					Counter64,
				extremeWingStatsRfdWlRadioStatDetailRawRxBytes
					Counter64,
				extremeWingStatsRfdWlRadioStatDetailRawTotalBytes
					Counter64,
				extremeWingStatsRfdWlRadioStatDetailRawTxPkts
					Counter64,
				extremeWingStatsRfdWlRadioStatDetailRawRxPkts
					Counter64,
				extremeWingStatsRfdWlRadioStatDetailRawTotalPkts
					Counter64,
				extremeWingStatsRfdWlRadioStatDetailRawTxBps
					Unsigned32,
				extremeWingStatsRfdWlRadioStatDetailRawRxBps
					Unsigned32,
				extremeWingStatsRfdWlRadioStatDetailRawTotalBps
					Unsigned32,
				extremeWingStatsRfdWlRadioStatDetailRawTxPps
					Unsigned32,
				extremeWingStatsRfdWlRadioStatDetailRawRxPps
					Unsigned32,
				extremeWingStatsRfdWlRadioStatDetailRawTotalPps
					Unsigned32,
				extremeWingStatsRfdWlRadioStatDetailRawTxRate
					Unsigned32,
				extremeWingStatsRfdWlRadioStatDetailRawRxRate
					Unsigned32,
				extremeWingStatsRfdWlRadioStatDetailRawOverallRate
					Unsigned32,
				extremeWingStatsRfdWlRadioStatDetailTxBcmcPkts
					Counter64,
				extremeWingStatsRfdWlRadioStatDetailRxBcmcPkts
					Counter64,
				extremeWingStatsRfdWlRadioStatDetailTotalBcmcPkts
					Counter64,
				extremeWingStatsRfdWlRadioStatDetailTxPps
					Unsigned32,
				extremeWingStatsRfdWlRadioStatDetailRxPps
					Unsigned32,
				extremeWingStatsRfdWlRadioStatDetailTotalPps
					Unsigned32,
				extremeWingStatsRfdWlRadioStatDetailTxMgmtPkts
					Counter64,
				extremeWingStatsRfdWlRadioStatDetailRxMgmtPkts
					Counter64,
				extremeWingStatsRfdWlRadioStatDetailTotalMgmtPkts
					Counter64,
				extremeWingStatsRfdWlRadioStatDetailTxRetries
					Counter64,
				extremeWingStatsRfdWlRadioStatDetailRxProbes
					Counter64,
				extremeWingStatsRfdWlRadioStatDetailRxActions
					Counter64,
				extremeWingStatsRfdWlRadioStatDetailRxPsPoll
					Counter64,
				extremeWingStatsRfdWlRadioStatDetailLastCallStatus
					DisplayString,
				extremeWingStatsRfdWlRadioStatDetailCallTotal
					Counter32,
				extremeWingStatsRfdWlRadioStatDetailCallStatOk
					Counter32,
				extremeWingStatsRfdWlRadioStatDetailCallStatBusy
					Counter32,
				extremeWingStatsRfdWlRadioStatDetailCallStatNoAnswer
					Counter32,
				extremeWingStatsRfdWlRadioStatDetailCallStatUnknownDest
					Counter32,
				extremeWingStatsRfdWlRadioStatDetailCallStatAdmDenied
					Counter32,
				extremeWingStatsRfdWlRadioStatDetailCallStatDeclined
					Counter32,
				extremeWingStatsRfdWlRadioStatDetailCallStatUnauth
					Counter32,
				extremeWingStatsRfdWlRadioStatDetailCallStatUnsuppMedia
					Counter32,
				extremeWingStatsRfdWlRadioStatDetailCallStatTempUnavail
					Counter32,
				extremeWingStatsRfdWlRadioStatDetailCallStatNoForkAllowed
					Counter32,
				extremeWingStatsRfdWlRadioStatDetailCallStatSessInactive
					Counter32,
				extremeWingStatsRfdWlRadioStatDetailCallStatOther
					Counter32,
				extremeWingStatsRfdWlRadioStatDetailTotalBytes
					Counter64,
				extremeWingStatsRfdWlRadioStatDetailTotalPkts
					Counter64,
				extremeWingStatsRfdWlRadioStatDetailRxRetries
					Counter64,
				extremeWingStatsRfdWlRadioStatDetailRxCrcErrors
					Counter64,
				extremeWingStatsRfdWlRadioStatDetailRxUndecryptable
					Counter64,
				extremeWingStatsRfdWlRadioStatDetailRxIncomplete
					Counter64,
				extremeWingStatsRfdWlRadioStatDetailRxLengthErrors
					Counter64,
				extremeWingStatsRfdWlRadioStatDetailRxOtherErrors
					Counter64,
				extremeWingStatsRfdWlRadioStatDetailLongPreambleClients
					Unsigned32,
				extremeWingStatsRfdWlRadioStatDetailLtClients
					Unsigned32,
				extremeWingStatsRfdWlRadioStatDetailHt20Clients
					Unsigned32,
				extremeWingStatsRfdWlRadioStatDetailLongSlotClients
					Unsigned32,
				extremeWingStatsRfdWlRadioStatDetailTxRetriedBytes
					Counter64
			 }

		-- 1.3.6.1.4.1.1916.2.131.50.1.4.3.2.11.1.1.1
		extremeWingStatsRfdWlRadioStatDetailId OBJECT-TYPE
			SYNTAX ExtremeWingIdentifier
			MAX-ACCESS read-only
			STATUS current
			DESCRIPTION
				"Unique ID for each radio interface in the form of
				AP-MAC:R%d. E.g., 00-A0-F8-00-00-00:R1
				
				XPath: /extremeWing-stats/rf_domain[name=key1]/wireless/radio-stats-details[radio_id=key2]/radio_id"
			::= { extremeWingStatsRfdWlRadioStatDetailEntry 1 }

		
		-- 1.3.6.1.4.1.1916.2.131.50.1.4.3.2.11.1.1.2
		extremeWingStatsRfdWlRadioStatDetailDeviceMac OBJECT-TYPE
			SYNTAX MacAddress
			MAX-ACCESS read-only
			STATUS current
			DESCRIPTION
				"MAC address of AP the radio belongs to
				
				XPath: /extremeWing-stats/rf_domain[name=key1]/wireless/radio-stats-details[radio_id=key2]/device_mac"
			::= { extremeWingStatsRfdWlRadioStatDetailEntry 2 }

		
		-- 1.3.6.1.4.1.1916.2.131.50.1.4.3.2.11.1.1.3
		extremeWingStatsRfdWlRadioStatDetailAlias OBJECT-TYPE
			SYNTAX DisplayString
			MAX-ACCESS read-only
			STATUS current
			DESCRIPTION
				"An alias to radio id in the form of hostname:R%d.
				E.g., wm3400-22A24E:R1
				
				XPath: /extremeWing-stats/rf_domain[name=key1]/wireless/radio-stats-details[radio_id=key2]/radio_alias"
			::= { extremeWingStatsRfdWlRadioStatDetailEntry 3 }

		
		-- 1.3.6.1.4.1.1916.2.131.50.1.4.3.2.11.1.1.4
		extremeWingStatsRfdWlRadioStatDetailMac OBJECT-TYPE
			SYNTAX MacAddress
			MAX-ACCESS read-only
			STATUS current
			DESCRIPTION
				"MAC address of the radio
				
				XPath: /extremeWing-stats/rf_domain[name=key1]/wireless/radio-stats-details[radio_id=key2]/radio_mac"
			::= { extremeWingStatsRfdWlRadioStatDetailEntry 4 }

		
		-- 1.3.6.1.4.1.1916.2.131.50.1.4.3.2.11.1.1.5
		extremeWingStatsRfdWlRadioStatDetailType OBJECT-TYPE
			SYNTAX DisplayString
			MAX-ACCESS read-only
			STATUS current
			DESCRIPTION
				"802.11 radio-type
				
				XPath: /extremeWing-stats/rf_domain[name=key1]/wireless/radio-stats-details[radio_id=key2]/radio_type"
			::= { extremeWingStatsRfdWlRadioStatDetailEntry 5 }

		
		-- 1.3.6.1.4.1.1916.2.131.50.1.4.3.2.11.1.1.6
		extremeWingStatsRfdWlRadioStatDetailTxBytes OBJECT-TYPE
			SYNTAX Counter64
			MAX-ACCESS read-only
			STATUS current
			DESCRIPTION
				"Number of data bytes transmitted from radio to clients
				
				XPath: /extremeWing-stats/rf_domain[name=key1]/wireless/radio-stats-details[radio_id=key2]/tx_bytes"
			::= { extremeWingStatsRfdWlRadioStatDetailEntry 6 }

		
		-- 1.3.6.1.4.1.1916.2.131.50.1.4.3.2.11.1.1.7
		extremeWingStatsRfdWlRadioStatDetailRxBytes OBJECT-TYPE
			SYNTAX Counter64
			MAX-ACCESS read-only
			STATUS current
			DESCRIPTION
				"Number of data bytes received from clients to radio
				
				XPath: /extremeWing-stats/rf_domain[name=key1]/wireless/radio-stats-details[radio_id=key2]/rx_bytes"
			::= { extremeWingStatsRfdWlRadioStatDetailEntry 7 }

		
		-- 1.3.6.1.4.1.1916.2.131.50.1.4.3.2.11.1.1.8
		extremeWingStatsRfdWlRadioStatDetailTxPkts OBJECT-TYPE
			SYNTAX Counter64
			MAX-ACCESS read-only
			STATUS current
			DESCRIPTION
				"Number of packets of data transmitted from radio to clients
				
				XPath: /extremeWing-stats/rf_domain[name=key1]/wireless/radio-stats-details[radio_id=key2]/tx_pkts"
			::= { extremeWingStatsRfdWlRadioStatDetailEntry 8 }

		
		-- 1.3.6.1.4.1.1916.2.131.50.1.4.3.2.11.1.1.9
		extremeWingStatsRfdWlRadioStatDetailRxPkts OBJECT-TYPE
			SYNTAX Counter64
			MAX-ACCESS read-only
			STATUS current
			DESCRIPTION
				"Number of packets of data received from clients to radio
				
				XPath: /extremeWing-stats/rf_domain[name=key1]/wireless/radio-stats-details[radio_id=key2]/rx_pkts"
			::= { extremeWingStatsRfdWlRadioStatDetailEntry 9 }

		
		-- 1.3.6.1.4.1.1916.2.131.50.1.4.3.2.11.1.1.10
		extremeWingStatsRfdWlRadioStatDetailTxDropped OBJECT-TYPE
			SYNTAX Counter64
			MAX-ACCESS read-only
			STATUS current
			DESCRIPTION
				"Number of packets of data dropped on transmission
				
				XPath: /extremeWing-stats/rf_domain[name=key1]/wireless/radio-stats-details[radio_id=key2]/tx_dropped"
			::= { extremeWingStatsRfdWlRadioStatDetailEntry 10 }

		
		-- 1.3.6.1.4.1.1916.2.131.50.1.4.3.2.11.1.1.11
		extremeWingStatsRfdWlRadioStatDetailRxErrors OBJECT-TYPE
			SYNTAX Counter64
			MAX-ACCESS read-only
			STATUS current
			DESCRIPTION
				"Number of packets of data received with errors
				
				XPath: /extremeWing-stats/rf_domain[name=key1]/wireless/radio-stats-details[radio_id=key2]/rx_errors"
			::= { extremeWingStatsRfdWlRadioStatDetailEntry 11 }

		
		-- 1.3.6.1.4.1.1916.2.131.50.1.4.3.2.11.1.1.12
		extremeWingStatsRfdWlRadioStatDetailTIndex OBJECT-TYPE
			SYNTAX Integer32
			MAX-ACCESS read-only
			STATUS current
			DESCRIPTION
				"Traffic Utilization Index
				
				Measures the efficiency the medium under consideration
				is used. It is the percentage of the current data throughput
				over the theoretical data rate limit, which is derived
				the current maximum physical rate configured over the medium
				based on past empirical data. This index could assist end user
				in site planning and expansion. The numerical value might be
				further classified as:
				  -1: no data available ( e.g. radio is not in wlan operation
				                          mode )
				  0-20 : very low utilization
				  20-40: low utilization
				  40-60: moderate utilization
				  60 and above: high utilization
				
				XPath: /extremeWing-stats/rf_domain[name=key1]/wireless/radio-stats-details[radio_id=key2]/t_index"
			::= { extremeWingStatsRfdWlRadioStatDetailEntry 12 }

		
		-- 1.3.6.1.4.1.1916.2.131.50.1.4.3.2.11.1.1.13
		extremeWingStatsRfdWlRadioStatDetailTxBps OBJECT-TYPE
			SYNTAX Unsigned32
			UNITS "kbps"
			MAX-ACCESS read-only
			STATUS current
			DESCRIPTION
				"User data transmit rate
				
				XPath: /extremeWing-stats/rf_domain[name=key1]/wireless/radio-stats-details[radio_id=key2]/tx_bps"
			::= { extremeWingStatsRfdWlRadioStatDetailEntry 13 }

		
		-- 1.3.6.1.4.1.1916.2.131.50.1.4.3.2.11.1.1.14
		extremeWingStatsRfdWlRadioStatDetailRxBps OBJECT-TYPE
			SYNTAX Unsigned32
			UNITS "kbps"
			MAX-ACCESS read-only
			STATUS current
			DESCRIPTION
				"User data receive rate
				
				XPath: /extremeWing-stats/rf_domain[name=key1]/wireless/radio-stats-details[radio_id=key2]/rx_bps"
			::= { extremeWingStatsRfdWlRadioStatDetailEntry 14 }

		
		-- 1.3.6.1.4.1.1916.2.131.50.1.4.3.2.11.1.1.15
		extremeWingStatsRfdWlRadioStatDetailSignal OBJECT-TYPE
			SYNTAX Integer32
			UNITS "dbm"
			MAX-ACCESS read-only
			STATUS current
			DESCRIPTION
				"Signal strength in units of dbm
				
				XPath: /extremeWing-stats/rf_domain[name=key1]/wireless/radio-stats-details[radio_id=key2]/signal"
			::= { extremeWingStatsRfdWlRadioStatDetailEntry 15 }

		
		-- 1.3.6.1.4.1.1916.2.131.50.1.4.3.2.11.1.1.16
		extremeWingStatsRfdWlRadioStatDetailNoise OBJECT-TYPE
			SYNTAX Integer32
			UNITS "dbm"
			MAX-ACCESS read-only
			STATUS current
			DESCRIPTION
				"Noise level in units of dbm
				
				XPath: /extremeWing-stats/rf_domain[name=key1]/wireless/radio-stats-details[radio_id=key2]/noise"
			::= { extremeWingStatsRfdWlRadioStatDetailEntry 16 }

		
		-- 1.3.6.1.4.1.1916.2.131.50.1.4.3.2.11.1.1.17
		extremeWingStatsRfdWlRadioStatDetailSnr OBJECT-TYPE
			SYNTAX Integer32
			UNITS "db"
			MAX-ACCESS read-only
			STATUS current
			DESCRIPTION
				"Signal to noise ratio in units of db
				
				XPath: /extremeWing-stats/rf_domain[name=key1]/wireless/radio-stats-details[radio_id=key2]/snr"
			::= { extremeWingStatsRfdWlRadioStatDetailEntry 17 }

		
		-- 1.3.6.1.4.1.1916.2.131.50.1.4.3.2.11.1.1.18
		extremeWingStatsRfdWlRadioStatDetailTxRate OBJECT-TYPE
			SYNTAX Unsigned32
			UNITS "Mbps"
			MAX-ACCESS read-only
			STATUS current
			DESCRIPTION
				"The effective phy-layer transmit rate
				
				XPath: /extremeWing-stats/rf_domain[name=key1]/wireless/radio-stats-details[radio_id=key2]/tx_rate"
			::= { extremeWingStatsRfdWlRadioStatDetailEntry 18 }

		
		-- 1.3.6.1.4.1.1916.2.131.50.1.4.3.2.11.1.1.19
		extremeWingStatsRfdWlRadioStatDetailRxRate OBJECT-TYPE
			SYNTAX Unsigned32
			UNITS "Mbps"
			MAX-ACCESS read-only
			STATUS current
			DESCRIPTION
				"The effective phy-layer receive rate
				
				XPath: /extremeWing-stats/rf_domain[name=key1]/wireless/radio-stats-details[radio_id=key2]/rx_rate"
			::= { extremeWingStatsRfdWlRadioStatDetailEntry 19 }

		
		-- 1.3.6.1.4.1.1916.2.131.50.1.4.3.2.11.1.1.20
		extremeWingStatsRfdWlRadioStatDetailErrorRate OBJECT-TYPE
			SYNTAX Unsigned32
			MAX-ACCESS read-only
			STATUS current
			DESCRIPTION
				"Ratio of errors to rx-packets in percentage
				
				XPath: /extremeWing-stats/rf_domain[name=key1]/wireless/radio-stats-details[radio_id=key2]/error_rate"
			::= { extremeWingStatsRfdWlRadioStatDetailEntry 20 }

		
		-- 1.3.6.1.4.1.1916.2.131.50.1.4.3.2.11.1.1.21
		extremeWingStatsRfdWlRadioStatDetailQIndex OBJECT-TYPE
			SYNTAX Integer32
			MAX-ACCESS read-only
			STATUS current
			DESCRIPTION
				"RF quality Index
				
				Measure the quality of the medium in percentage. It is a
				function of average retries and error rate. Its range is from
				0-100. Typically:
				  -1: no data available ( e.g. radio is not in wlan operation
				                          mode )
				  0-20: very poor quality
				  20-40: poor quality
				  40-60: average quality
				  60-100: good quality
				
				XPath: /extremeWing-stats/rf_domain[name=key1]/wireless/radio-stats-details[radio_id=key2]/q_index"
			::= { extremeWingStatsRfdWlRadioStatDetailEntry 21 }

		
		-- 1.3.6.1.4.1.1916.2.131.50.1.4.3.2.11.1.1.22
		extremeWingStatsRfdWlRadioStatDetailNumClients OBJECT-TYPE
			SYNTAX Unsigned32
			MAX-ACCESS read-only
			STATUS current
			DESCRIPTION
				"Total number of clients
				
				XPath: /extremeWing-stats/rf_domain[name=key1]/wireless/radio-stats-details[radio_id=key2]/num_clients"
			::= { extremeWingStatsRfdWlRadioStatDetailEntry 22 }

		
		-- 1.3.6.1.4.1.1916.2.131.50.1.4.3.2.11.1.1.23
		extremeWingStatsRfdWlRadioStatDetailNumBClients OBJECT-TYPE
			SYNTAX Unsigned32
			MAX-ACCESS read-only
			STATUS current
			DESCRIPTION
				"Number of 11b clients
				
				XPath: /extremeWing-stats/rf_domain[name=key1]/wireless/radio-stats-details[radio_id=key2]/num_b_clients"
			::= { extremeWingStatsRfdWlRadioStatDetailEntry 23 }

		
		-- 1.3.6.1.4.1.1916.2.131.50.1.4.3.2.11.1.1.24
		extremeWingStatsRfdWlRadioStatDetailNumBgClients OBJECT-TYPE
			SYNTAX Unsigned32
			MAX-ACCESS read-only
			STATUS current
			DESCRIPTION
				"Number of 11bg clients
				
				XPath: /extremeWing-stats/rf_domain[name=key1]/wireless/radio-stats-details[radio_id=key2]/num_bg_clients"
			::= { extremeWingStatsRfdWlRadioStatDetailEntry 24 }

		
		-- 1.3.6.1.4.1.1916.2.131.50.1.4.3.2.11.1.1.25
		extremeWingStatsRfdWlRadioStatDetailNumBgnClients OBJECT-TYPE
			SYNTAX Unsigned32
			MAX-ACCESS read-only
			STATUS current
			DESCRIPTION
				"Number of 11bgn clients
				
				XPath: /extremeWing-stats/rf_domain[name=key1]/wireless/radio-stats-details[radio_id=key2]/num_bgn_clients"
			::= { extremeWingStatsRfdWlRadioStatDetailEntry 25 }

		
		-- 1.3.6.1.4.1.1916.2.131.50.1.4.3.2.11.1.1.26
		extremeWingStatsRfdWlRadioStatDetailNumAClients OBJECT-TYPE
			SYNTAX Unsigned32
			MAX-ACCESS read-only
			STATUS current
			DESCRIPTION
				"Number of 11a clients
				
				XPath: /extremeWing-stats/rf_domain[name=key1]/wireless/radio-stats-details[radio_id=key2]/num_a_clients"
			::= { extremeWingStatsRfdWlRadioStatDetailEntry 26 }

		
		-- 1.3.6.1.4.1.1916.2.131.50.1.4.3.2.11.1.1.27
		extremeWingStatsRfdWlRadioStatDetailNumAnClients OBJECT-TYPE
			SYNTAX Unsigned32
			MAX-ACCESS read-only
			STATUS current
			DESCRIPTION
				"Number of 11an clients
				
				XPath: /extremeWing-stats/rf_domain[name=key1]/wireless/radio-stats-details[radio_id=key2]/num_an_clients"
			::= { extremeWingStatsRfdWlRadioStatDetailEntry 27 }

		
		-- 1.3.6.1.4.1.1916.2.131.50.1.4.3.2.11.1.1.28
		extremeWingStatsRfdWlRadioStatDetailMediumErrorRate OBJECT-TYPE
			SYNTAX Unsigned32
			MAX-ACCESS read-only
			STATUS current
			DESCRIPTION
				"Ratio of medium errors and rx-retries to rx-packets
				in percentage
				
				XPath: /extremeWing-stats/rf_domain[name=key1]/wireless/radio-stats-details[radio_id=key2]/medium_error_rate"
			::= { extremeWingStatsRfdWlRadioStatDetailEntry 28 }

		
		-- 1.3.6.1.4.1.1916.2.131.50.1.4.3.2.11.1.1.29
		extremeWingStatsRfdWlRadioStatDetailRawTxBytes OBJECT-TYPE
			SYNTAX Counter64
			MAX-ACCESS read-only
			STATUS current
			DESCRIPTION
				"Number of raw (data + management) bytes transmitted
				from radio to clients
				
				XPath: /extremeWing-stats/rf_domain[name=key1]/wireless/radio-stats-details[radio_id=key2]/raw_tx_bytes"
			::= { extremeWingStatsRfdWlRadioStatDetailEntry 29 }

		
		-- 1.3.6.1.4.1.1916.2.131.50.1.4.3.2.11.1.1.30
		extremeWingStatsRfdWlRadioStatDetailRawRxBytes OBJECT-TYPE
			SYNTAX Counter64
			MAX-ACCESS read-only
			STATUS current
			DESCRIPTION
				"Number of raw (data + management) bytes received
				from clients to radio
				
				XPath: /extremeWing-stats/rf_domain[name=key1]/wireless/radio-stats-details[radio_id=key2]/raw_rx_bytes"
			::= { extremeWingStatsRfdWlRadioStatDetailEntry 30 }

		
		-- 1.3.6.1.4.1.1916.2.131.50.1.4.3.2.11.1.1.31
		extremeWingStatsRfdWlRadioStatDetailRawTotalBytes OBJECT-TYPE
			SYNTAX Counter64
			MAX-ACCESS read-only
			STATUS current
			DESCRIPTION
				"Total mumber of raw (data + management) bytes through
				the radio for clients
				
				XPath: /extremeWing-stats/rf_domain[name=key1]/wireless/radio-stats-details[radio_id=key2]/raw_total_bytes"
			::= { extremeWingStatsRfdWlRadioStatDetailEntry 31 }

		
		-- 1.3.6.1.4.1.1916.2.131.50.1.4.3.2.11.1.1.32
		extremeWingStatsRfdWlRadioStatDetailRawTxPkts OBJECT-TYPE
			SYNTAX Counter64
			MAX-ACCESS read-only
			STATUS current
			DESCRIPTION
				"Number of packets of raw (data + management) transmitted
				from radio to clients
				
				XPath: /extremeWing-stats/rf_domain[name=key1]/wireless/radio-stats-details[radio_id=key2]/raw_tx_pkts"
			::= { extremeWingStatsRfdWlRadioStatDetailEntry 32 }

		
		-- 1.3.6.1.4.1.1916.2.131.50.1.4.3.2.11.1.1.33
		extremeWingStatsRfdWlRadioStatDetailRawRxPkts OBJECT-TYPE
			SYNTAX Counter64
			MAX-ACCESS read-only
			STATUS current
			DESCRIPTION
				"Number of packets of raw (data + management) received
				from clients to radio
				
				XPath: /extremeWing-stats/rf_domain[name=key1]/wireless/radio-stats-details[radio_id=key2]/raw_rx_pkts"
			::= { extremeWingStatsRfdWlRadioStatDetailEntry 33 }

		
		-- 1.3.6.1.4.1.1916.2.131.50.1.4.3.2.11.1.1.34
		extremeWingStatsRfdWlRadioStatDetailRawTotalPkts OBJECT-TYPE
			SYNTAX Counter64
			MAX-ACCESS read-only
			STATUS current
			DESCRIPTION
				"Total number of raw packets through the radio
				
				XPath: /extremeWing-stats/rf_domain[name=key1]/wireless/radio-stats-details[radio_id=key2]/raw_total_pkts"
			::= { extremeWingStatsRfdWlRadioStatDetailEntry 34 }

		
		-- 1.3.6.1.4.1.1916.2.131.50.1.4.3.2.11.1.1.35
		extremeWingStatsRfdWlRadioStatDetailRawTxBps OBJECT-TYPE
			SYNTAX Unsigned32
			UNITS "kbps"
			MAX-ACCESS read-only
			STATUS current
			DESCRIPTION
				"User raw (data + management) transmit rate
				
				XPath: /extremeWing-stats/rf_domain[name=key1]/wireless/radio-stats-details[radio_id=key2]/raw_tx_bps"
			::= { extremeWingStatsRfdWlRadioStatDetailEntry 35 }

		
		-- 1.3.6.1.4.1.1916.2.131.50.1.4.3.2.11.1.1.36
		extremeWingStatsRfdWlRadioStatDetailRawRxBps OBJECT-TYPE
			SYNTAX Unsigned32
			UNITS "kbps"
			MAX-ACCESS read-only
			STATUS current
			DESCRIPTION
				"User raw (data + management) receive rate
				
				XPath: /extremeWing-stats/rf_domain[name=key1]/wireless/radio-stats-details[radio_id=key2]/raw_rx_bps"
			::= { extremeWingStatsRfdWlRadioStatDetailEntry 36 }

		
		-- 1.3.6.1.4.1.1916.2.131.50.1.4.3.2.11.1.1.37
		extremeWingStatsRfdWlRadioStatDetailRawTotalBps OBJECT-TYPE
			SYNTAX Unsigned32
			UNITS "kbps"
			MAX-ACCESS read-only
			STATUS current
			DESCRIPTION
				"Total user raw (data + management) rate
				
				XPath: /extremeWing-stats/rf_domain[name=key1]/wireless/radio-stats-details[radio_id=key2]/raw_total_bps"
			::= { extremeWingStatsRfdWlRadioStatDetailEntry 37 }

		
		-- 1.3.6.1.4.1.1916.2.131.50.1.4.3.2.11.1.1.38
		extremeWingStatsRfdWlRadioStatDetailRawTxPps OBJECT-TYPE
			SYNTAX Unsigned32
			MAX-ACCESS read-only
			STATUS current
			DESCRIPTION
				"Raw packet rate per second transmitted by the radio
				
				XPath: /extremeWing-stats/rf_domain[name=key1]/wireless/radio-stats-details[radio_id=key2]/raw_tx_pps"
			::= { extremeWingStatsRfdWlRadioStatDetailEntry 38 }

		
		-- 1.3.6.1.4.1.1916.2.131.50.1.4.3.2.11.1.1.39
		extremeWingStatsRfdWlRadioStatDetailRawRxPps OBJECT-TYPE
			SYNTAX Unsigned32
			MAX-ACCESS read-only
			STATUS current
			DESCRIPTION
				"Raw packet rate per second received by the radio
				
				XPath: /extremeWing-stats/rf_domain[name=key1]/wireless/radio-stats-details[radio_id=key2]/raw_rx_pps"
			::= { extremeWingStatsRfdWlRadioStatDetailEntry 39 }

		
		-- 1.3.6.1.4.1.1916.2.131.50.1.4.3.2.11.1.1.40
		extremeWingStatsRfdWlRadioStatDetailRawTotalPps OBJECT-TYPE
			SYNTAX Unsigned32
			MAX-ACCESS read-only
			STATUS current
			DESCRIPTION
				"Raw packet rate per second through the radio
				
				XPath: /extremeWing-stats/rf_domain[name=key1]/wireless/radio-stats-details[radio_id=key2]/raw_total_pps"
			::= { extremeWingStatsRfdWlRadioStatDetailEntry 40 }

		
		-- 1.3.6.1.4.1.1916.2.131.50.1.4.3.2.11.1.1.41
		extremeWingStatsRfdWlRadioStatDetailRawTxRate OBJECT-TYPE
			SYNTAX Unsigned32
			UNITS "Mbps"
			MAX-ACCESS read-only
			STATUS current
			DESCRIPTION
				"The effective phy-layer transmit rate for raw data
				
				XPath: /extremeWing-stats/rf_domain[name=key1]/wireless/radio-stats-details[radio_id=key2]/raw_tx_rate"
			::= { extremeWingStatsRfdWlRadioStatDetailEntry 41 }

		
		-- 1.3.6.1.4.1.1916.2.131.50.1.4.3.2.11.1.1.42
		extremeWingStatsRfdWlRadioStatDetailRawRxRate OBJECT-TYPE
			SYNTAX Unsigned32
			UNITS "Mbps"
			MAX-ACCESS read-only
			STATUS current
			DESCRIPTION
				"The effective phy-layer receive rate for raw data
				
				XPath: /extremeWing-stats/rf_domain[name=key1]/wireless/radio-stats-details[radio_id=key2]/raw_rx_rate"
			::= { extremeWingStatsRfdWlRadioStatDetailEntry 42 }

		
		-- 1.3.6.1.4.1.1916.2.131.50.1.4.3.2.11.1.1.43
		extremeWingStatsRfdWlRadioStatDetailRawOverallRate OBJECT-TYPE
			SYNTAX Unsigned32
			UNITS "Mbps"
			MAX-ACCESS read-only
			STATUS current
			DESCRIPTION
				"The effective phy-layer overall rate, averaged on transmit
				and receive for raw data
				
				XPath: /extremeWing-stats/rf_domain[name=key1]/wireless/radio-stats-details[radio_id=key2]/raw_overall_rate"
			::= { extremeWingStatsRfdWlRadioStatDetailEntry 43 }

		
		-- 1.3.6.1.4.1.1916.2.131.50.1.4.3.2.11.1.1.44
		extremeWingStatsRfdWlRadioStatDetailTxBcmcPkts OBJECT-TYPE
			SYNTAX Counter64
			MAX-ACCESS read-only
			STATUS current
			DESCRIPTION
				"Number of broadcast packets transmitted by the radio
				
				XPath: /extremeWing-stats/rf_domain[name=key1]/wireless/radio-stats-details[radio_id=key2]/tx_bcmc_pkts"
			::= { extremeWingStatsRfdWlRadioStatDetailEntry 44 }

		
		-- 1.3.6.1.4.1.1916.2.131.50.1.4.3.2.11.1.1.45
		extremeWingStatsRfdWlRadioStatDetailRxBcmcPkts OBJECT-TYPE
			SYNTAX Counter64
			MAX-ACCESS read-only
			STATUS current
			DESCRIPTION
				"Number of broadcast packets of received by the radio
				
				XPath: /extremeWing-stats/rf_domain[name=key1]/wireless/radio-stats-details[radio_id=key2]/rx_bcmc_pkts"
			::= { extremeWingStatsRfdWlRadioStatDetailEntry 45 }

		
		-- 1.3.6.1.4.1.1916.2.131.50.1.4.3.2.11.1.1.46
		extremeWingStatsRfdWlRadioStatDetailTotalBcmcPkts OBJECT-TYPE
			SYNTAX Counter64
			MAX-ACCESS read-only
			STATUS current
			DESCRIPTION
				"Total Number of broadcast packets through the radio
				
				XPath: /extremeWing-stats/rf_domain[name=key1]/wireless/radio-stats-details[radio_id=key2]/total_bcmc_pkts"
			::= { extremeWingStatsRfdWlRadioStatDetailEntry 46 }

		
		-- 1.3.6.1.4.1.1916.2.131.50.1.4.3.2.11.1.1.47
		extremeWingStatsRfdWlRadioStatDetailTxPps OBJECT-TYPE
			SYNTAX Unsigned32
			MAX-ACCESS read-only
			STATUS current
			DESCRIPTION
				"Packet rate per second transmitted by the radio
				
				XPath: /extremeWing-stats/rf_domain[name=key1]/wireless/radio-stats-details[radio_id=key2]/tx_pps"
			::= { extremeWingStatsRfdWlRadioStatDetailEntry 47 }

		
		-- 1.3.6.1.4.1.1916.2.131.50.1.4.3.2.11.1.1.48
		extremeWingStatsRfdWlRadioStatDetailRxPps OBJECT-TYPE
			SYNTAX Unsigned32
			MAX-ACCESS read-only
			STATUS current
			DESCRIPTION
				"Packet rate per second received by the radio
				
				XPath: /extremeWing-stats/rf_domain[name=key1]/wireless/radio-stats-details[radio_id=key2]/rx_pps"
			::= { extremeWingStatsRfdWlRadioStatDetailEntry 48 }

		
		-- 1.3.6.1.4.1.1916.2.131.50.1.4.3.2.11.1.1.49
		extremeWingStatsRfdWlRadioStatDetailTotalPps OBJECT-TYPE
			SYNTAX Unsigned32
			MAX-ACCESS read-only
			STATUS current
			DESCRIPTION
				"Packet rate per second through the radio
				
				XPath: /extremeWing-stats/rf_domain[name=key1]/wireless/radio-stats-details[radio_id=key2]/total_pps"
			::= { extremeWingStatsRfdWlRadioStatDetailEntry 49 }

		
		-- 1.3.6.1.4.1.1916.2.131.50.1.4.3.2.11.1.1.50
		extremeWingStatsRfdWlRadioStatDetailTxMgmtPkts OBJECT-TYPE
			SYNTAX Counter64
			MAX-ACCESS read-only
			STATUS current
			DESCRIPTION
				"Number of management packets of transmitted by the radio
				
				XPath: /extremeWing-stats/rf_domain[name=key1]/wireless/radio-stats-details[radio_id=key2]/tx_mgmt_pkts"
			::= { extremeWingStatsRfdWlRadioStatDetailEntry 50 }

		
		-- 1.3.6.1.4.1.1916.2.131.50.1.4.3.2.11.1.1.51
		extremeWingStatsRfdWlRadioStatDetailRxMgmtPkts OBJECT-TYPE
			SYNTAX Counter64
			MAX-ACCESS read-only
			STATUS current
			DESCRIPTION
				"Number of management packets of received by the radio
				
				XPath: /extremeWing-stats/rf_domain[name=key1]/wireless/radio-stats-details[radio_id=key2]/rx_mgmt_pkts"
			::= { extremeWingStatsRfdWlRadioStatDetailEntry 51 }

		
		-- 1.3.6.1.4.1.1916.2.131.50.1.4.3.2.11.1.1.52
		extremeWingStatsRfdWlRadioStatDetailTotalMgmtPkts OBJECT-TYPE
			SYNTAX Counter64
			MAX-ACCESS read-only
			STATUS current
			DESCRIPTION
				"Number of management packets through the radio
				
				XPath: /extremeWing-stats/rf_domain[name=key1]/wireless/radio-stats-details[radio_id=key2]/total_mgmt_pkts"
			::= { extremeWingStatsRfdWlRadioStatDetailEntry 52 }

		
		-- 1.3.6.1.4.1.1916.2.131.50.1.4.3.2.11.1.1.53
		extremeWingStatsRfdWlRadioStatDetailTxRetries OBJECT-TYPE
			SYNTAX Counter64
			MAX-ACCESS read-only
			STATUS current
			DESCRIPTION
				"Total number of retries
				
				XPath: /extremeWing-stats/rf_domain[name=key1]/wireless/radio-stats-details[radio_id=key2]/tx_retries"
			::= { extremeWingStatsRfdWlRadioStatDetailEntry 53 }

		
		-- 1.3.6.1.4.1.1916.2.131.50.1.4.3.2.11.1.1.54
		extremeWingStatsRfdWlRadioStatDetailRxProbes OBJECT-TYPE
			SYNTAX Counter64
			MAX-ACCESS read-only
			STATUS current
			DESCRIPTION
				"Total number of probe-request packets received
				
				XPath: /extremeWing-stats/rf_domain[name=key1]/wireless/radio-stats-details[radio_id=key2]/rx_probes"
			::= { extremeWingStatsRfdWlRadioStatDetailEntry 54 }

		
		-- 1.3.6.1.4.1.1916.2.131.50.1.4.3.2.11.1.1.55
		extremeWingStatsRfdWlRadioStatDetailRxActions OBJECT-TYPE
			SYNTAX Counter64
			MAX-ACCESS read-only
			STATUS current
			DESCRIPTION
				"Total number of action packets received
				
				XPath: /extremeWing-stats/rf_domain[name=key1]/wireless/radio-stats-details[radio_id=key2]/rx_actions"
			::= { extremeWingStatsRfdWlRadioStatDetailEntry 55 }

		
		-- 1.3.6.1.4.1.1916.2.131.50.1.4.3.2.11.1.1.56
		extremeWingStatsRfdWlRadioStatDetailRxPsPoll OBJECT-TYPE
			SYNTAX Counter64
			MAX-ACCESS read-only
			STATUS current
			DESCRIPTION
				"Total number of PS-Poll packets received
				
				XPath: /extremeWing-stats/rf_domain[name=key1]/wireless/radio-stats-details[radio_id=key2]/rx_ps_poll"
			::= { extremeWingStatsRfdWlRadioStatDetailEntry 56 }

		
		-- 1.3.6.1.4.1.1916.2.131.50.1.4.3.2.11.1.1.57
		extremeWingStatsRfdWlRadioStatDetailLastCallStatus OBJECT-TYPE
			SYNTAX DisplayString
			MAX-ACCESS read-only
			STATUS current
			DESCRIPTION
				"Last voice call status
				
				XPath: /extremeWing-stats/rf_domain[name=key1]/wireless/radio-stats-details[radio_id=key2]/last_call_status"
			::= { extremeWingStatsRfdWlRadioStatDetailEntry 57 }

		
		-- 1.3.6.1.4.1.1916.2.131.50.1.4.3.2.11.1.1.58
		extremeWingStatsRfdWlRadioStatDetailCallTotal OBJECT-TYPE
			SYNTAX Counter32
			MAX-ACCESS read-only
			STATUS current
			DESCRIPTION
				"Total number of voice calls attempted
				
				XPath: /extremeWing-stats/rf_domain[name=key1]/wireless/radio-stats-details[radio_id=key2]/call_total"
			::= { extremeWingStatsRfdWlRadioStatDetailEntry 58 }

		
		-- 1.3.6.1.4.1.1916.2.131.50.1.4.3.2.11.1.1.59
		extremeWingStatsRfdWlRadioStatDetailCallStatOk OBJECT-TYPE
			SYNTAX Counter32
			MAX-ACCESS read-only
			STATUS current
			DESCRIPTION
				"Voice calls successfully made
				
				XPath: /extremeWing-stats/rf_domain[name=key1]/wireless/radio-stats-details[radio_id=key2]/call_status_ok"
			::= { extremeWingStatsRfdWlRadioStatDetailEntry 59 }

		
		-- 1.3.6.1.4.1.1916.2.131.50.1.4.3.2.11.1.1.60
		extremeWingStatsRfdWlRadioStatDetailCallStatBusy OBJECT-TYPE
			SYNTAX Counter32
			MAX-ACCESS read-only
			STATUS current
			DESCRIPTION
				"Voice calls failed because of busy
				
				XPath: /extremeWing-stats/rf_domain[name=key1]/wireless/radio-stats-details[radio_id=key2]/call_status_busy"
			::= { extremeWingStatsRfdWlRadioStatDetailEntry 60 }

		
		-- 1.3.6.1.4.1.1916.2.131.50.1.4.3.2.11.1.1.61
		extremeWingStatsRfdWlRadioStatDetailCallStatNoAnswer OBJECT-TYPE
			SYNTAX Counter32
			MAX-ACCESS read-only
			STATUS current
			DESCRIPTION
				"Voice calls failed because of no-answer
				
				XPath: /extremeWing-stats/rf_domain[name=key1]/wireless/radio-stats-details[radio_id=key2]/call_status_no_answer"
			::= { extremeWingStatsRfdWlRadioStatDetailEntry 61 }

		
		-- 1.3.6.1.4.1.1916.2.131.50.1.4.3.2.11.1.1.62
		extremeWingStatsRfdWlRadioStatDetailCallStatUnknownDest OBJECT-TYPE
			SYNTAX Counter32
			MAX-ACCESS read-only
			STATUS current
			DESCRIPTION
				"Voice calls failed because of unknown destination
				
				XPath: /extremeWing-stats/rf_domain[name=key1]/wireless/radio-stats-details[radio_id=key2]/call_status_unknown_dest"
			::= { extremeWingStatsRfdWlRadioStatDetailEntry 62 }

		
		-- 1.3.6.1.4.1.1916.2.131.50.1.4.3.2.11.1.1.63
		extremeWingStatsRfdWlRadioStatDetailCallStatAdmDenied OBJECT-TYPE
			SYNTAX Counter32
			MAX-ACCESS read-only
			STATUS current
			DESCRIPTION
				"Voice calls failed because of admission denied
				
				XPath: /extremeWing-stats/rf_domain[name=key1]/wireless/radio-stats-details[radio_id=key2]/call_status_admission_denied"
			::= { extremeWingStatsRfdWlRadioStatDetailEntry 63 }

		
		-- 1.3.6.1.4.1.1916.2.131.50.1.4.3.2.11.1.1.64
		extremeWingStatsRfdWlRadioStatDetailCallStatDeclined OBJECT-TYPE
			SYNTAX Counter32
			MAX-ACCESS read-only
			STATUS current
			DESCRIPTION
				"Voice calls failed because of being declined
				
				XPath: /extremeWing-stats/rf_domain[name=key1]/wireless/radio-stats-details[radio_id=key2]/call_status_declined"
			::= { extremeWingStatsRfdWlRadioStatDetailEntry 64 }

		
		-- 1.3.6.1.4.1.1916.2.131.50.1.4.3.2.11.1.1.65
		extremeWingStatsRfdWlRadioStatDetailCallStatUnauth OBJECT-TYPE
			SYNTAX Counter32
			MAX-ACCESS read-only
			STATUS current
			DESCRIPTION
				"Voice calls failed because of being unauthorized
				
				XPath: /extremeWing-stats/rf_domain[name=key1]/wireless/radio-stats-details[radio_id=key2]/call_status_unauthorized"
			::= { extremeWingStatsRfdWlRadioStatDetailEntry 65 }

		
		-- 1.3.6.1.4.1.1916.2.131.50.1.4.3.2.11.1.1.66
		extremeWingStatsRfdWlRadioStatDetailCallStatUnsuppMedia OBJECT-TYPE
			SYNTAX Counter32
			MAX-ACCESS read-only
			STATUS current
			DESCRIPTION
				"Voice calls failed because of unsupported media
				
				XPath: /extremeWing-stats/rf_domain[name=key1]/wireless/radio-stats-details[radio_id=key2]/call_status_unsupported_media"
			::= { extremeWingStatsRfdWlRadioStatDetailEntry 66 }

		
		-- 1.3.6.1.4.1.1916.2.131.50.1.4.3.2.11.1.1.67
		extremeWingStatsRfdWlRadioStatDetailCallStatTempUnavail OBJECT-TYPE
			SYNTAX Counter32
			MAX-ACCESS read-only
			STATUS current
			DESCRIPTION
				"Voice calls failed because of temporarily
				unavailable resources
				
				XPath: /extremeWing-stats/rf_domain[name=key1]/wireless/radio-stats-details[radio_id=key2]/call_status_temporarily_unavailable"
			::= { extremeWingStatsRfdWlRadioStatDetailEntry 67 }

		
		-- 1.3.6.1.4.1.1916.2.131.50.1.4.3.2.11.1.1.68
		extremeWingStatsRfdWlRadioStatDetailCallStatNoForkAllowed OBJECT-TYPE
			SYNTAX Counter32
			MAX-ACCESS read-only
			STATUS current
			DESCRIPTION
				"Voice calls failed because of no-fork-allowed
				
				XPath: /extremeWing-stats/rf_domain[name=key1]/wireless/radio-stats-details[radio_id=key2]/call_status_no_fork_allowed"
			::= { extremeWingStatsRfdWlRadioStatDetailEntry 68 }

		
		-- 1.3.6.1.4.1.1916.2.131.50.1.4.3.2.11.1.1.69
		extremeWingStatsRfdWlRadioStatDetailCallStatSessInactive OBJECT-TYPE
			SYNTAX Counter32
			MAX-ACCESS read-only
			STATUS current
			DESCRIPTION
				"Voice calls ended because of session-inactive
				
				XPath: /extremeWing-stats/rf_domain[name=key1]/wireless/radio-stats-details[radio_id=key2]/call_status_session_inactive"
			::= { extremeWingStatsRfdWlRadioStatDetailEntry 69 }

		
		-- 1.3.6.1.4.1.1916.2.131.50.1.4.3.2.11.1.1.70
		extremeWingStatsRfdWlRadioStatDetailCallStatOther OBJECT-TYPE
			SYNTAX Counter32
			MAX-ACCESS read-only
			STATUS current
			DESCRIPTION
				"Voice calls ended for unknown reason
				
				XPath: /extremeWing-stats/rf_domain[name=key1]/wireless/radio-stats-details[radio_id=key2]/call_status_other"
			::= { extremeWingStatsRfdWlRadioStatDetailEntry 70 }

		
		-- 1.3.6.1.4.1.1916.2.131.50.1.4.3.2.11.1.1.71
		extremeWingStatsRfdWlRadioStatDetailTotalBytes OBJECT-TYPE
			SYNTAX Counter64
			MAX-ACCESS read-only
			STATUS current
			DESCRIPTION
				"Total mumber of data bytes through the radio
				
				XPath: /extremeWing-stats/rf_domain[name=key1]/wireless/radio-stats-details[radio_id=key2]/total_bytes"
			::= { extremeWingStatsRfdWlRadioStatDetailEntry 71 }

		
		-- 1.3.6.1.4.1.1916.2.131.50.1.4.3.2.11.1.1.72
		extremeWingStatsRfdWlRadioStatDetailTotalPkts OBJECT-TYPE
			SYNTAX Counter64
			MAX-ACCESS read-only
			STATUS current
			DESCRIPTION
				"Total number of packets through the radio
				
				XPath: /extremeWing-stats/rf_domain[name=key1]/wireless/radio-stats-details[radio_id=key2]/total_pkts"
			::= { extremeWingStatsRfdWlRadioStatDetailEntry 72 }

		
		-- 1.3.6.1.4.1.1916.2.131.50.1.4.3.2.11.1.1.73
		extremeWingStatsRfdWlRadioStatDetailRxRetries OBJECT-TYPE
			SYNTAX Counter64
			MAX-ACCESS read-only
			STATUS current
			DESCRIPTION
				"Received packets with retries
				
				XPath: /extremeWing-stats/rf_domain[name=key1]/wireless/radio-stats-details[radio_id=key2]/rx_retries"
			::= { extremeWingStatsRfdWlRadioStatDetailEntry 73 }

		
		-- 1.3.6.1.4.1.1916.2.131.50.1.4.3.2.11.1.1.74
		extremeWingStatsRfdWlRadioStatDetailRxCrcErrors OBJECT-TYPE
			SYNTAX Counter64
			MAX-ACCESS read-only
			STATUS current
			DESCRIPTION
				"Received packets with CRC errors
				
				XPath: /extremeWing-stats/rf_domain[name=key1]/wireless/radio-stats-details[radio_id=key2]/rx_crc_errors"
			::= { extremeWingStatsRfdWlRadioStatDetailEntry 74 }

		
		-- 1.3.6.1.4.1.1916.2.131.50.1.4.3.2.11.1.1.75
		extremeWingStatsRfdWlRadioStatDetailRxUndecryptable OBJECT-TYPE
			SYNTAX Counter64
			MAX-ACCESS read-only
			STATUS current
			DESCRIPTION
				"Received undecryptable packets
				
				XPath: /extremeWing-stats/rf_domain[name=key1]/wireless/radio-stats-details[radio_id=key2]/rx_undecryptable"
			::= { extremeWingStatsRfdWlRadioStatDetailEntry 75 }

		
		-- 1.3.6.1.4.1.1916.2.131.50.1.4.3.2.11.1.1.76
		extremeWingStatsRfdWlRadioStatDetailRxIncomplete OBJECT-TYPE
			SYNTAX Counter64
			MAX-ACCESS read-only
			STATUS current
			DESCRIPTION
				"Received incomplete packets
				
				XPath: /extremeWing-stats/rf_domain[name=key1]/wireless/radio-stats-details[radio_id=key2]/rx_incomplete"
			::= { extremeWingStatsRfdWlRadioStatDetailEntry 76 }

		
		-- 1.3.6.1.4.1.1916.2.131.50.1.4.3.2.11.1.1.77
		extremeWingStatsRfdWlRadioStatDetailRxLengthErrors OBJECT-TYPE
			SYNTAX Counter64
			MAX-ACCESS read-only
			STATUS current
			DESCRIPTION
				"Received packets with length errors
				
				XPath: /extremeWing-stats/rf_domain[name=key1]/wireless/radio-stats-details[radio_id=key2]/rx_length_errors"
			::= { extremeWingStatsRfdWlRadioStatDetailEntry 77 }

		
		-- 1.3.6.1.4.1.1916.2.131.50.1.4.3.2.11.1.1.78
		extremeWingStatsRfdWlRadioStatDetailRxOtherErrors OBJECT-TYPE
			SYNTAX Counter64
			MAX-ACCESS read-only
			STATUS current
			DESCRIPTION
				"Received packets with other errors
				
				XPath: /extremeWing-stats/rf_domain[name=key1]/wireless/radio-stats-details[radio_id=key2]/rx_other_errors"
			::= { extremeWingStatsRfdWlRadioStatDetailEntry 78 }

		
		-- 1.3.6.1.4.1.1916.2.131.50.1.4.3.2.11.1.1.79
		extremeWingStatsRfdWlRadioStatDetailLongPreambleClients OBJECT-TYPE
			SYNTAX Unsigned32
			MAX-ACCESS read-only
			STATUS current
			DESCRIPTION
				"Long-preamble-only only clients
				
				XPath: /extremeWing-stats/rf_domain[name=key1]/wireless/radio-stats-details[radio_id=key2]/long_preamble_clients"
			::= { extremeWingStatsRfdWlRadioStatDetailEntry 79 }

		
		-- 1.3.6.1.4.1.1916.2.131.50.1.4.3.2.11.1.1.80
		extremeWingStatsRfdWlRadioStatDetailLtClients OBJECT-TYPE
			SYNTAX Unsigned32
			MAX-ACCESS read-only
			STATUS current
			DESCRIPTION
				"Low throughput clients in contrast to HT client
				
				XPath: /extremeWing-stats/rf_domain[name=key1]/wireless/radio-stats-details[radio_id=key2]/lt_clients"
			::= { extremeWingStatsRfdWlRadioStatDetailEntry 80 }

		
		-- 1.3.6.1.4.1.1916.2.131.50.1.4.3.2.11.1.1.81
		extremeWingStatsRfdWlRadioStatDetailHt20Clients OBJECT-TYPE
			SYNTAX Unsigned32
			MAX-ACCESS read-only
			STATUS current
			DESCRIPTION
				"HT client single channel only
				
				XPath: /extremeWing-stats/rf_domain[name=key1]/wireless/radio-stats-details[radio_id=key2]/ht_20_clients"
			::= { extremeWingStatsRfdWlRadioStatDetailEntry 81 }

		
		-- 1.3.6.1.4.1.1916.2.131.50.1.4.3.2.11.1.1.82
		extremeWingStatsRfdWlRadioStatDetailLongSlotClients OBJECT-TYPE
			SYNTAX Unsigned32
			MAX-ACCESS read-only
			STATUS current
			DESCRIPTION
				"Long slot clients
				
				XPath: /extremeWing-stats/rf_domain[name=key1]/wireless/radio-stats-details[radio_id=key2]/long_slot_clients"
			::= { extremeWingStatsRfdWlRadioStatDetailEntry 82 }

		
		-- 1.3.6.1.4.1.1916.2.131.50.1.4.3.2.11.1.1.83
		extremeWingStatsRfdWlRadioStatDetailTxRetriedBytes OBJECT-TYPE
			SYNTAX Counter64
			MAX-ACCESS read-only
			STATUS current
			DESCRIPTION
				"Total retried bytes excluding bytes sent.				    
				XPath: /extremeWing-stats/rf_domain[name=key1]/wireless/radio-stats-details[radio_id=key2]/tx_retried_bytes."
			::= { extremeWingStatsRfdWlRadioStatDetailEntry 83 }


		-- 1.3.6.1.4.1.1916.2.131.50.1.4.3.3
		extremeWingStatsRfdCaptivePortal OBJECT IDENTIFIER ::= { extremeWingStatsRfd 3 }

		
		-- 1.3.6.1.4.1.1916.2.131.50.1.4.3.3.1
		extremeWingStatsRfdCaptivePortalClientTable OBJECT-TYPE
			SYNTAX SEQUENCE OF ExtremeWingStatsRfdCaptivePortalClientEntry
			MAX-ACCESS not-accessible
			STATUS current
			DESCRIPTION
				"Information about Captive Portal Clients on this rf-domain
				
				Xpath = /extremeWing-stats/rf_domain[name=key1]/captive-portal[mac=key2]/client"
			::= { extremeWingStatsRfdCaptivePortal 1 }

		
		-- 1.3.6.1.4.1.1916.2.131.50.1.4.3.3.1.1
		extremeWingStatsRfdCaptivePortalClientEntry OBJECT-TYPE
			SYNTAX ExtremeWingStatsRfdCaptivePortalClientEntry
			MAX-ACCESS not-accessible
			STATUS current
			DESCRIPTION
				"An entry in the table."
			INDEX { extremeWingStatsRfdName }
			::= { extremeWingStatsRfdCaptivePortalClientTable 1 }

		
		ExtremeWingStatsRfdCaptivePortalClientEntry ::=
			SEQUENCE { 
				extremeWingStatsRfdCaptivePortalClientCp
					DisplayString,
				extremeWingStatsRfdCaptivePortalClientIPv4
					IpAddress,
				extremeWingStatsRfdCaptivePortalClientMac
					MacAddress,
				extremeWingStatsRfdCaptivePortalClientSessTime
					Unsigned32,
				extremeWingStatsRfdCaptivePortalClientState
					DisplayString,
				extremeWingStatsRfdCaptivePortalClientVlan
					Unsigned32,
				extremeWingStatsRfdCaptivePortalClientWlan
					DisplayString,
				extremeWingStatsRfdCaptivePortalClientRxBytes
					Counter64,
				extremeWingStatsRfdCaptivePortalClientRxPkts
					Counter32,
				extremeWingStatsRfdCaptivePortalClientTxBytes
					Counter64,
				extremeWingStatsRfdCaptivePortalClientTxPkts
					Counter32
			 }

		-- 1.3.6.1.4.1.1916.2.131.50.1.4.3.3.1.1.1
		extremeWingStatsRfdCaptivePortalClientCp OBJECT-TYPE
			SYNTAX DisplayString (SIZE (0..64))
			MAX-ACCESS read-only
			STATUS current
			DESCRIPTION
				"Captive Portal to which the client is authenticated
				
				XPath: /extremeWing-stats/rf_domain[name=key1]/captive-portal/client[mac=key2]/cp"
			::= { extremeWingStatsRfdCaptivePortalClientEntry 1 }

		
		-- 1.3.6.1.4.1.1916.2.131.50.1.4.3.3.1.1.2
		extremeWingStatsRfdCaptivePortalClientIPv4 OBJECT-TYPE
			SYNTAX IpAddress
			MAX-ACCESS read-only
			STATUS current
			DESCRIPTION
				"IP Address of the Captive Portal Client
				
				
				XPath: /extremeWing-stats/rf_domain[name=key1]/captive-portal/client[mac=key2]/ipv4"
			::= { extremeWingStatsRfdCaptivePortalClientEntry 2 }

		
		-- 1.3.6.1.4.1.1916.2.131.50.1.4.3.3.1.1.3
		extremeWingStatsRfdCaptivePortalClientMac OBJECT-TYPE
			SYNTAX MacAddress
			MAX-ACCESS read-only
			STATUS current
			DESCRIPTION
				"Captive Portal Client MAC Address
				
				
				XPath: /extremeWing-stats/rf_domain[name=key1]/captive-portal/client[mac=key2]/mac"
			::= { extremeWingStatsRfdCaptivePortalClientEntry 3 }

		
		-- 1.3.6.1.4.1.1916.2.131.50.1.4.3.3.1.1.4
		extremeWingStatsRfdCaptivePortalClientSessTime OBJECT-TYPE
			SYNTAX Unsigned32
			MAX-ACCESS read-only
			STATUS current
			DESCRIPTION
				"Remaining allowed session time
				
				
				XPath: /extremeWing-stats/rf_domain[name=key1]/captive-portal/client[mac=key2]/sess_time"
			::= { extremeWingStatsRfdCaptivePortalClientEntry 4 }

		
		-- 1.3.6.1.4.1.1916.2.131.50.1.4.3.3.1.1.5
		extremeWingStatsRfdCaptivePortalClientState OBJECT-TYPE
			SYNTAX DisplayString
			MAX-ACCESS read-only
			STATUS current
			DESCRIPTION
				"current auth state of the client
				
				
				XPath: /extremeWing-stats/rf_domain[name=key1]/captive-portal/client[mac=key2]/state"
			::= { extremeWingStatsRfdCaptivePortalClientEntry 5 }

		
		-- 1.3.6.1.4.1.1916.2.131.50.1.4.3.3.1.1.6
		extremeWingStatsRfdCaptivePortalClientVlan OBJECT-TYPE
			SYNTAX Unsigned32
			MAX-ACCESS read-only
			STATUS current
			DESCRIPTION
				"The VLAN assigned to the Captive Portal Client
				
				
				XPath: /extremeWing-stats/rf_domain[name=key1]/captive-portal/client[mac=key2]/Vlan"
			::= { extremeWingStatsRfdCaptivePortalClientEntry 6 }

		
		-- 1.3.6.1.4.1.1916.2.131.50.1.4.3.3.1.1.7
		extremeWingStatsRfdCaptivePortalClientWlan OBJECT-TYPE
			SYNTAX DisplayString (SIZE (0..64))
			MAX-ACCESS read-only
			STATUS current
			DESCRIPTION
				"wlan where the Captive Portal Client is associated
				
				
				XPath: /extremeWing-stats/rf_domain[name=key1]/captive-portal/client[mac=key2]/wlan"
			::= { extremeWingStatsRfdCaptivePortalClientEntry 7 }

		
		-- 1.3.6.1.4.1.1916.2.131.50.1.4.3.3.1.1.8
		extremeWingStatsRfdCaptivePortalClientRxBytes OBJECT-TYPE
			SYNTAX Counter64
			MAX-ACCESS read-only
			STATUS current
			DESCRIPTION
				"				    
				XPath: /extremeWing-stats/rf_domain[name=key1]/captive-portal/client[mac=key2]/rx_bytes."
			::= { extremeWingStatsRfdCaptivePortalClientEntry 8 }


		-- 1.3.6.1.4.1.1916.2.131.50.1.4.3.3.1.1.9
		extremeWingStatsRfdCaptivePortalClientRxPkts OBJECT-TYPE
			SYNTAX Counter32
			MAX-ACCESS read-only
			STATUS current
			DESCRIPTION
				"				    
				XPath: /extremeWing-stats/rf_domain[name=key1]/captive-portal/client[mac=key2]/rx_pkts."
			::= { extremeWingStatsRfdCaptivePortalClientEntry 9 }


		-- 1.3.6.1.4.1.1916.2.131.50.1.4.3.3.1.1.10
		extremeWingStatsRfdCaptivePortalClientTxBytes OBJECT-TYPE
			SYNTAX Counter64
			MAX-ACCESS read-only
			STATUS current
			DESCRIPTION
				"				    
				XPath: /extremeWing-stats/rf_domain[name=key1]/captive-portal/client[mac=key2]/tx_bytes."
			::= { extremeWingStatsRfdCaptivePortalClientEntry 10 }


		-- 1.3.6.1.4.1.1916.2.131.50.1.4.3.3.1.1.11
		extremeWingStatsRfdCaptivePortalClientTxPkts OBJECT-TYPE
			SYNTAX Counter32
			MAX-ACCESS read-only
			STATUS current
			DESCRIPTION
				"				    
				XPath: /extremeWing-stats/rf_domain[name=key1]/captive-portal/client[mac=key2]/tx_pkts."
			::= { extremeWingStatsRfdCaptivePortalClientEntry 11 }


		-- 1.3.6.1.4.1.1916.2.131.50.1.4.3.5
		extremeWingStatsRfdSmartRf OBJECT IDENTIFIER ::= { extremeWingStatsRfd 5 }

		
		-- 1.3.6.1.4.1.1916.2.131.50.1.4.3.5.1
		extremeWingStatsRfdSmartRfRadioInfoTable OBJECT-TYPE
			SYNTAX SEQUENCE OF ExtremeWingStatsRfdSmartRfRadioInfoEntry
			MAX-ACCESS not-accessible
			STATUS current
			DESCRIPTION
				"
				
				/extremeWing-stats/rf_domain/smart-rf/radio_info"
			::= { extremeWingStatsRfdSmartRf 1 }

		
		-- 1.3.6.1.4.1.1916.2.131.50.1.4.3.5.1.1
		extremeWingStatsRfdSmartRfRadioInfoEntry OBJECT-TYPE
			SYNTAX ExtremeWingStatsRfdSmartRfRadioInfoEntry
			MAX-ACCESS not-accessible
			STATUS current
			DESCRIPTION
				"An entry in the table."
			INDEX { extremeWingStatsRfdName, extremeWingStatsRfdSmartRfRadioInfoMac }
			::= { extremeWingStatsRfdSmartRfRadioInfoTable 1 }

		
		ExtremeWingStatsRfdSmartRfRadioInfoEntry ::=
			SEQUENCE { 
				extremeWingStatsRfdSmartRfRadioInfoMac
					ExtremeWingIdentifier,
				extremeWingStatsRfdSmartRfRadioInfoApMac
					DisplayString,
				extremeWingStatsRfdSmartRfRadioInfoHostname
					DisplayString,
				extremeWingStatsRfdSmartRfRadioInfoChannel
					DisplayString,
				extremeWingStatsRfdSmartRfRadioInfoPower
					Unsigned32,
				extremeWingStatsRfdSmartRfRadioInfoRadioIdx
					Unsigned32,
				extremeWingStatsRfdSmartRfRadioInfoState
					DisplayString,
				extremeWingStatsRfdSmartRfRadioInfoType
					DisplayString
			 }

		-- 1.3.6.1.4.1.1916.2.131.50.1.4.3.5.1.1.1
		extremeWingStatsRfdSmartRfRadioInfoMac OBJECT-TYPE
			SYNTAX ExtremeWingIdentifier
			MAX-ACCESS read-only
			STATUS current
			DESCRIPTION
				"Radio MAC address
				
				XPath: /extremeWing-stats/rf_domain[name=key1]/smart-rf/radio_info[mac=key2]/mac"
			::= { extremeWingStatsRfdSmartRfRadioInfoEntry 1 }

		
		-- 1.3.6.1.4.1.1916.2.131.50.1.4.3.5.1.1.3
		extremeWingStatsRfdSmartRfRadioInfoApMac OBJECT-TYPE
			SYNTAX DisplayString
			MAX-ACCESS read-only
			STATUS current
			DESCRIPTION
				"Access point MAC address in which this radio is present
				
				XPath: /extremeWing-stats/rf_domain[name=key1]/smart-rf/radio_info[mac=key2]/ap_mac"
			::= { extremeWingStatsRfdSmartRfRadioInfoEntry 3 }

		
		-- 1.3.6.1.4.1.1916.2.131.50.1.4.3.5.1.1.4
		extremeWingStatsRfdSmartRfRadioInfoHostname OBJECT-TYPE
			SYNTAX DisplayString (SIZE (64))
			MAX-ACCESS read-only
			STATUS current
			DESCRIPTION
				"Access point hostname in which this radio is present
				
				XPath: /extremeWing-stats/rf_domain[name=key1]/smart-rf/radio_info[mac=key2]/hostname"
			::= { extremeWingStatsRfdSmartRfRadioInfoEntry 4 }

		
		-- 1.3.6.1.4.1.1916.2.131.50.1.4.3.5.1.1.5
		extremeWingStatsRfdSmartRfRadioInfoChannel OBJECT-TYPE
			SYNTAX DisplayString
			MAX-ACCESS read-only
			STATUS current
			DESCRIPTION
				"Smart-rf assigned radio channel
				
				Values:
				1,
				1+,
				2,
				2+,
				3,
				3+,
				4,
				4+,
				5,
				5+,
				5-,
				6,
				6+,
				6-,
				7,
				7+,
				7-,
				8,
				8+,
				8-,
				9,
				9+,
				9-,
				10,
				10-,
				11,
				11-,
				12,
				12-,
				13,
				13-,
				14,
				36,
				36+,
				40,
				40-,
				44,
				44+,
				48,
				48-,
				52,
				52+,
				56,
				56-,
				60,
				60+,
				64,
				64-,
				100,
				100+,
				104,
				104-,
				108,
				108+,
				112,
				112-,
				116,
				116+,
				120,
				120-,
				124,
				124+,
				128,
				128-,
				132,
				132+,
				136,
				136-,
				140,
				149,
				149+,
				153,
				153-,
				157,
				157+,
				161,
				161-,
				165,
				34,
				38,
				42,
				46
				
				XPath: /extremeWing-stats/rf_domain[name=key1]/smart-rf/radio_info[mac=key2]/channel"
			::= { extremeWingStatsRfdSmartRfRadioInfoEntry 5 }

		
		-- 1.3.6.1.4.1.1916.2.131.50.1.4.3.5.1.1.6
		extremeWingStatsRfdSmartRfRadioInfoPower OBJECT-TYPE
			SYNTAX Unsigned32 (0..23)
			UNITS "dBm"
			MAX-ACCESS read-only
			STATUS current
			DESCRIPTION
				"Smart-rf assigned transmit power for this radio
				
				XPath: /extremeWing-stats/rf_domain[name=key1]/smart-rf/radio_info[mac=key2]/power"
			::= { extremeWingStatsRfdSmartRfRadioInfoEntry 6 }

		
		-- 1.3.6.1.4.1.1916.2.131.50.1.4.3.5.1.1.7
		extremeWingStatsRfdSmartRfRadioInfoRadioIdx OBJECT-TYPE
			SYNTAX Unsigned32
			MAX-ACCESS read-only
			STATUS current
			DESCRIPTION
				"Radio index of this radio in AP
				
				XPath: /extremeWing-stats/rf_domain[name=key1]/smart-rf/radio_info[mac=key2]/radio_idx"
			::= { extremeWingStatsRfdSmartRfRadioInfoEntry 7 }

		
		-- 1.3.6.1.4.1.1916.2.131.50.1.4.3.5.1.1.8
		extremeWingStatsRfdSmartRfRadioInfoState OBJECT-TYPE
			SYNTAX DisplayString
			MAX-ACCESS read-only
			STATUS current
			DESCRIPTION
				"Current radio state
				
				Values:
				offline,
				normal,
				sensor
				
				XPath: /extremeWing-stats/rf_domain[name=key1]/smart-rf/radio_info[mac=key2]/state"
			::= { extremeWingStatsRfdSmartRfRadioInfoEntry 8 }

		
		-- 1.3.6.1.4.1.1916.2.131.50.1.4.3.5.1.1.9
		extremeWingStatsRfdSmartRfRadioInfoType OBJECT-TYPE
			SYNTAX DisplayString
			MAX-ACCESS read-only
			STATUS current
			DESCRIPTION
				"Radio type
				
				Values:
				11an,
				11bgn
				
				XPath: /extremeWing-stats/rf_domain[name=key1]/smart-rf/radio_info[mac=key2]/type"
			::= { extremeWingStatsRfdSmartRfRadioInfoEntry 9 }

		
		-- 1.3.6.1.4.1.1916.2.131.50.1.4.3.5.2
		extremeWingStatsRfdSmartRfRadioActTable OBJECT-TYPE
			SYNTAX SEQUENCE OF ExtremeWingStatsRfdSmartRfRadioActEntry
			MAX-ACCESS not-accessible
			STATUS current
			DESCRIPTION
				"
				
				/extremeWing-stats/rf_domain/smart-rf/radio_activity"
			::= { extremeWingStatsRfdSmartRf 2 }

		
		-- 1.3.6.1.4.1.1916.2.131.50.1.4.3.5.2.1
		extremeWingStatsRfdSmartRfRadioActEntry OBJECT-TYPE
			SYNTAX ExtremeWingStatsRfdSmartRfRadioActEntry
			MAX-ACCESS not-accessible
			STATUS current
			DESCRIPTION
				"An entry in the table."
			INDEX { extremeWingStatsRfdName, extremeWingStatsRfdSmartRfRadioActMac }
			::= { extremeWingStatsRfdSmartRfRadioActTable 1 }

		
		ExtremeWingStatsRfdSmartRfRadioActEntry ::=
			SEQUENCE { 
				extremeWingStatsRfdSmartRfRadioActMac
					ExtremeWingIdentifier,
				extremeWingStatsRfdSmartRfRadioActApMac
					DisplayString,
				extremeWingStatsRfdSmartRfRadioActType
					DisplayString,
				extremeWingStatsRfdSmartRfRadioActPowerChanges
					Unsigned32,
				extremeWingStatsRfdSmartRfRadioActChannelChanges
					Unsigned32,
				extremeWingStatsRfdSmartRfRadioActCoverageChanges
					Unsigned32
			 }

		-- 1.3.6.1.4.1.1916.2.131.50.1.4.3.5.2.1.1
		extremeWingStatsRfdSmartRfRadioActMac OBJECT-TYPE
			SYNTAX ExtremeWingIdentifier
			MAX-ACCESS read-only
			STATUS current
			DESCRIPTION
				"Radio MAC address
				
				XPath: /extremeWing-stats/rf_domain[name=key1]/smart-rf/radio_activity[mac=key2]/mac"
			::= { extremeWingStatsRfdSmartRfRadioActEntry 1 }

		
		-- 1.3.6.1.4.1.1916.2.131.50.1.4.3.5.2.1.3
		extremeWingStatsRfdSmartRfRadioActApMac OBJECT-TYPE
			SYNTAX DisplayString
			MAX-ACCESS read-only
			STATUS current
			DESCRIPTION
				"Access point MAC address in which this radio is present
				
				XPath: /extremeWing-stats/rf_domain[name=key1]/smart-rf/radio_activity[mac=key2]/ap_mac"
			::= { extremeWingStatsRfdSmartRfRadioActEntry 3 }

		
		-- 1.3.6.1.4.1.1916.2.131.50.1.4.3.5.2.1.4
		extremeWingStatsRfdSmartRfRadioActType OBJECT-TYPE
			SYNTAX DisplayString
			MAX-ACCESS read-only
			STATUS current
			DESCRIPTION
				"Radio type
				
				Values:
				11an,
				11bgn
				
				XPath: /extremeWing-stats/rf_domain[name=key1]/smart-rf/radio_activity[mac=key2]/type"
			::= { extremeWingStatsRfdSmartRfRadioActEntry 4 }

		
		-- 1.3.6.1.4.1.1916.2.131.50.1.4.3.5.2.1.5
		extremeWingStatsRfdSmartRfRadioActPowerChanges OBJECT-TYPE
			SYNTAX Unsigned32 (0..1024)
			MAX-ACCESS read-only
			STATUS current
			DESCRIPTION
				"Number of neighbor recovery power changes for this radio
				
				XPath: /extremeWing-stats/rf_domain[name=key1]/smart-rf/radio_activity[mac=key2]/power_changes"
			::= { extremeWingStatsRfdSmartRfRadioActEntry 5 }

		
		-- 1.3.6.1.4.1.1916.2.131.50.1.4.3.5.2.1.6
		extremeWingStatsRfdSmartRfRadioActChannelChanges OBJECT-TYPE
			SYNTAX Unsigned32 (0..1024)
			MAX-ACCESS read-only
			STATUS current
			DESCRIPTION
				"Number of channel changes for this radio
				
				XPath: /extremeWing-stats/rf_domain[name=key1]/smart-rf/radio_activity[mac=key2]/channel_changes"
			::= { extremeWingStatsRfdSmartRfRadioActEntry 6 }

		
		-- 1.3.6.1.4.1.1916.2.131.50.1.4.3.5.2.1.7
		extremeWingStatsRfdSmartRfRadioActCoverageChanges OBJECT-TYPE
			SYNTAX Unsigned32 (0..1024)
			MAX-ACCESS read-only
			STATUS current
			DESCRIPTION
				"Number of coverage hole recovery power changes for this radio
				
				XPath: /extremeWing-stats/rf_domain[name=key1]/smart-rf/radio_activity[mac=key2]/coverage_changes"
			::= { extremeWingStatsRfdSmartRfRadioActEntry 7 }

		
		-- 1.3.6.1.4.1.1916.2.131.50.1.4.3.5.3
		extremeWingStatsRfdSmartRfRadioNeighborsTable OBJECT-TYPE
			SYNTAX SEQUENCE OF ExtremeWingStatsRfdSmartRfRadioNeighborsEntry
			MAX-ACCESS not-accessible
			STATUS current
			DESCRIPTION
				"
				
				/extremeWing-stats/rf_domain/smart-rf/radio_neighbors"
			::= { extremeWingStatsRfdSmartRf 3 }

		
		-- 1.3.6.1.4.1.1916.2.131.50.1.4.3.5.3.1
		extremeWingStatsRfdSmartRfRadioNeighborsEntry OBJECT-TYPE
			SYNTAX ExtremeWingStatsRfdSmartRfRadioNeighborsEntry
			MAX-ACCESS not-accessible
			STATUS current
			DESCRIPTION
				"An entry in the table."
			INDEX { extremeWingStatsRfdName, extremeWingStatsRfdSmartRfRadioNeighborsMac }
			::= { extremeWingStatsRfdSmartRfRadioNeighborsTable 1 }

		
		ExtremeWingStatsRfdSmartRfRadioNeighborsEntry ::=
			SEQUENCE { 
				extremeWingStatsRfdSmartRfRadioNeighborsMac
					ExtremeWingIdentifier,
				extremeWingStatsRfdSmartRfRadioNeighborsApMac
					DisplayString,
				extremeWingStatsRfdSmartRfRadioNeighborsHostname
					DisplayString,
				extremeWingStatsRfdSmartRfRadioNeighborsChannel
					DisplayString,
				extremeWingStatsRfdSmartRfRadioNeighborsRadioIdx
					Unsigned32,
				extremeWingStatsRfdSmartRfRadioNeighborsType
					DisplayString
			 }

		-- 1.3.6.1.4.1.1916.2.131.50.1.4.3.5.3.1.1
		extremeWingStatsRfdSmartRfRadioNeighborsMac OBJECT-TYPE
			SYNTAX ExtremeWingIdentifier
			MAX-ACCESS read-only
			STATUS current
			DESCRIPTION
				"Radio MAC address
				
				XPath: /extremeWing-stats/rf_domain[name=key1]/smart-rf/radio_neighbors[mac=key2]/mac"
			::= { extremeWingStatsRfdSmartRfRadioNeighborsEntry 1 }

		
		-- 1.3.6.1.4.1.1916.2.131.50.1.4.3.5.3.1.3
		extremeWingStatsRfdSmartRfRadioNeighborsApMac OBJECT-TYPE
			SYNTAX DisplayString
			MAX-ACCESS read-only
			STATUS current
			DESCRIPTION
				"Access point MAC address in which this radio is present
				
				XPath: /extremeWing-stats/rf_domain[name=key1]/smart-rf/radio_neighbors[mac=key2]/ap_mac"
			::= { extremeWingStatsRfdSmartRfRadioNeighborsEntry 3 }

		
		-- 1.3.6.1.4.1.1916.2.131.50.1.4.3.5.3.1.4
		extremeWingStatsRfdSmartRfRadioNeighborsHostname OBJECT-TYPE
			SYNTAX DisplayString (SIZE (64))
			MAX-ACCESS read-only
			STATUS current
			DESCRIPTION
				"Access point hostname in which this radio is present
				
				XPath: /extremeWing-stats/rf_domain[name=key1]/smart-rf/radio_neighbors[mac=key2]/hostname"
			::= { extremeWingStatsRfdSmartRfRadioNeighborsEntry 4 }

		
		-- 1.3.6.1.4.1.1916.2.131.50.1.4.3.5.3.1.5
		extremeWingStatsRfdSmartRfRadioNeighborsChannel OBJECT-TYPE
			SYNTAX DisplayString
			MAX-ACCESS read-only
			STATUS current
			DESCRIPTION
				"Smart-rf assigned radio channel
				
				Values:
				1,
				1+,
				2,
				2+,
				3,
				3+,
				4,
				4+,
				5,
				5+,
				5-,
				6,
				6+,
				6-,
				7,
				7+,
				7-,
				8,
				8+,
				8-,
				9,
				9+,
				9-,
				10,
				10-,
				11,
				11-,
				12,
				12-,
				13,
				13-,
				14,
				36,
				36+,
				40,
				40-,
				44,
				44+,
				48,
				48-,
				52,
				52+,
				56,
				56-,
				60,
				60+,
				64,
				64-,
				100,
				100+,
				104,
				104-,
				108,
				108+,
				112,
				112-,
				116,
				116+,
				120,
				120-,
				124,
				124+,
				128,
				128-,
				132,
				132+,
				136,
				136-,
				140,
				149,
				149+,
				153,
				153-,
				157,
				157+,
				161,
				161-,
				165,
				34,
				38,
				42,
				46
				
				XPath: /extremeWing-stats/rf_domain[name=key1]/smart-rf/radio_neighbors[mac=key2]/channel"
			::= { extremeWingStatsRfdSmartRfRadioNeighborsEntry 5 }

		
		-- 1.3.6.1.4.1.1916.2.131.50.1.4.3.5.3.1.6
		extremeWingStatsRfdSmartRfRadioNeighborsRadioIdx OBJECT-TYPE
			SYNTAX Unsigned32
			MAX-ACCESS read-only
			STATUS current
			DESCRIPTION
				"Radio index of this radio in AP
				
				XPath: /extremeWing-stats/rf_domain[name=key1]/smart-rf/radio_neighbors[mac=key2]/radio_idx"
			::= { extremeWingStatsRfdSmartRfRadioNeighborsEntry 6 }

		
		-- 1.3.6.1.4.1.1916.2.131.50.1.4.3.5.3.1.7
		extremeWingStatsRfdSmartRfRadioNeighborsType OBJECT-TYPE
			SYNTAX DisplayString
			MAX-ACCESS read-only
			STATUS current
			DESCRIPTION
				"Radio type
				
				Values:
				11an,
				11bgn
				
				XPath: /extremeWing-stats/rf_domain[name=key1]/smart-rf/radio_neighbors[mac=key2]/type"
			::= { extremeWingStatsRfdSmartRfRadioNeighborsEntry 7 }

		
		-- 1.3.6.1.4.1.1916.2.131.50.1.4.3.5.4
		extremeWingStatsRfdSmartRfRadioNeighborsNeighborsTable OBJECT-TYPE
			SYNTAX SEQUENCE OF ExtremeWingStatsRfdSmartRfRadioNeighborsNeighborsEntry
			MAX-ACCESS not-accessible
			STATUS current
			DESCRIPTION
				"
				
				/extremeWing-stats/rf_domain/smart-rf/radio_neighbors/neighbors"
			::= { extremeWingStatsRfdSmartRf 4 }

		
		-- 1.3.6.1.4.1.1916.2.131.50.1.4.3.5.4.1
		extremeWingStatsRfdSmartRfRadioNeighborsNeighborsEntry OBJECT-TYPE
			SYNTAX ExtremeWingStatsRfdSmartRfRadioNeighborsNeighborsEntry
			MAX-ACCESS not-accessible
			STATUS current
			DESCRIPTION
				"An entry in the table."
			INDEX { extremeWingStatsRfdName, extremeWingStatsRfdSmartRfRadioNeighborsMac }
			::= { extremeWingStatsRfdSmartRfRadioNeighborsNeighborsTable 1 }

		
		ExtremeWingStatsRfdSmartRfRadioNeighborsNeighborsEntry ::=
			SEQUENCE { 
				extremeWingStatsRfdSmartRfRadioNeighborsNeighborsMac
					DisplayString,
				extremeWingStatsRfdSmartRfRadioNeighborsNeighborsApMac
					DisplayString,
				extremeWingStatsRfdSmartRfRadioNeighborsNeighborsChannel
					DisplayString,
				extremeWingStatsRfdSmartRfRadioNeighborsNeighborsPower
					Unsigned32,
				extremeWingStatsRfdSmartRfRadioNeighborsNeighborsAttenuation
					Unsigned32,
				extremeWingStatsRfdSmartRfRadioNeighborsNeighborsRadioIdx
					Unsigned32
			 }

		-- 1.3.6.1.4.1.1916.2.131.50.1.4.3.5.4.1.1
		extremeWingStatsRfdSmartRfRadioNeighborsNeighborsMac OBJECT-TYPE
			SYNTAX DisplayString
			MAX-ACCESS read-only
			STATUS current
			DESCRIPTION
				"Neighbor radio MAC address
				
				XPath: /extremeWing-stats/rf_domain[name=key1]/smart-rf/radio_neighbors[mac=key2]/neighbors/mac"
			::= { extremeWingStatsRfdSmartRfRadioNeighborsNeighborsEntry 1 }

		
		-- 1.3.6.1.4.1.1916.2.131.50.1.4.3.5.4.1.2
		extremeWingStatsRfdSmartRfRadioNeighborsNeighborsApMac OBJECT-TYPE
			SYNTAX DisplayString
			MAX-ACCESS read-only
			STATUS current
			DESCRIPTION
				"Access point MAC address in which this neighbor radio is present
				
				XPath: /extremeWing-stats/rf_domain[name=key1]/smart-rf/radio_neighbors[mac=key2]/neighbors/ap_mac"
			::= { extremeWingStatsRfdSmartRfRadioNeighborsNeighborsEntry 2 }

		
		-- 1.3.6.1.4.1.1916.2.131.50.1.4.3.5.4.1.3
		extremeWingStatsRfdSmartRfRadioNeighborsNeighborsChannel OBJECT-TYPE
			SYNTAX DisplayString
			MAX-ACCESS read-only
			STATUS current
			DESCRIPTION
				"Smart-rf assigned neighbor radio channel
				
				Values:
				1,
				1+,
				2,
				2+,
				3,
				3+,
				4,
				4+,
				5,
				5+,
				5-,
				6,
				6+,
				6-,
				7,
				7+,
				7-,
				8,
				8+,
				8-,
				9,
				9+,
				9-,
				10,
				10-,
				11,
				11-,
				12,
				12-,
				13,
				13-,
				14,
				36,
				36+,
				40,
				40-,
				44,
				44+,
				48,
				48-,
				52,
				52+,
				56,
				56-,
				60,
				60+,
				64,
				64-,
				100,
				100+,
				104,
				104-,
				108,
				108+,
				112,
				112-,
				116,
				116+,
				120,
				120-,
				124,
				124+,
				128,
				128-,
				132,
				132+,
				136,
				136-,
				140,
				149,
				149+,
				153,
				153-,
				157,
				157+,
				161,
				161-,
				165,
				34,
				38,
				42,
				46
				
				XPath: /extremeWing-stats/rf_domain[name=key1]/smart-rf/radio_neighbors[mac=key2]/neighbors/channel"
			::= { extremeWingStatsRfdSmartRfRadioNeighborsNeighborsEntry 3 }

		
		-- 1.3.6.1.4.1.1916.2.131.50.1.4.3.5.4.1.4
		extremeWingStatsRfdSmartRfRadioNeighborsNeighborsPower OBJECT-TYPE
			SYNTAX Unsigned32 (0..23)
			UNITS "dBm"
			MAX-ACCESS read-only
			STATUS current
			DESCRIPTION
				"Smart-rf assigned transmit power for this neighbor radio
				
				XPath: /extremeWing-stats/rf_domain[name=key1]/smart-rf/radio_neighbors[mac=key2]/neighbors/power"
			::= { extremeWingStatsRfdSmartRfRadioNeighborsNeighborsEntry 4 }

		
		-- 1.3.6.1.4.1.1916.2.131.50.1.4.3.5.4.1.5
		extremeWingStatsRfdSmartRfRadioNeighborsNeighborsAttenuation OBJECT-TYPE
			SYNTAX Unsigned32
			UNITS "dB"
			MAX-ACCESS read-only
			STATUS current
			DESCRIPTION
				"Attenuation of neighbor radio
				
				XPath: /extremeWing-stats/rf_domain[name=key1]/smart-rf/radio_neighbors[mac=key2]/neighbors/attenuation"
			::= { extremeWingStatsRfdSmartRfRadioNeighborsNeighborsEntry 5 }

		
		-- 1.3.6.1.4.1.1916.2.131.50.1.4.3.5.4.1.6
		extremeWingStatsRfdSmartRfRadioNeighborsNeighborsRadioIdx OBJECT-TYPE
			SYNTAX Unsigned32
			MAX-ACCESS read-only
			STATUS current
			DESCRIPTION
				"Radio index of this neighbor radio in AP
				
				XPath: /extremeWing-stats/rf_domain[name=key1]/smart-rf/radio_neighbors[mac=key2]/neighbors/radio_idx"
			::= { extremeWingStatsRfdSmartRfRadioNeighborsNeighborsEntry 6 }

		
		-- 1.3.6.1.4.1.1916.2.131.50.1.4.3.5.5
		extremeWingStatsRfdSmartRfRadioEnergyTable OBJECT-TYPE
			SYNTAX SEQUENCE OF ExtremeWingStatsRfdSmartRfRadioEnergyEntry
			MAX-ACCESS not-accessible
			STATUS current
			DESCRIPTION
				"
				
				/extremeWing-stats/rf_domain/smart-rf/radio_energy"
			::= { extremeWingStatsRfdSmartRf 5 }

		
		-- 1.3.6.1.4.1.1916.2.131.50.1.4.3.5.5.1
		extremeWingStatsRfdSmartRfRadioEnergyEntry OBJECT-TYPE
			SYNTAX ExtremeWingStatsRfdSmartRfRadioEnergyEntry
			MAX-ACCESS not-accessible
			STATUS current
			DESCRIPTION
				"An entry in the table."
			INDEX { extremeWingStatsRfdName, extremeWingStatsRfdSmartRfRadioEnergyMac }
			::= { extremeWingStatsRfdSmartRfRadioEnergyTable 1 }

		
		ExtremeWingStatsRfdSmartRfRadioEnergyEntry ::=
			SEQUENCE { 
				extremeWingStatsRfdSmartRfRadioEnergyMac
					ExtremeWingIdentifier,
				extremeWingStatsRfdSmartRfRadioEnergyApMac
					DisplayString,
				extremeWingStatsRfdSmartRfRadioEnergyHostname
					DisplayString,
				extremeWingStatsRfdSmartRfRadioEnergyChannel
					DisplayString,
				extremeWingStatsRfdSmartRfRadioEnergyRadioIdx
					Unsigned32,
				extremeWingStatsRfdSmartRfRadioEnergyType
					DisplayString
			 }

		-- 1.3.6.1.4.1.1916.2.131.50.1.4.3.5.5.1.1
		extremeWingStatsRfdSmartRfRadioEnergyMac OBJECT-TYPE
			SYNTAX ExtremeWingIdentifier
			MAX-ACCESS read-only
			STATUS current
			DESCRIPTION
				"Radio MAC address
				
				XPath: /extremeWing-stats/rf_domain[name=key1]/smart-rf/radio_energy[mac=key2]/mac"
			::= { extremeWingStatsRfdSmartRfRadioEnergyEntry 1 }

		
		-- 1.3.6.1.4.1.1916.2.131.50.1.4.3.5.5.1.3
		extremeWingStatsRfdSmartRfRadioEnergyApMac OBJECT-TYPE
			SYNTAX DisplayString
			MAX-ACCESS read-only
			STATUS current
			DESCRIPTION
				"Access point MAC address in which this radio is present
				
				XPath: /extremeWing-stats/rf_domain[name=key1]/smart-rf/radio_energy[mac=key2]/ap_mac"
			::= { extremeWingStatsRfdSmartRfRadioEnergyEntry 3 }

		
		-- 1.3.6.1.4.1.1916.2.131.50.1.4.3.5.5.1.4
		extremeWingStatsRfdSmartRfRadioEnergyHostname OBJECT-TYPE
			SYNTAX DisplayString
			MAX-ACCESS read-only
			STATUS current
			DESCRIPTION
				"Access point hostname in which this radio is present
				
				XPath: /extremeWing-stats/rf_domain[name=key1]/smart-rf/radio_energy[mac=key2]/hostname"
			::= { extremeWingStatsRfdSmartRfRadioEnergyEntry 4 }

		
		-- 1.3.6.1.4.1.1916.2.131.50.1.4.3.5.5.1.5
		extremeWingStatsRfdSmartRfRadioEnergyChannel OBJECT-TYPE
			SYNTAX DisplayString
			MAX-ACCESS read-only
			STATUS current
			DESCRIPTION
				"Smart-rf assigned radio channel
				
				Values:
				46
				
				XPath: /extremeWing-stats/rf_domain[name=key1]/smart-rf/radio_energy[mac=key2]/channel"
			::= { extremeWingStatsRfdSmartRfRadioEnergyEntry 5 }

		
		-- 1.3.6.1.4.1.1916.2.131.50.1.4.3.5.5.1.6
		extremeWingStatsRfdSmartRfRadioEnergyRadioIdx OBJECT-TYPE
			SYNTAX Unsigned32
			MAX-ACCESS read-only
			STATUS current
			DESCRIPTION
				"Radio index of this radio in AP
				
				XPath: /extremeWing-stats/rf_domain[name=key1]/smart-rf/radio_energy[mac=key2]/radio_idx"
			::= { extremeWingStatsRfdSmartRfRadioEnergyEntry 6 }

		
		-- 1.3.6.1.4.1.1916.2.131.50.1.4.3.5.5.1.7
		extremeWingStatsRfdSmartRfRadioEnergyType OBJECT-TYPE
			SYNTAX DisplayString
			MAX-ACCESS read-only
			STATUS current
			DESCRIPTION
				"Radio type
				
				Values:
				11bgn
				
				XPath: /extremeWing-stats/rf_domain[name=key1]/smart-rf/radio_energy[mac=key2]/type"
			::= { extremeWingStatsRfdSmartRfRadioEnergyEntry 7 }

		
		-- 1.3.6.1.4.1.1916.2.131.50.1.4.3.5.6
		extremeWingStatsRfdSmartRfRadioEnergyEnergyTable OBJECT-TYPE
			SYNTAX SEQUENCE OF ExtremeWingStatsRfdSmartRfRadioEnergyEnergyEntry
			MAX-ACCESS not-accessible
			STATUS current
			DESCRIPTION
				"
				
				/extremeWing-stats/rf_domain/smart-rf/radio_energy/energy"
			::= { extremeWingStatsRfdSmartRf 6 }

		
		-- 1.3.6.1.4.1.1916.2.131.50.1.4.3.5.6.1
		extremeWingStatsRfdSmartRfRadioEnergyEnergyEntry OBJECT-TYPE
			SYNTAX ExtremeWingStatsRfdSmartRfRadioEnergyEnergyEntry
			MAX-ACCESS not-accessible
			STATUS current
			DESCRIPTION
				"An entry in the table."
			INDEX { extremeWingStatsRfdName, extremeWingStatsRfdSmartRfRadioEnergyMac }
			::= { extremeWingStatsRfdSmartRfRadioEnergyEnergyTable 1 }

		
		ExtremeWingStatsRfdSmartRfRadioEnergyEnergyEntry ::=
			SEQUENCE { 
				extremeWingStatsRfdSmartRfRadioEnergyEnergyChannel
					DisplayString,
				extremeWingStatsRfdSmartRfRadioEnergyEnergyExternal
					Integer32,
				extremeWingStatsRfdSmartRfRadioEnergyEnergyNeighbor
					Integer32,
				extremeWingStatsRfdSmartRfRadioEnergyEnergyNoise
					Integer32,
				extremeWingStatsRfdSmartRfRadioEnergyEnergyTotal
					Integer32
			 }

		-- 1.3.6.1.4.1.1916.2.131.50.1.4.3.5.6.1.1
		extremeWingStatsRfdSmartRfRadioEnergyEnergyChannel OBJECT-TYPE
			SYNTAX DisplayString
			MAX-ACCESS read-only
			STATUS current
			DESCRIPTION
				"Channel for which energy readings have been taken
				
				Values:
				1,
				2,
				3,
				4,
				5,
				6,
				7,
				8,
				9,
				10,
				11,
				12,
				13,
				14,
				36,
				40,
				44,
				48,
				52,
				56,
				60,
				64,
				100,
				104,
				108,
				112,
				116,
				120,
				124,
				128,
				132,
				136,
				140,
				149,
				153,
				157,
				161,
				165,
				34,
				38,
				42,
				46
				
				XPath: /extremeWing-stats/rf_domain[name=key1]/smart-rf/radio_energy[mac=key2]/energy/channel"
			::= { extremeWingStatsRfdSmartRfRadioEnergyEnergyEntry 1 }

		
		-- 1.3.6.1.4.1.1916.2.131.50.1.4.3.5.6.1.2
		extremeWingStatsRfdSmartRfRadioEnergyEnergyExternal OBJECT-TYPE
			SYNTAX Integer32
			UNITS "dbm"
			MAX-ACCESS read-only
			STATUS current
			DESCRIPTION
				"Interference due to external wireless sources
				
				XPath: /extremeWing-stats/rf_domain[name=key1]/smart-rf/radio_energy[mac=key2]/energy/external"
			::= { extremeWingStatsRfdSmartRfRadioEnergyEnergyEntry 2 }

		
		-- 1.3.6.1.4.1.1916.2.131.50.1.4.3.5.6.1.3
		extremeWingStatsRfdSmartRfRadioEnergyEnergyNeighbor OBJECT-TYPE
			SYNTAX Integer32
			UNITS "dbm"
			MAX-ACCESS read-only
			STATUS current
			DESCRIPTION
				"Interference due to neighboring radios
				
				XPath: /extremeWing-stats/rf_domain[name=key1]/smart-rf/radio_energy[mac=key2]/energy/neighbor"
			::= { extremeWingStatsRfdSmartRfRadioEnergyEnergyEntry 3 }

		
		-- 1.3.6.1.4.1.1916.2.131.50.1.4.3.5.6.1.4
		extremeWingStatsRfdSmartRfRadioEnergyEnergyNoise OBJECT-TYPE
			SYNTAX Integer32
			UNITS "dbm"
			MAX-ACCESS read-only
			STATUS current
			DESCRIPTION
				"Interference due to non-wifi sources
				
				XPath: /extremeWing-stats/rf_domain[name=key1]/smart-rf/radio_energy[mac=key2]/energy/noise"
			::= { extremeWingStatsRfdSmartRfRadioEnergyEnergyEntry 4 }

		
		-- 1.3.6.1.4.1.1916.2.131.50.1.4.3.5.6.1.5
		extremeWingStatsRfdSmartRfRadioEnergyEnergyTotal OBJECT-TYPE
			SYNTAX Integer32
			UNITS "dbm"
			MAX-ACCESS read-only
			STATUS current
			DESCRIPTION
				"Total interference perceived by radio
				
				XPath: /extremeWing-stats/rf_domain[name=key1]/smart-rf/radio_energy[mac=key2]/energy/total"
			::= { extremeWingStatsRfdSmartRfRadioEnergyEnergyEntry 5 }

		
		-- 1.3.6.1.4.1.1916.2.131.50.1.4.3.5.7
		extremeWingStatsRfdSmartRfRadioNonSsmTable OBJECT-TYPE
			SYNTAX SEQUENCE OF ExtremeWingStatsRfdSmartRfRadioNonSsmEntry
			MAX-ACCESS not-accessible
			STATUS current
			DESCRIPTION
				"
				
				/extremeWing-stats/rf_domain/smart-rf/radio"
			::= { extremeWingStatsRfdSmartRf 7 }

		
		-- 1.3.6.1.4.1.1916.2.131.50.1.4.3.5.7.1
		extremeWingStatsRfdSmartRfRadioNonSsmEntry OBJECT-TYPE
			SYNTAX ExtremeWingStatsRfdSmartRfRadioNonSsmEntry
			MAX-ACCESS not-accessible
			STATUS current
			DESCRIPTION
				"An entry in the table."
			INDEX { extremeWingStatsRfdName, extremeWingStatsRfdSmartRfRadioNonSsmMac }
			::= { extremeWingStatsRfdSmartRfRadioNonSsmTable 1 }

		
		ExtremeWingStatsRfdSmartRfRadioNonSsmEntry ::=
			SEQUENCE { 
				extremeWingStatsRfdSmartRfRadioNonSsmMac
					ExtremeWingIdentifier,
				extremeWingStatsRfdSmartRfRadioNonSsmInfoApMac
					DisplayString,
				extremeWingStatsRfdSmartRfRadioNonSsmHostname
					DisplayString,
				extremeWingStatsRfdSmartRfRadioNonSsmChannel
					DisplayString,
				extremeWingStatsRfdSmartRfRadioNonSsmPower
					Unsigned32,
				extremeWingStatsRfdSmartRfRadioNonSsmRadioIdx
					Unsigned32,
				extremeWingStatsRfdSmartRfRadioNonSsmState
					DisplayString,
				extremeWingStatsRfdSmartRfRadioNonSsmInfoType
					DisplayString,
				extremeWingStatsRfdSmartRfRadioNonSsmActApMac
					DisplayString,
				extremeWingStatsRfdSmartRfRadioNonSsmActType
					DisplayString,
				extremeWingStatsRfdSmartRfRadioNonSsmPowerChanges
					Unsigned32,
				extremeWingStatsRfdSmartRfRadioNonSsmChannelChanges
					Unsigned32,
				extremeWingStatsRfdSmartRfRadioNonSsmCoverageChanges
					Unsigned32
			 }

		-- 1.3.6.1.4.1.1916.2.131.50.1.4.3.5.7.1.1
		extremeWingStatsRfdSmartRfRadioNonSsmMac OBJECT-TYPE
			SYNTAX ExtremeWingIdentifier
			MAX-ACCESS read-only
			STATUS current
			DESCRIPTION
				"Radio MAC address
				
				XPath: /extremeWing-stats/rf_domain[name=key1]/smart-rf/radio[mac=key2]/mac"
			::= { extremeWingStatsRfdSmartRfRadioNonSsmEntry 1 }

		
		-- 1.3.6.1.4.1.1916.2.131.50.1.4.3.5.7.1.3
		extremeWingStatsRfdSmartRfRadioNonSsmInfoApMac OBJECT-TYPE
			SYNTAX DisplayString
			MAX-ACCESS read-only
			STATUS current
			DESCRIPTION
				"Access point MAC address in which this radio is present
				
				XPath: /extremeWing-stats/rf_domain[name=key1]/smart-rf/radio[mac=key2]/info/ap_mac"
			::= { extremeWingStatsRfdSmartRfRadioNonSsmEntry 3 }

		
		-- 1.3.6.1.4.1.1916.2.131.50.1.4.3.5.7.1.4
		extremeWingStatsRfdSmartRfRadioNonSsmHostname OBJECT-TYPE
			SYNTAX DisplayString (SIZE (64))
			MAX-ACCESS read-only
			STATUS current
			DESCRIPTION
				"Access point hostname in which this radio is present
				
				XPath: /extremeWing-stats/rf_domain[name=key1]/smart-rf/radio[mac=key2]/info/hostname"
			::= { extremeWingStatsRfdSmartRfRadioNonSsmEntry 4 }

		
		-- 1.3.6.1.4.1.1916.2.131.50.1.4.3.5.7.1.5
		extremeWingStatsRfdSmartRfRadioNonSsmChannel OBJECT-TYPE
			SYNTAX DisplayString
			MAX-ACCESS read-only
			STATUS current
			DESCRIPTION
				"Smart-rf assigned radio channel
				
				Values:
				1,
				1+,
				2,
				2+,
				3,
				3+,
				4,
				4+,
				5,
				5+,
				5-,
				6,
				6+,
				6-,
				7,
				7+,
				7-,
				8,
				8+,
				8-,
				9,
				9+,
				9-,
				10,
				10-,
				11,
				11-,
				12,
				12-,
				13,
				13-,
				14,
				36,
				36+,
				40,
				40-,
				44,
				44+,
				48,
				48-,
				52,
				52+,
				56,
				56-,
				60,
				60+,
				64,
				64-,
				100,
				100+,
				104,
				104-,
				108,
				108+,
				112,
				112-,
				116,
				116+,
				120,
				120-,
				124,
				124+,
				128,
				128-,
				132,
				132+,
				136,
				136-,
				140,
				149,
				149+,
				153,
				153-,
				157,
				157+,
				161,
				161-,
				165,
				34,
				38,
				42,
				46
				
				XPath: /extremeWing-stats/rf_domain[name=key1]/smart-rf/radio[mac=key2]/info/channel"
			::= { extremeWingStatsRfdSmartRfRadioNonSsmEntry 5 }

		
		-- 1.3.6.1.4.1.1916.2.131.50.1.4.3.5.7.1.6
		extremeWingStatsRfdSmartRfRadioNonSsmPower OBJECT-TYPE
			SYNTAX Unsigned32 (0..23)
			UNITS "dBm"
			MAX-ACCESS read-only
			STATUS current
			DESCRIPTION
				"Smart-rf assigned transmit power for this radio
				
				XPath: /extremeWing-stats/rf_domain[name=key1]/smart-rf/radio[mac=key2]/info/power"
			::= { extremeWingStatsRfdSmartRfRadioNonSsmEntry 6 }

		
		-- 1.3.6.1.4.1.1916.2.131.50.1.4.3.5.7.1.7
		extremeWingStatsRfdSmartRfRadioNonSsmRadioIdx OBJECT-TYPE
			SYNTAX Unsigned32
			MAX-ACCESS read-only
			STATUS current
			DESCRIPTION
				"Radio index of this radio in AP
				
				XPath: /extremeWing-stats/rf_domain[name=key1]/smart-rf/radio[mac=key2]/info/radio_idx"
			::= { extremeWingStatsRfdSmartRfRadioNonSsmEntry 7 }

		
		-- 1.3.6.1.4.1.1916.2.131.50.1.4.3.5.7.1.8
		extremeWingStatsRfdSmartRfRadioNonSsmState OBJECT-TYPE
			SYNTAX DisplayString
			MAX-ACCESS read-only
			STATUS current
			DESCRIPTION
				"Current radio state
				
				Values:
				offline,
				normal,
				sensor
				
				XPath: /extremeWing-stats/rf_domain[name=key1]/smart-rf/radio[mac=key2]/info/state"
			::= { extremeWingStatsRfdSmartRfRadioNonSsmEntry 8 }

		
		-- 1.3.6.1.4.1.1916.2.131.50.1.4.3.5.7.1.9
		extremeWingStatsRfdSmartRfRadioNonSsmInfoType OBJECT-TYPE
			SYNTAX DisplayString
			MAX-ACCESS read-only
			STATUS current
			DESCRIPTION
				"Radio type
				
				Values:
				11an,
				11bgn
				
				XPath: /extremeWing-stats/rf_domain[name=key1]/smart-rf/radio[mac=key2]/info/type"
			::= { extremeWingStatsRfdSmartRfRadioNonSsmEntry 9 }

		
		-- 1.3.6.1.4.1.1916.2.131.50.1.4.3.5.7.1.10
		extremeWingStatsRfdSmartRfRadioNonSsmActApMac OBJECT-TYPE
			SYNTAX DisplayString
			MAX-ACCESS read-only
			STATUS current
			DESCRIPTION
				"Access point MAC address in which this radio is present
				
				XPath: /extremeWing-stats/rf_domain[name=key1]/smart-rf/radio[mac=key2]/activity/ap_mac"
			::= { extremeWingStatsRfdSmartRfRadioNonSsmEntry 10 }

		
		-- 1.3.6.1.4.1.1916.2.131.50.1.4.3.5.7.1.11
		extremeWingStatsRfdSmartRfRadioNonSsmActType OBJECT-TYPE
			SYNTAX DisplayString
			MAX-ACCESS read-only
			STATUS current
			DESCRIPTION
				"Radio type
				
				Values:
				11an,
				11bgn
				
				XPath: /extremeWing-stats/rf_domain[name=key1]/smart-rf/radio[mac=key2]/activity/type"
			::= { extremeWingStatsRfdSmartRfRadioNonSsmEntry 11 }

		
		-- 1.3.6.1.4.1.1916.2.131.50.1.4.3.5.7.1.12
		extremeWingStatsRfdSmartRfRadioNonSsmPowerChanges OBJECT-TYPE
			SYNTAX Unsigned32 (0..1024)
			MAX-ACCESS read-only
			STATUS current
			DESCRIPTION
				"Number of neighbor recovery power changes for this radio
				
				XPath: /extremeWing-stats/rf_domain[name=key1]/smart-rf/radio[mac=key2]/activity/power_changes"
			::= { extremeWingStatsRfdSmartRfRadioNonSsmEntry 12 }

		
		-- 1.3.6.1.4.1.1916.2.131.50.1.4.3.5.7.1.13
		extremeWingStatsRfdSmartRfRadioNonSsmChannelChanges OBJECT-TYPE
			SYNTAX Unsigned32 (0..1024)
			MAX-ACCESS read-only
			STATUS current
			DESCRIPTION
				"Number of channel changes for this radio
				
				XPath: /extremeWing-stats/rf_domain[name=key1]/smart-rf/radio[mac=key2]/activity/channel_changes"
			::= { extremeWingStatsRfdSmartRfRadioNonSsmEntry 13 }

		
		-- 1.3.6.1.4.1.1916.2.131.50.1.4.3.5.7.1.14
		extremeWingStatsRfdSmartRfRadioNonSsmCoverageChanges OBJECT-TYPE
			SYNTAX Unsigned32 (0..1024)
			MAX-ACCESS read-only
			STATUS current
			DESCRIPTION
				"Number of coverage hole recovery power changes for this radio
				
				XPath: /extremeWing-stats/rf_domain[name=key1]/smart-rf/radio[mac=key2]/activity/coverage_changes"
			::= { extremeWingStatsRfdSmartRfRadioNonSsmEntry 14 }

		
		-- 1.3.6.1.4.1.1916.2.131.50.1.4.3.5.8
		extremeWingStatsRfdSmartRfRadioNonSsmNeighborsTable OBJECT-TYPE
			SYNTAX SEQUENCE OF ExtremeWingStatsRfdSmartRfRadioNonSsmNeighborsEntry
			MAX-ACCESS not-accessible
			STATUS current
			DESCRIPTION
				"
				
				/extremeWing-stats/rf_domain/smart-rf/radio/neighbors"
			::= { extremeWingStatsRfdSmartRf 8 }

		
		-- 1.3.6.1.4.1.1916.2.131.50.1.4.3.5.8.1
		extremeWingStatsRfdSmartRfRadioNonSsmNeighborsEntry OBJECT-TYPE
			SYNTAX ExtremeWingStatsRfdSmartRfRadioNonSsmNeighborsEntry
			MAX-ACCESS not-accessible
			STATUS current
			DESCRIPTION
				"An entry in the table."
			INDEX { extremeWingStatsRfdName, extremeWingStatsRfdSmartRfRadioNonSsmMac }
			::= { extremeWingStatsRfdSmartRfRadioNonSsmNeighborsTable 1 }

		
		ExtremeWingStatsRfdSmartRfRadioNonSsmNeighborsEntry ::=
			SEQUENCE { 
				extremeWingStatsRfdSmartRfRadioNonSsmNeighborsMac
					DisplayString,
				extremeWingStatsRfdSmartRfRadioNonSsmNeighborsApMac
					DisplayString,
				extremeWingStatsRfdSmartRfRadioNonSsmNeighborsChannel
					DisplayString,
				extremeWingStatsRfdSmartRfRadioNonSsmNeighborsPower
					Unsigned32,
				extremeWingStatsRfdSmartRfRadioNonSsmNeighborsAttenuation
					Unsigned32,
				extremeWingStatsRfdSmartRfRadioNonSsmNeighborsRadioIdx
					Unsigned32
			 }

		-- 1.3.6.1.4.1.1916.2.131.50.1.4.3.5.8.1.1
		extremeWingStatsRfdSmartRfRadioNonSsmNeighborsMac OBJECT-TYPE
			SYNTAX DisplayString
			MAX-ACCESS read-only
			STATUS current
			DESCRIPTION
				"Radio MAC address
				
				XPath: /extremeWing-stats/rf_domain[name=key1]/smart-rf/radio[mac=key2]/neighbors/mac"
			::= { extremeWingStatsRfdSmartRfRadioNonSsmNeighborsEntry 1 }

		
		-- 1.3.6.1.4.1.1916.2.131.50.1.4.3.5.8.1.2
		extremeWingStatsRfdSmartRfRadioNonSsmNeighborsApMac OBJECT-TYPE
			SYNTAX DisplayString
			MAX-ACCESS read-only
			STATUS current
			DESCRIPTION
				"Access point MAC address in which this radio is present
				
				XPath: /extremeWing-stats/rf_domain[name=key1]/smart-rf/radio[mac=key2]/neighbors/ap_mac"
			::= { extremeWingStatsRfdSmartRfRadioNonSsmNeighborsEntry 2 }

		
		-- 1.3.6.1.4.1.1916.2.131.50.1.4.3.5.8.1.3
		extremeWingStatsRfdSmartRfRadioNonSsmNeighborsChannel OBJECT-TYPE
			SYNTAX DisplayString
			MAX-ACCESS read-only
			STATUS current
			DESCRIPTION
				"Smart-rf assigned radio channel
				
				Values:
				1,
				1+,
				2,
				2+,
				3,
				3+,
				4,
				4+,
				5,
				5+,
				5-,
				6,
				6+,
				6-,
				7,
				7+,
				7-,
				8,
				8+,
				8-,
				9,
				9+,
				9-,
				10,
				10-,
				11,
				11-,
				12,
				12-,
				13,
				13-,
				14,
				36,
				36+,
				40,
				40-,
				44,
				44+,
				48,
				48-,
				52,
				52+,
				56,
				56-,
				60,
				60+,
				64,
				64-,
				100,
				100+,
				104,
				104-,
				108,
				108+,
				112,
				112-,
				116,
				116+,
				120,
				120-,
				124,
				124+,
				128,
				128-,
				132,
				132+,
				136,
				136-,
				140,
				149,
				149+,
				153,
				153-,
				157,
				157+,
				161,
				161-,
				165,
				34,
				38,
				42,
				46
				
				XPath: /extremeWing-stats/rf_domain[name=key1]/smart-rf/radio[mac=key2]/neighbors/channel"
			::= { extremeWingStatsRfdSmartRfRadioNonSsmNeighborsEntry 3 }

		
		-- 1.3.6.1.4.1.1916.2.131.50.1.4.3.5.8.1.4
		extremeWingStatsRfdSmartRfRadioNonSsmNeighborsPower OBJECT-TYPE
			SYNTAX Unsigned32 (0..23)
			UNITS "dBm"
			MAX-ACCESS read-only
			STATUS current
			DESCRIPTION
				"Smart-rf assigned transmit power for this neighbor radio
				
				XPath: /extremeWing-stats/rf_domain[name=key1]/smart-rf/radio[mac=key2]/neighbors/power"
			::= { extremeWingStatsRfdSmartRfRadioNonSsmNeighborsEntry 4 }

		
		-- 1.3.6.1.4.1.1916.2.131.50.1.4.3.5.8.1.5
		extremeWingStatsRfdSmartRfRadioNonSsmNeighborsAttenuation OBJECT-TYPE
			SYNTAX Unsigned32
			UNITS "dB"
			MAX-ACCESS read-only
			STATUS current
			DESCRIPTION
				"Attenuation of neighbor radio
				
				XPath: /extremeWing-stats/rf_domain[name=key1]/smart-rf/radio[mac=key2]/neighbors/attenuation"
			::= { extremeWingStatsRfdSmartRfRadioNonSsmNeighborsEntry 5 }

		
		-- 1.3.6.1.4.1.1916.2.131.50.1.4.3.5.8.1.6
		extremeWingStatsRfdSmartRfRadioNonSsmNeighborsRadioIdx OBJECT-TYPE
			SYNTAX Unsigned32
			MAX-ACCESS read-only
			STATUS current
			DESCRIPTION
				"Radio index of this neighbor radio in AP
				
				XPath: /extremeWing-stats/rf_domain[name=key1]/smart-rf/radio[mac=key2]/neighbors/radio_idx"
			::= { extremeWingStatsRfdSmartRfRadioNonSsmNeighborsEntry 6 }

		
		-- 1.3.6.1.4.1.1916.2.131.50.1.4.3.5.9
		extremeWingStatsRfdSmartRfRadioNonSsmEnergyTable OBJECT-TYPE
			SYNTAX SEQUENCE OF ExtremeWingStatsRfdSmartRfRadioNonSsmEnergyEntry
			MAX-ACCESS not-accessible
			STATUS current
			DESCRIPTION
				"
				
				/extremeWing-stats/rf_domain/smart-rf/radio/energy"
			::= { extremeWingStatsRfdSmartRf 9 }

		
		-- 1.3.6.1.4.1.1916.2.131.50.1.4.3.5.9.1
		extremeWingStatsRfdSmartRfRadioNonSsmEnergyEntry OBJECT-TYPE
			SYNTAX ExtremeWingStatsRfdSmartRfRadioNonSsmEnergyEntry
			MAX-ACCESS not-accessible
			STATUS current
			DESCRIPTION
				"An entry in the table."
			INDEX { extremeWingStatsRfdName, extremeWingStatsRfdSmartRfRadioNonSsmMac }
			::= { extremeWingStatsRfdSmartRfRadioNonSsmEnergyTable 1 }

		
		ExtremeWingStatsRfdSmartRfRadioNonSsmEnergyEntry ::=
			SEQUENCE { 
				extremeWingStatsRfdSmartRfRadioNonSsmEnergyChannel
					DisplayString,
				extremeWingStatsRfdSmartRfRadioNonSsmEnergyExternal
					Integer32,
				extremeWingStatsRfdSmartRfRadioNonSsmEnergyNeighbor
					Integer32,
				extremeWingStatsRfdSmartRfRadioNonSsmEnergyNoise
					Integer32,
				extremeWingStatsRfdSmartRfRadioNonSsmEnergyTotal
					Integer32
			 }

		-- 1.3.6.1.4.1.1916.2.131.50.1.4.3.5.9.1.1
		extremeWingStatsRfdSmartRfRadioNonSsmEnergyChannel OBJECT-TYPE
			SYNTAX DisplayString
			MAX-ACCESS read-only
			STATUS current
			DESCRIPTION
				"Channel for which energy readings have been taken
				
				Values:
				1,
				2,
				3,
				4,
				5,
				6,
				7,
				8,
				9,
				10,
				11,
				12,
				13,
				14,
				36,
				40,
				44,
				48,
				52,
				56,
				60,
				64,
				100,
				104,
				108,
				112,
				116,
				120,
				124,
				128,
				132,
				136,
				140,
				149,
				153,
				157,
				161,
				165,
				34,
				38,
				42,
				46
				
				XPath: /extremeWing-stats/rf_domain[name=key1]/smart-rf/radio[mac=key2]/energy/channel"
			::= { extremeWingStatsRfdSmartRfRadioNonSsmEnergyEntry 1 }

		
		-- 1.3.6.1.4.1.1916.2.131.50.1.4.3.5.9.1.2
		extremeWingStatsRfdSmartRfRadioNonSsmEnergyExternal OBJECT-TYPE
			SYNTAX Integer32
			UNITS "dbm"
			MAX-ACCESS read-only
			STATUS current
			DESCRIPTION
				"Interference due to external wireless sources
				
				XPath: /extremeWing-stats/rf_domain[name=key1]/smart-rf/radio[mac=key2]/energy/external"
			::= { extremeWingStatsRfdSmartRfRadioNonSsmEnergyEntry 2 }

		
		-- 1.3.6.1.4.1.1916.2.131.50.1.4.3.5.9.1.3
		extremeWingStatsRfdSmartRfRadioNonSsmEnergyNeighbor OBJECT-TYPE
			SYNTAX Integer32
			UNITS "dbm"
			MAX-ACCESS read-only
			STATUS current
			DESCRIPTION
				"Interference due to neighboring radios
				
				XPath: /extremeWing-stats/rf_domain[name=key1]/smart-rf/radio[mac=key2]/energy/neighbor"
			::= { extremeWingStatsRfdSmartRfRadioNonSsmEnergyEntry 3 }

		
		-- 1.3.6.1.4.1.1916.2.131.50.1.4.3.5.9.1.4
		extremeWingStatsRfdSmartRfRadioNonSsmEnergyNoise OBJECT-TYPE
			SYNTAX Integer32
			UNITS "dbm"
			MAX-ACCESS read-only
			STATUS current
			DESCRIPTION
				"Interference due to non-wifi sources
				
				XPath: /extremeWing-stats/rf_domain[name=key1]/smart-rf/radio[mac=key2]/energy/noise"
			::= { extremeWingStatsRfdSmartRfRadioNonSsmEnergyEntry 4 }

		
		-- 1.3.6.1.4.1.1916.2.131.50.1.4.3.5.9.1.5
		extremeWingStatsRfdSmartRfRadioNonSsmEnergyTotal OBJECT-TYPE
			SYNTAX Integer32
			UNITS "dbm"
			MAX-ACCESS read-only
			STATUS current
			DESCRIPTION
				"Total interference perceived by radio
				
				XPath: /extremeWing-stats/rf_domain[name=key1]/smart-rf/radio[mac=key2]/energy/total"
			::= { extremeWingStatsRfdSmartRfRadioNonSsmEnergyEntry 5 }

		
		-- 1.3.6.1.4.1.1916.2.131.50.1.4.3.5.10
		extremeWingStatsRfdSmartRfApTable OBJECT-TYPE
			SYNTAX SEQUENCE OF ExtremeWingStatsRfdSmartRfApEntry
			MAX-ACCESS not-accessible
			STATUS current
			DESCRIPTION
				"
				
				/extremeWing-stats/rf_domain/smart-rf/ap"
			::= { extremeWingStatsRfdSmartRf 10 }

		
		-- 1.3.6.1.4.1.1916.2.131.50.1.4.3.5.10.1
		extremeWingStatsRfdSmartRfApEntry OBJECT-TYPE
			SYNTAX ExtremeWingStatsRfdSmartRfApEntry
			MAX-ACCESS not-accessible
			STATUS current
			DESCRIPTION
				"An entry in the table."
			INDEX { extremeWingStatsRfdName, extremeWingStatsRfdSmartRfApMac }
			::= { extremeWingStatsRfdSmartRfApTable 1 }

		
		ExtremeWingStatsRfdSmartRfApEntry ::=
			SEQUENCE { 
				extremeWingStatsRfdSmartRfApMac
					ExtremeWingIdentifier
			 }

		-- 1.3.6.1.4.1.1916.2.131.50.1.4.3.5.10.1.1
		extremeWingStatsRfdSmartRfApMac OBJECT-TYPE
			SYNTAX ExtremeWingIdentifier
			MAX-ACCESS read-only
			STATUS current
			DESCRIPTION
				"AP mac address
				
				XPath: /extremeWing-stats/rf_domain[name=key1]/ap[mac=key2]/mac"
			::= { extremeWingStatsRfdSmartRfApEntry 1 }

		
		-- 1.3.6.1.4.1.1916.2.131.50.1.4.3.5.11
		extremeWingStatsRfdSmartRfApNeighborsTable OBJECT-TYPE
			SYNTAX SEQUENCE OF ExtremeWingStatsRfdSmartRfApNeighborsEntry
			MAX-ACCESS not-accessible
			STATUS current
			DESCRIPTION
				"
				
				/extremeWing-stats/rf_domain/smart-rf/ap/neighbors"
			::= { extremeWingStatsRfdSmartRf 11 }

		
		-- 1.3.6.1.4.1.1916.2.131.50.1.4.3.5.11.1
		extremeWingStatsRfdSmartRfApNeighborsEntry OBJECT-TYPE
			SYNTAX ExtremeWingStatsRfdSmartRfApNeighborsEntry
			MAX-ACCESS not-accessible
			STATUS current
			DESCRIPTION
				"An entry in the table."
			INDEX { extremeWingStatsRfdName, extremeWingStatsRfdSmartRfApMac }
			::= { extremeWingStatsRfdSmartRfApNeighborsTable 1 }

		
		ExtremeWingStatsRfdSmartRfApNeighborsEntry ::=
			SEQUENCE { 
				extremeWingStatsRfdSmartRfApNeighborsMac
					DisplayString,
				extremeWingStatsRfdSmartRfApNeighborsApMac
					DisplayString,
				extremeWingStatsRfdSmartRfApNeighborsHostname
					DisplayString,
				extremeWingStatsRfdSmartRfApNeighborsChannel
					DisplayString,
				extremeWingStatsRfdSmartRfApNeighborsPower
					Unsigned32,
				extremeWingStatsRfdSmartRfApNeighborsAttenuation
					Unsigned32,
				extremeWingStatsRfdSmartRfApNeighborsInterference
					Integer32,
				extremeWingStatsRfdSmartRfApNeighborsRadioIdx
					Unsigned32,
				extremeWingStatsRfdSmartRfApNeighborsListenerIdx
					Unsigned32,
				extremeWingStatsRfdSmartRfApNeighborsListenerMac
					DisplayString,
				extremeWingStatsRfdSmartRfApNeighborsType
					DisplayString
			 }

		-- 1.3.6.1.4.1.1916.2.131.50.1.4.3.5.11.1.1
		extremeWingStatsRfdSmartRfApNeighborsMac OBJECT-TYPE
			SYNTAX DisplayString
			MAX-ACCESS read-only
			STATUS current
			DESCRIPTION
				"Neighbor radio MAC address
				
				XPath: /extremeWing-stats/rf_domain[name=key1]/ap[mac=key2]/neighbors/mac"
			::= { extremeWingStatsRfdSmartRfApNeighborsEntry 1 }

		
		-- 1.3.6.1.4.1.1916.2.131.50.1.4.3.5.11.1.2
		extremeWingStatsRfdSmartRfApNeighborsApMac OBJECT-TYPE
			SYNTAX DisplayString
			MAX-ACCESS read-only
			STATUS current
			DESCRIPTION
				"Access point MAC address in which this neighbor radio is present
				
				XPath: /extremeWing-stats/rf_domain[name=key1]/ap[mac=key2]/neighbors/ap_mac"
			::= { extremeWingStatsRfdSmartRfApNeighborsEntry 2 }

		
		-- 1.3.6.1.4.1.1916.2.131.50.1.4.3.5.11.1.3
		extremeWingStatsRfdSmartRfApNeighborsHostname OBJECT-TYPE
			SYNTAX DisplayString (SIZE (64))
			MAX-ACCESS read-only
			STATUS current
			DESCRIPTION
				"Access point hostname in which this neighbor radio is present
				
				XPath: /extremeWing-stats/rf_domain[name=key1]/ap[mac=key2]/neighbors/hostname"
			::= { extremeWingStatsRfdSmartRfApNeighborsEntry 3 }

		
		-- 1.3.6.1.4.1.1916.2.131.50.1.4.3.5.11.1.4
		extremeWingStatsRfdSmartRfApNeighborsChannel OBJECT-TYPE
			SYNTAX DisplayString
			MAX-ACCESS read-only
			STATUS current
			DESCRIPTION
				"Smart-rf assigned neighbor radio channel
				
				Values:
				1,
				1+,
				2,
				2+,
				3,
				3+,
				4,
				4+,
				5,
				5+,
				5-,
				6,
				6+,
				6-,
				7,
				7+,
				7-,
				8,
				8+,
				8-,
				9,
				9+,
				9-,
				10,
				10-,
				11,
				11-,
				12,
				12-,
				13,
				13-,
				14,
				36,
				36+,
				40,
				40-,
				44,
				44+,
				48,
				48-,
				52,
				52+,
				56,
				56-,
				60,
				60+,
				64,
				64-,
				100,
				100+,
				104,
				104-,
				108,
				108+,
				112,
				112-,
				116,
				116+,
				120,
				120-,
				124,
				124+,
				128,
				128-,
				132,
				132+,
				136,
				136-,
				140,
				149,
				149+,
				153,
				153-,
				157,
				157+,
				161,
				161-,
				165,
				34,
				38,
				42,
				46
				
				XPath: /extremeWing-stats/rf_domain[name=key1]/ap[mac=key2]/neighbors/channel"
			::= { extremeWingStatsRfdSmartRfApNeighborsEntry 4 }

		
		-- 1.3.6.1.4.1.1916.2.131.50.1.4.3.5.11.1.5
		extremeWingStatsRfdSmartRfApNeighborsPower OBJECT-TYPE
			SYNTAX Unsigned32 (0..23)
			UNITS "dBm"
			MAX-ACCESS read-only
			STATUS current
			DESCRIPTION
				"Smart-rf assigned transmit power for this neighbor radio
				
				XPath: /extremeWing-stats/rf_domain[name=key1]/ap[mac=key2]/neighbors/power"
			::= { extremeWingStatsRfdSmartRfApNeighborsEntry 5 }

		
		-- 1.3.6.1.4.1.1916.2.131.50.1.4.3.5.11.1.6
		extremeWingStatsRfdSmartRfApNeighborsAttenuation OBJECT-TYPE
			SYNTAX Unsigned32
			UNITS "dB"
			MAX-ACCESS read-only
			STATUS current
			DESCRIPTION
				"Attenuation of neighbor radio
				
				XPath: /extremeWing-stats/rf_domain[name=key1]/ap[mac=key2]/neighbors/attenuation"
			::= { extremeWingStatsRfdSmartRfApNeighborsEntry 6 }

		
		-- 1.3.6.1.4.1.1916.2.131.50.1.4.3.5.11.1.7
		extremeWingStatsRfdSmartRfApNeighborsInterference OBJECT-TYPE
			SYNTAX Integer32
			UNITS "dbm"
			MAX-ACCESS read-only
			STATUS current
			DESCRIPTION
				"Co Channel interference due to neighboring radios
				
				XPath: /extremeWing-stats/rf_domain[name=key1]/ap[mac=key2]/neighbors/interference"
			::= { extremeWingStatsRfdSmartRfApNeighborsEntry 7 }

		
		-- 1.3.6.1.4.1.1916.2.131.50.1.4.3.5.11.1.8
		extremeWingStatsRfdSmartRfApNeighborsRadioIdx OBJECT-TYPE
			SYNTAX Unsigned32
			MAX-ACCESS read-only
			STATUS current
			DESCRIPTION
				"Radio index of this neighbor radio in AP
				
				XPath: /extremeWing-stats/rf_domain[name=key1]/ap[mac=key2]/neighbors/radio_idx"
			::= { extremeWingStatsRfdSmartRfApNeighborsEntry 8 }

		
		-- 1.3.6.1.4.1.1916.2.131.50.1.4.3.5.11.1.9
		extremeWingStatsRfdSmartRfApNeighborsListenerIdx OBJECT-TYPE
			SYNTAX Unsigned32
			MAX-ACCESS read-only
			STATUS current
			DESCRIPTION
				"Radio index of the radio which hears this neighbor
				
				XPath: /extremeWing-stats/rf_domain[name=key1]/ap[mac=key2]/neighbors/listener_idx"
			::= { extremeWingStatsRfdSmartRfApNeighborsEntry 9 }

		
		-- 1.3.6.1.4.1.1916.2.131.50.1.4.3.5.11.1.10
		extremeWingStatsRfdSmartRfApNeighborsListenerMac OBJECT-TYPE
			SYNTAX DisplayString
			MAX-ACCESS read-only
			STATUS current
			DESCRIPTION
				"MAC address of the radio which hears this neighbor
				
				XPath: /extremeWing-stats/rf_domain[name=key1]/ap[mac=key2]/neighbors/listener_mac"
			::= { extremeWingStatsRfdSmartRfApNeighborsEntry 10 }

		
		-- 1.3.6.1.4.1.1916.2.131.50.1.4.3.5.11.1.11
		extremeWingStatsRfdSmartRfApNeighborsType OBJECT-TYPE
			SYNTAX DisplayString
			MAX-ACCESS read-only
			STATUS current
			DESCRIPTION
				"Radio type
				
				Values:
				11an,
				11bgn
				
				XPath: /extremeWing-stats/rf_domain[name=key1]/ap[mac=key2]/neighbors/type"
			::= { extremeWingStatsRfdSmartRfApNeighborsEntry 11 }

		
		-- 1.3.6.1.4.1.1916.2.131.50.1.4.3.5.12
		extremeWingStatsRfdSmartRfHighActRadiosTable OBJECT-TYPE
			SYNTAX SEQUENCE OF ExtremeWingStatsRfdSmartRfHighActRadiosEntry
			MAX-ACCESS not-accessible
			STATUS current
			DESCRIPTION
				"
				
				/extremeWing-stats/rf_domain/smart-rf/high_activity_radios"
			::= { extremeWingStatsRfdSmartRf 12 }

		
		-- 1.3.6.1.4.1.1916.2.131.50.1.4.3.5.12.1
		extremeWingStatsRfdSmartRfHighActRadiosEntry OBJECT-TYPE
			SYNTAX ExtremeWingStatsRfdSmartRfHighActRadiosEntry
			MAX-ACCESS not-accessible
			STATUS current
			DESCRIPTION
				"An entry in the table."
			INDEX { extremeWingStatsRfdName }
			::= { extremeWingStatsRfdSmartRfHighActRadiosTable 1 }

		
		ExtremeWingStatsRfdSmartRfHighActRadiosEntry ::=
			SEQUENCE { 
				extremeWingStatsRfdSmartRfHighActRadiosMac
					DisplayString,
				extremeWingStatsRfdSmartRfHighActRadiosApMac
					DisplayString,
				extremeWingStatsRfdSmartRfHighActRadiosHostname
					DisplayString,
				extremeWingStatsRfdSmartRfHighActRadiosType
					DisplayString,
				extremeWingStatsRfdSmartRfHighActRadiosPowerChanges
					Unsigned32,
				extremeWingStatsRfdSmartRfHighActRadiosChannelChanges
					Unsigned32,
				extremeWingStatsRfdSmartRfHighActRadiosCoverageChanges
					Unsigned32
			 }

		-- 1.3.6.1.4.1.1916.2.131.50.1.4.3.5.12.1.1
		extremeWingStatsRfdSmartRfHighActRadiosMac OBJECT-TYPE
			SYNTAX DisplayString
			MAX-ACCESS read-only
			STATUS current
			DESCRIPTION
				"Radio MAC address
				
				XPath: /extremeWing-stats/rf_domain[name=key1]/smart-rf/high_activity_radios/mac"
			::= { extremeWingStatsRfdSmartRfHighActRadiosEntry 1 }

		
		-- 1.3.6.1.4.1.1916.2.131.50.1.4.3.5.12.1.2
		extremeWingStatsRfdSmartRfHighActRadiosApMac OBJECT-TYPE
			SYNTAX DisplayString
			MAX-ACCESS read-only
			STATUS current
			DESCRIPTION
				"Access point MAC address in which this radio is present
				
				XPath: /extremeWing-stats/rf_domain[name=key1]/smart-rf/high_activity_radios/ap_mac"
			::= { extremeWingStatsRfdSmartRfHighActRadiosEntry 2 }

		
		-- 1.3.6.1.4.1.1916.2.131.50.1.4.3.5.12.1.3
		extremeWingStatsRfdSmartRfHighActRadiosHostname OBJECT-TYPE
			SYNTAX DisplayString (SIZE (64))
			MAX-ACCESS read-only
			STATUS current
			DESCRIPTION
				"Access point hostname in which this radio is present
				
				XPath: /extremeWing-stats/rf_domain[name=key1]/smart-rf/high_activity_radios/hostname"
			::= { extremeWingStatsRfdSmartRfHighActRadiosEntry 3 }

		
		-- 1.3.6.1.4.1.1916.2.131.50.1.4.3.5.12.1.4
		extremeWingStatsRfdSmartRfHighActRadiosType OBJECT-TYPE
			SYNTAX DisplayString
			MAX-ACCESS read-only
			STATUS current
			DESCRIPTION
				"Radio type
				
				Values:
				11an,
				11bgn
				
				XPath: /extremeWing-stats/rf_domain[name=key1]/smart-rf/high_activity_radios/type"
			::= { extremeWingStatsRfdSmartRfHighActRadiosEntry 4 }

		
		-- 1.3.6.1.4.1.1916.2.131.50.1.4.3.5.12.1.5
		extremeWingStatsRfdSmartRfHighActRadiosPowerChanges OBJECT-TYPE
			SYNTAX Unsigned32 (0..1024)
			MAX-ACCESS read-only
			STATUS current
			DESCRIPTION
				"Number of neighbor recovery power changes for this radio
				
				XPath: /extremeWing-stats/rf_domain[name=key1]/smart-rf/high_activity_radios/power_changes"
			::= { extremeWingStatsRfdSmartRfHighActRadiosEntry 5 }

		
		-- 1.3.6.1.4.1.1916.2.131.50.1.4.3.5.12.1.6
		extremeWingStatsRfdSmartRfHighActRadiosChannelChanges OBJECT-TYPE
			SYNTAX Unsigned32 (0..1024)
			MAX-ACCESS read-only
			STATUS current
			DESCRIPTION
				"Number of channel changes for this radio
				
				XPath: /extremeWing-stats/rf_domain[name=key1]/smart-rf/high_activity_radios/channel_changes"
			::= { extremeWingStatsRfdSmartRfHighActRadiosEntry 6 }

		
		-- 1.3.6.1.4.1.1916.2.131.50.1.4.3.5.12.1.7
		extremeWingStatsRfdSmartRfHighActRadiosCoverageChanges OBJECT-TYPE
			SYNTAX Unsigned32 (0..1024)
			MAX-ACCESS read-only
			STATUS current
			DESCRIPTION
				"Number of coverage hole recovery power changes for this radio
				
				XPath: /extremeWing-stats/rf_domain[name=key1]/smart-rf/high_activity_radios/coverage_changes"
			::= { extremeWingStatsRfdSmartRfHighActRadiosEntry 7 }

		
		-- 1.3.6.1.4.1.1916.2.131.50.1.4.3.5.13
		extremeWingStatsRfdSmartRfHistoryTable OBJECT-TYPE
			SYNTAX SEQUENCE OF ExtremeWingStatsRfdSmartRfHistoryEntry
			MAX-ACCESS not-accessible
			STATUS current
			DESCRIPTION
				"
				
				/extremeWing-stats/rf_domain/smart-rf/history"
			::= { extremeWingStatsRfdSmartRf 13 }

		
		-- 1.3.6.1.4.1.1916.2.131.50.1.4.3.5.13.1
		extremeWingStatsRfdSmartRfHistoryEntry OBJECT-TYPE
			SYNTAX ExtremeWingStatsRfdSmartRfHistoryEntry
			MAX-ACCESS not-accessible
			STATUS current
			DESCRIPTION
				"An entry in the table."
			INDEX { extremeWingStatsRfdName }
			::= { extremeWingStatsRfdSmartRfHistoryTable 1 }

		
		ExtremeWingStatsRfdSmartRfHistoryEntry ::=
			SEQUENCE { 
				extremeWingStatsRfdSmartRfHistoryTime
					Unsigned32,
				extremeWingStatsRfdSmartRfHistoryApMac
					DisplayString,
				extremeWingStatsRfdSmartRfHistoryHostname
					DisplayString,
				extremeWingStatsRfdSmartRfHistoryRadioMac
					DisplayString,
				extremeWingStatsRfdSmartRfHistoryRadioIdx
					Integer32,
				extremeWingStatsRfdSmartRfHistoryOldValue
					DisplayString,
				extremeWingStatsRfdSmartRfHistoryNewValue
					DisplayString
			 }

		-- 1.3.6.1.4.1.1916.2.131.50.1.4.3.5.13.1.1
		extremeWingStatsRfdSmartRfHistoryTime OBJECT-TYPE
			SYNTAX Unsigned32
			MAX-ACCESS read-only
			STATUS current
			DESCRIPTION
				"
				
				XPath: /extremeWing-stats/rf_domain[name=key1]/smart-rf/history/time"
			::= { extremeWingStatsRfdSmartRfHistoryEntry 1 }

		
		-- 1.3.6.1.4.1.1916.2.131.50.1.4.3.5.13.1.2
		extremeWingStatsRfdSmartRfHistoryApMac OBJECT-TYPE
			SYNTAX DisplayString
			MAX-ACCESS read-only
			STATUS current
			DESCRIPTION
				"Access point MAC address
				
				XPath: /extremeWing-stats/rf_domain[name=key1]/smart-rf/history/ap_mac"
			::= { extremeWingStatsRfdSmartRfHistoryEntry 2 }

		
		-- 1.3.6.1.4.1.1916.2.131.50.1.4.3.5.13.1.3
		extremeWingStatsRfdSmartRfHistoryHostname OBJECT-TYPE
			SYNTAX DisplayString (SIZE (64))
			MAX-ACCESS read-only
			STATUS current
			DESCRIPTION
				"Access point hostname
				
				XPath: /extremeWing-stats/rf_domain[name=key1]/smart-rf/history/hostname"
			::= { extremeWingStatsRfdSmartRfHistoryEntry 3 }

		
		-- 1.3.6.1.4.1.1916.2.131.50.1.4.3.5.13.1.4
		extremeWingStatsRfdSmartRfHistoryRadioMac OBJECT-TYPE
			SYNTAX DisplayString
			MAX-ACCESS read-only
			STATUS current
			DESCRIPTION
				"Radio MAC address
				
				XPath: /extremeWing-stats/rf_domain[name=key1]/smart-rf/history/radio_mac"
			::= { extremeWingStatsRfdSmartRfHistoryEntry 4 }

		
		-- 1.3.6.1.4.1.1916.2.131.50.1.4.3.5.13.1.5
		extremeWingStatsRfdSmartRfHistoryRadioIdx OBJECT-TYPE
			SYNTAX Integer32
			MAX-ACCESS read-only
			STATUS current
			DESCRIPTION
				"Radio index
				
				XPath: /extremeWing-stats/rf_domain[name=key1]/smart-rf/history/radio_idx"
			::= { extremeWingStatsRfdSmartRfHistoryEntry 5 }

		
		-- 1.3.6.1.4.1.1916.2.131.50.1.4.3.5.13.1.6
		extremeWingStatsRfdSmartRfHistoryOldValue OBJECT-TYPE
			SYNTAX DisplayString (SIZE (32))
			MAX-ACCESS read-only
			STATUS current
			DESCRIPTION
				"Old value
				
				XPath: /extremeWing-stats/rf_domain[name=key1]/smart-rf/history/old_value"
			::= { extremeWingStatsRfdSmartRfHistoryEntry 6 }

		
		-- 1.3.6.1.4.1.1916.2.131.50.1.4.3.5.13.1.7
		extremeWingStatsRfdSmartRfHistoryNewValue OBJECT-TYPE
			SYNTAX DisplayString (SIZE (32))
			MAX-ACCESS read-only
			STATUS current
			DESCRIPTION
				"Old value
				
				XPath: /extremeWing-stats/rf_domain[name=key1]/smart-rf/history/new_value"
			::= { extremeWingStatsRfdSmartRfHistoryEntry 7 }

		
		-- 1.3.6.1.4.1.1916.2.131.50.1.4.3.5.14
		extremeWingStatsRfdSmartRfHistoryDaysTable OBJECT-TYPE
			SYNTAX SEQUENCE OF ExtremeWingStatsRfdSmartRfHistoryDaysEntry
			MAX-ACCESS not-accessible
			STATUS current
			DESCRIPTION
				"
				
				/extremeWing-stats/rf_domain/smart-rf/history_days"
			::= { extremeWingStatsRfdSmartRf 14 }

		
		-- 1.3.6.1.4.1.1916.2.131.50.1.4.3.5.14.1
		extremeWingStatsRfdSmartRfHistoryDaysEntry OBJECT-TYPE
			SYNTAX ExtremeWingStatsRfdSmartRfHistoryDaysEntry
			MAX-ACCESS not-accessible
			STATUS current
			DESCRIPTION
				"An entry in the table."
			INDEX { extremeWingStatsRfdName }
			::= { extremeWingStatsRfdSmartRfHistoryDaysTable 1 }

		
		ExtremeWingStatsRfdSmartRfHistoryDaysEntry ::=
			SEQUENCE { 
				extremeWingStatsRfdSmartRfHistoryDaysTime
					Unsigned32,
				extremeWingStatsRfdSmartRfHistoryDaysPowerChanges
					Unsigned32,
				extremeWingStatsRfdSmartRfHistoryDaysChannelChanges
					Unsigned32,
				extremeWingStatsRfdSmartRfHistoryDaysCoverageChanges
					Unsigned32
			 }

		-- 1.3.6.1.4.1.1916.2.131.50.1.4.3.5.14.1.1
		extremeWingStatsRfdSmartRfHistoryDaysTime OBJECT-TYPE
			SYNTAX Unsigned32
			MAX-ACCESS read-only
			STATUS current
			DESCRIPTION
				"
				
				XPath: /extremeWing-stats/rf_domain[name=key1]/smart-rf/history_days/time"
			::= { extremeWingStatsRfdSmartRfHistoryDaysEntry 1 }

		
		-- 1.3.6.1.4.1.1916.2.131.50.1.4.3.5.14.1.2
		extremeWingStatsRfdSmartRfHistoryDaysPowerChanges OBJECT-TYPE
			SYNTAX Unsigned32 (0..65535)
			MAX-ACCESS read-only
			STATUS current
			DESCRIPTION
				"Number of neighbor recovery power changes
				
				XPath: /extremeWing-stats/rf_domain[name=key1]/smart-rf/history_days/power_changes"
			::= { extremeWingStatsRfdSmartRfHistoryDaysEntry 2 }

		
		-- 1.3.6.1.4.1.1916.2.131.50.1.4.3.5.14.1.3
		extremeWingStatsRfdSmartRfHistoryDaysChannelChanges OBJECT-TYPE
			SYNTAX Unsigned32 (0..65535)
			MAX-ACCESS read-only
			STATUS current
			DESCRIPTION
				"Number of channel changes
				
				XPath: /extremeWing-stats/rf_domain[name=key1]/smart-rf/history_days/channel_changes"
			::= { extremeWingStatsRfdSmartRfHistoryDaysEntry 3 }

		
		-- 1.3.6.1.4.1.1916.2.131.50.1.4.3.5.14.1.4
		extremeWingStatsRfdSmartRfHistoryDaysCoverageChanges OBJECT-TYPE
			SYNTAX Unsigned32 (0..65535)
			MAX-ACCESS read-only
			STATUS current
			DESCRIPTION
				"Number of coverage hole recovery power changes
				
				XPath: /extremeWing-stats/rf_domain[name=key1]/smart-rf/history_days/coverage_changes"
			::= { extremeWingStatsRfdSmartRfHistoryDaysEntry 4 }

		
		-- 1.3.6.1.4.1.1916.2.131.50.1.4.3.5.15
		extremeWingStatsRfdSmartRfHistoryHoursTable OBJECT-TYPE
			SYNTAX SEQUENCE OF ExtremeWingStatsRfdSmartRfHistoryHoursEntry
			MAX-ACCESS not-accessible
			STATUS current
			DESCRIPTION
				"
				
				/extremeWing-stats/rf_domain/smart-rf/history_hours"
			::= { extremeWingStatsRfdSmartRf 15 }

		
		-- 1.3.6.1.4.1.1916.2.131.50.1.4.3.5.15.1
		extremeWingStatsRfdSmartRfHistoryHoursEntry OBJECT-TYPE
			SYNTAX ExtremeWingStatsRfdSmartRfHistoryHoursEntry
			MAX-ACCESS not-accessible
			STATUS current
			DESCRIPTION
				"An entry in the table."
			INDEX { extremeWingStatsRfdName }
			::= { extremeWingStatsRfdSmartRfHistoryHoursTable 1 }

		
		ExtremeWingStatsRfdSmartRfHistoryHoursEntry ::=
			SEQUENCE { 
				extremeWingStatsRfdSmartRfHistoryHoursTime
					Unsigned32,
				extremeWingStatsRfdSmartRfHistoryHoursPowerChanges
					Unsigned32,
				extremeWingStatsRfdSmartRfHistoryHoursChannelChanges
					Unsigned32,
				extremeWingStatsRfdSmartRfHistoryHoursCoverageChanges
					Unsigned32
			 }

		-- 1.3.6.1.4.1.1916.2.131.50.1.4.3.5.15.1.1
		extremeWingStatsRfdSmartRfHistoryHoursTime OBJECT-TYPE
			SYNTAX Unsigned32
			MAX-ACCESS read-only
			STATUS current
			DESCRIPTION
				"
				
				XPath: /extremeWing-stats/rf_domain[name=key1]/smart-rf/history_hours/time"
			::= { extremeWingStatsRfdSmartRfHistoryHoursEntry 1 }

		
		-- 1.3.6.1.4.1.1916.2.131.50.1.4.3.5.15.1.2
		extremeWingStatsRfdSmartRfHistoryHoursPowerChanges OBJECT-TYPE
			SYNTAX Unsigned32 (0..65535)
			MAX-ACCESS read-only
			STATUS current
			DESCRIPTION
				"Number of neighbor recovery power changes
				
				XPath: /extremeWing-stats/rf_domain[name=key1]/smart-rf/history_hours/power_changes"
			::= { extremeWingStatsRfdSmartRfHistoryHoursEntry 2 }

		
		-- 1.3.6.1.4.1.1916.2.131.50.1.4.3.5.15.1.3
		extremeWingStatsRfdSmartRfHistoryHoursChannelChanges OBJECT-TYPE
			SYNTAX Unsigned32 (0..65535)
			MAX-ACCESS read-only
			STATUS current
			DESCRIPTION
				"Number of channel changes
				
				XPath: /extremeWing-stats/rf_domain[name=key1]/smart-rf/history_hours/channel_changes"
			::= { extremeWingStatsRfdSmartRfHistoryHoursEntry 3 }

		
		-- 1.3.6.1.4.1.1916.2.131.50.1.4.3.5.15.1.4
		extremeWingStatsRfdSmartRfHistoryHoursCoverageChanges OBJECT-TYPE
			SYNTAX Unsigned32 (0..65535)
			MAX-ACCESS read-only
			STATUS current
			DESCRIPTION
				"Number of coverage hole recovery power changes
				
				XPath: /extremeWing-stats/rf_domain[name=key1]/smart-rf/history_hours/coverage_changes"
			::= { extremeWingStatsRfdSmartRfHistoryHoursEntry 4 }

		
		-- 1.3.6.1.4.1.1916.2.131.50.1.4.3.5.16
		extremeWingStatsRfdSmartRfDashboardHistoryTable OBJECT-TYPE
			SYNTAX SEQUENCE OF ExtremeWingStatsRfdSmartRfDashboardHistoryEntry
			MAX-ACCESS not-accessible
			STATUS current
			DESCRIPTION
				"
				
				/extremeWing-stats/rf_domain/smart-rf/dashboard_history"
			::= { extremeWingStatsRfdSmartRf 16 }

		
		-- 1.3.6.1.4.1.1916.2.131.50.1.4.3.5.16.1
		extremeWingStatsRfdSmartRfDashboardHistoryEntry OBJECT-TYPE
			SYNTAX ExtremeWingStatsRfdSmartRfDashboardHistoryEntry
			MAX-ACCESS not-accessible
			STATUS current
			DESCRIPTION
				"An entry in the table."
			INDEX { extremeWingStatsRfdName }
			::= { extremeWingStatsRfdSmartRfDashboardHistoryTable 1 }

		
		ExtremeWingStatsRfdSmartRfDashboardHistoryEntry ::=
			SEQUENCE { 
				extremeWingStatsRfdSmartRfDashboardHistoryDetails
					DisplayString,
				extremeWingStatsRfdSmartRfDashboardHistoryPowerChanges
					Unsigned32,
				extremeWingStatsRfdSmartRfDashboardHistoryChannelChanges
					Unsigned32,
				extremeWingStatsRfdSmartRfDashboardHistoryCoverageChanges
					Unsigned32
			 }

		-- 1.3.6.1.4.1.1916.2.131.50.1.4.3.5.16.1.1
		extremeWingStatsRfdSmartRfDashboardHistoryDetails OBJECT-TYPE
			SYNTAX DisplayString
			MAX-ACCESS read-only
			STATUS current
			DESCRIPTION
				"
				
				Values:
				current_hour,
				last_hour,
				last_24_hours,
				last_7_days
				
				XPath: /extremeWing-stats/rf_domain[name=key1]/smart-rf/dashboard_history/details"
			::= { extremeWingStatsRfdSmartRfDashboardHistoryEntry 1 }

		
		-- 1.3.6.1.4.1.1916.2.131.50.1.4.3.5.16.1.2
		extremeWingStatsRfdSmartRfDashboardHistoryPowerChanges OBJECT-TYPE
			SYNTAX Unsigned32 (0..65535)
			MAX-ACCESS read-only
			STATUS current
			DESCRIPTION
				"Number of neighbor recovery power changes
				
				XPath: /extremeWing-stats/rf_domain[name=key1]/smart-rf/dashboard_history/power_changes"
			::= { extremeWingStatsRfdSmartRfDashboardHistoryEntry 2 }

		
		-- 1.3.6.1.4.1.1916.2.131.50.1.4.3.5.16.1.3
		extremeWingStatsRfdSmartRfDashboardHistoryChannelChanges OBJECT-TYPE
			SYNTAX Unsigned32 (0..65535)
			MAX-ACCESS read-only
			STATUS current
			DESCRIPTION
				"Number of channel changes
				
				XPath: /extremeWing-stats/rf_domain[name=key1]/smart-rf/dashboard_history/channel_changes"
			::= { extremeWingStatsRfdSmartRfDashboardHistoryEntry 3 }

		
		-- 1.3.6.1.4.1.1916.2.131.50.1.4.3.5.16.1.4
		extremeWingStatsRfdSmartRfDashboardHistoryCoverageChanges OBJECT-TYPE
			SYNTAX Unsigned32 (0..65535)
			MAX-ACCESS read-only
			STATUS current
			DESCRIPTION
				"Number of coverage hole recovery power changes
				
				XPath: /extremeWing-stats/rf_domain[name=key1]/smart-rf/dashboard_history/coverage_changes"
			::= { extremeWingStatsRfdSmartRfDashboardHistoryEntry 4 }

		
		-- 1.3.6.1.4.1.1916.2.131.50.1.4.3.5.17
		extremeWingStatsRfdSmartRfCalibrateResultTable OBJECT-TYPE
			SYNTAX SEQUENCE OF ExtremeWingStatsRfdSmartRfCalibrateResultEntry
			MAX-ACCESS not-accessible
			STATUS current
			DESCRIPTION
				"
				
				/extremeWing-stats/rf_domain/smart-rf/calibration_result"
			::= { extremeWingStatsRfdSmartRf 17 }

		
		-- 1.3.6.1.4.1.1916.2.131.50.1.4.3.5.17.1
		extremeWingStatsRfdSmartRfCalibrateResultEntry OBJECT-TYPE
			SYNTAX ExtremeWingStatsRfdSmartRfCalibrateResultEntry
			MAX-ACCESS not-accessible
			STATUS current
			DESCRIPTION
				"An entry in the table."
			INDEX { extremeWingStatsRfdName, extremeWingStatsRfdSmartRfCalibrateResultMac }
			::= { extremeWingStatsRfdSmartRfCalibrateResultTable 1 }

		
		ExtremeWingStatsRfdSmartRfCalibrateResultEntry ::=
			SEQUENCE { 
				extremeWingStatsRfdSmartRfCalibrateResultMac
					ExtremeWingIdentifier,
				extremeWingStatsRfdSmartRfCalibrateResultResultMac
					DisplayString,
				extremeWingStatsRfdSmartRfCalibrateResultApMac
					DisplayString,
				extremeWingStatsRfdSmartRfCalibrateResultChannel
					DisplayString,
				extremeWingStatsRfdSmartRfCalibrateResultOldChannel
					DisplayString,
				extremeWingStatsRfdSmartRfCalibrateResultPower
					Unsigned32,
				extremeWingStatsRfdSmartRfCalibrateResultOldPower
					Unsigned32,
				extremeWingStatsRfdSmartRfCalibrateResultRadioIdx
					Unsigned32,
				extremeWingStatsRfdSmartRfCalibrateResultState
					DisplayString,
				extremeWingStatsRfdSmartRfCalibrateResultType
					DisplayString,
				extremeWingStatsRfdSmartRfCalibrateResultSmartSensor
					TruthValue
			 }

		-- 1.3.6.1.4.1.1916.2.131.50.1.4.3.5.17.1.1
		extremeWingStatsRfdSmartRfCalibrateResultMac OBJECT-TYPE
			SYNTAX ExtremeWingIdentifier
			MAX-ACCESS read-only
			STATUS current
			DESCRIPTION
				"Radio mac address
				
				XPath: /extremeWing-stats/rf_domain[name=key1]/smart-rf/calibration_result[mac=key2]/mac"
			::= { extremeWingStatsRfdSmartRfCalibrateResultEntry 1 }

		
		-- 1.3.6.1.4.1.1916.2.131.50.1.4.3.5.17.1.3
		extremeWingStatsRfdSmartRfCalibrateResultResultMac OBJECT-TYPE
			SYNTAX DisplayString
			MAX-ACCESS read-only
			STATUS current
			DESCRIPTION
				"Radio MAC address
				
				XPath: /extremeWing-stats/rf_domain[name=key1]/smart-rf/calibration_result[mac=key2]/result/mac"
			::= { extremeWingStatsRfdSmartRfCalibrateResultEntry 3 }

		
		-- 1.3.6.1.4.1.1916.2.131.50.1.4.3.5.17.1.4
		extremeWingStatsRfdSmartRfCalibrateResultApMac OBJECT-TYPE
			SYNTAX DisplayString
			MAX-ACCESS read-only
			STATUS current
			DESCRIPTION
				"Access point MAC address in which this radio is present
				
				XPath: /extremeWing-stats/rf_domain[name=key1]/smart-rf/calibration_result[mac=key2]/result/ap_mac"
			::= { extremeWingStatsRfdSmartRfCalibrateResultEntry 4 }

		
		-- 1.3.6.1.4.1.1916.2.131.50.1.4.3.5.17.1.5
		extremeWingStatsRfdSmartRfCalibrateResultChannel OBJECT-TYPE
			SYNTAX DisplayString
			MAX-ACCESS read-only
			STATUS current
			DESCRIPTION
				"Smart-rf assigned radio channel
				
				Values:
				1,
				1+,
				2,
				2+,
				3,
				3+,
				4,
				4+,
				5,
				5+,
				5-,
				6,
				6+,
				6-,
				7,
				7+,
				7-,
				8,
				8+,
				8-,
				9,
				9+,
				9-,
				10,
				10-,
				11,
				11-,
				12,
				12-,
				13,
				13-,
				14,
				36,
				36+,
				40,
				40-,
				44,
				44+,
				48,
				48-,
				52,
				52+,
				56,
				56-,
				60,
				60+,
				64,
				64-,
				100,
				100+,
				104,
				104-,
				108,
				108+,
				112,
				112-,
				116,
				116+,
				120,
				120-,
				124,
				124+,
				128,
				128-,
				132,
				132+,
				136,
				136-,
				140,
				149,
				149+,
				153,
				153-,
				157,
				157+,
				161,
				161-,
				165,
				34,
				38,
				42,
				46
				
				XPath: /extremeWing-stats/rf_domain[name=key1]/smart-rf/calibration_result[mac=key2]/result/channel"
			::= { extremeWingStatsRfdSmartRfCalibrateResultEntry 5 }

		
		-- 1.3.6.1.4.1.1916.2.131.50.1.4.3.5.17.1.6
		extremeWingStatsRfdSmartRfCalibrateResultOldChannel OBJECT-TYPE
			SYNTAX DisplayString
			MAX-ACCESS read-only
			STATUS current
			DESCRIPTION
				"Original radio channel
				
				Values:
				1,
				1+,
				2,
				2+,
				3,
				3+,
				4,
				4+,
				5,
				5+,
				5-,
				6,
				6+,
				6-,
				7,
				7+,
				7-,
				8,
				8+,
				8-,
				9,
				9+,
				9-,
				10,
				10-,
				11,
				11-,
				12,
				12-,
				13,
				13-,
				14,
				36,
				36+,
				40,
				40-,
				44,
				44+,
				48,
				48-,
				52,
				52+,
				56,
				56-,
				60,
				60+,
				64,
				64-,
				100,
				100+,
				104,
				104-,
				108,
				108+,
				112,
				112-,
				116,
				116+,
				120,
				120-,
				124,
				124+,
				128,
				128-,
				132,
				132+,
				136,
				136-,
				140,
				149,
				149+,
				153,
				153-,
				157,
				157+,
				161,
				161-,
				165,
				34,
				38,
				42,
				46
				
				XPath: /extremeWing-stats/rf_domain[name=key1]/smart-rf/calibration_result[mac=key2]/result/old_channel"
			::= { extremeWingStatsRfdSmartRfCalibrateResultEntry 6 }

		
		-- 1.3.6.1.4.1.1916.2.131.50.1.4.3.5.17.1.7
		extremeWingStatsRfdSmartRfCalibrateResultPower OBJECT-TYPE
			SYNTAX Unsigned32 (0..23)
			UNITS "dBm"
			MAX-ACCESS read-only
			STATUS current
			DESCRIPTION
				"Smart-rf assigned transmit power for this radio
				
				XPath: /extremeWing-stats/rf_domain[name=key1]/smart-rf/calibration_result[mac=key2]/result/power"
			::= { extremeWingStatsRfdSmartRfCalibrateResultEntry 7 }

		
		-- 1.3.6.1.4.1.1916.2.131.50.1.4.3.5.17.1.8
		extremeWingStatsRfdSmartRfCalibrateResultOldPower OBJECT-TYPE
			SYNTAX Unsigned32 (0..23)
			UNITS "dBm"
			MAX-ACCESS read-only
			STATUS current
			DESCRIPTION
				"Original transmit power for this radio
				
				XPath: /extremeWing-stats/rf_domain[name=key1]/smart-rf/calibration_result[mac=key2]/result/old_power"
			::= { extremeWingStatsRfdSmartRfCalibrateResultEntry 8 }

		
		-- 1.3.6.1.4.1.1916.2.131.50.1.4.3.5.17.1.9
		extremeWingStatsRfdSmartRfCalibrateResultRadioIdx OBJECT-TYPE
			SYNTAX Unsigned32
			MAX-ACCESS read-only
			STATUS current
			DESCRIPTION
				"Radio index of this radio in AP
				
				XPath: /extremeWing-stats/rf_domain[name=key1]/smart-rf/calibration_result[mac=key2]/result/radio_idx"
			::= { extremeWingStatsRfdSmartRfCalibrateResultEntry 9 }

		
		-- 1.3.6.1.4.1.1916.2.131.50.1.4.3.5.17.1.10
		extremeWingStatsRfdSmartRfCalibrateResultState OBJECT-TYPE
			SYNTAX DisplayString
			MAX-ACCESS read-only
			STATUS current
			DESCRIPTION
				"Current radio state
				
				Values:
				offline,
				normal,
				sensor
				
				XPath: /extremeWing-stats/rf_domain[name=key1]/smart-rf/calibration_result[mac=key2]/result/state"
			::= { extremeWingStatsRfdSmartRfCalibrateResultEntry 10 }

		
		-- 1.3.6.1.4.1.1916.2.131.50.1.4.3.5.17.1.11
		extremeWingStatsRfdSmartRfCalibrateResultType OBJECT-TYPE
			SYNTAX DisplayString
			MAX-ACCESS read-only
			STATUS current
			DESCRIPTION
				"Radio type
				
				Values:
				11an,
				11bgn
				
				XPath: /extremeWing-stats/rf_domain[name=key1]/smart-rf/calibration_result[mac=key2]/result/type"
			::= { extremeWingStatsRfdSmartRfCalibrateResultEntry 11 }

		
		-- 1.3.6.1.4.1.1916.2.131.50.1.4.3.5.17.1.12
		extremeWingStatsRfdSmartRfCalibrateResultSmartSensor OBJECT-TYPE
			SYNTAX TruthValue
			MAX-ACCESS read-only
			STATUS current
			DESCRIPTION
				"Has smart-rf assigned this radio as sensor
				
				XPath: /extremeWing-stats/rf_domain[name=key1]/smart-rf/calibration_result[mac=key2]/result/smart_sensor"
			::= { extremeWingStatsRfdSmartRfCalibrateResultEntry 12 }

		
		-- 1.3.6.1.4.1.1916.2.131.50.1.5
		extremeWingAction OBJECT IDENTIFIER ::= { extremeWingObjects 5 }

		
-- Copy from one file to another.
		-- 1.3.6.1.4.1.1916.2.131.50.1.5.1
		extremeWingActionFileCopy OBJECT IDENTIFIER ::= { extremeWingAction 1 }

		
-- Input objects for action.
		-- 1.3.6.1.4.1.1916.2.131.50.1.5.1.1
		extremeWingActionFileCopyIn OBJECT IDENTIFIER ::= { extremeWingActionFileCopy 1 }

		
		-- 1.3.6.1.4.1.1916.2.131.50.1.5.1.1.1
		extremeWingActionFileCopyInMac OBJECT-TYPE
			SYNTAX MacAddress
			MAX-ACCESS read-write
			STATUS current
			DESCRIPTION
				"Mac address of the device."
			::= { extremeWingActionFileCopyIn 1 }

		
		-- 1.3.6.1.4.1.1916.2.131.50.1.5.1.1.2
		extremeWingActionFileCopyInFrom OBJECT-TYPE
			SYNTAX DisplayString
			MAX-ACCESS read-write
			STATUS current
			DESCRIPTION
				"File or URL from which to copy.
				
				Files: flash:/path/file
				       nvram:startup-config
				       system:running-config
				
				URLs:  tftp://<hostname|IP>[:port]/path/file
				       ftp://<user>:<passwd>@<hostname|IP>[:port]/path/file
				       sftp://<user>:<passwd>@<hostname|IP>[:port]>/path/file
				       http://<hostname|IP>[:port]/path/file"
			::= { extremeWingActionFileCopyIn 2 }

		
		-- 1.3.6.1.4.1.1916.2.131.50.1.5.1.1.3
		extremeWingActionFileCopyInTo OBJECT-TYPE
			SYNTAX DisplayString
			MAX-ACCESS read-write
			STATUS current
			DESCRIPTION
				"File or URL to which to copy.
				
				Files: flash:/path/file
				       nvram:startup-config
				       system:running-config
				
				URLs:  tftp://<hostname|IP>[:port]/path/file
				       ftp://<user>:<passwd>@<hostname|IP>[:port]/path/file
				       sftp://<user>:<passwd>@<hostname|IP>[:port]>/path/file
				       http://<hostname|IP>[:port]/path/file"
			::= { extremeWingActionFileCopyIn 3 }

		
-- Output objects for action.
		-- 1.3.6.1.4.1.1916.2.131.50.1.5.1.2
		extremeWingActionFileCopyOut OBJECT IDENTIFIER ::= { extremeWingActionFileCopy 2 }

		
		-- 1.3.6.1.4.1.1916.2.131.50.1.5.1.2.1
		extremeWingActionFileCopyOutStatus OBJECT-TYPE
			SYNTAX TruthValue
			MAX-ACCESS read-only
			STATUS current
			DESCRIPTION
				"Whether the action is successful."
			::= { extremeWingActionFileCopyOut 1 }

		
		-- 1.3.6.1.4.1.1916.2.131.50.1.5.1.2.2
		extremeWingActionFileCopyOutMessage OBJECT-TYPE
			SYNTAX DisplayString
			MAX-ACCESS read-only
			STATUS current
			DESCRIPTION
				"Error message if the action is not successful."
			::= { extremeWingActionFileCopyOut 2 }

		
		-- 1.3.6.1.4.1.1916.2.131.50.1.5.1.3
		extremeWingActionFileCopyRun OBJECT-TYPE
			SYNTAX ExtremeWingDoActionNow
			MAX-ACCESS read-write
			STATUS current
			DESCRIPTION
				"Run action that copies from one file to another."
			::= { extremeWingActionFileCopy 3 }

		
-- File Configuration Checksum
		-- 1.3.6.1.4.1.1916.2.131.50.1.5.2
		extremeWingActionFileMD5sum OBJECT IDENTIFIER ::= { extremeWingAction 2 }

		
-- Input objects for action.
		-- 1.3.6.1.4.1.1916.2.131.50.1.5.2.1
		extremeWingActionFileMD5sumIn OBJECT IDENTIFIER ::= { extremeWingActionFileMD5sum 1 }

		
		-- 1.3.6.1.4.1.1916.2.131.50.1.5.2.1.1
		extremeWingActionFileMD5sumInMac OBJECT-TYPE
			SYNTAX MacAddress
			MAX-ACCESS read-write
			STATUS current
			DESCRIPTION
				"Mac address of the device."
			::= { extremeWingActionFileMD5sumIn 1 }

		
		-- 1.3.6.1.4.1.1916.2.131.50.1.5.2.1.2
		extremeWingActionFileMD5sumInPath OBJECT-TYPE
			SYNTAX DisplayString
			MAX-ACCESS read-write
			STATUS current
			DESCRIPTION
				"Local file path
				
				Files: flash:/path/file
				             nvram:startup-config
				             system:running-config"
			::= { extremeWingActionFileMD5sumIn 2 }

		
-- Output objects for action.
		-- 1.3.6.1.4.1.1916.2.131.50.1.5.2.2
		extremeWingActionFileMD5sumOut OBJECT IDENTIFIER ::= { extremeWingActionFileMD5sum 2 }

		
		-- 1.3.6.1.4.1.1916.2.131.50.1.5.2.2.1
		extremeWingActionFileMD5sumOutStatus OBJECT-TYPE
			SYNTAX TruthValue
			MAX-ACCESS read-only
			STATUS current
			DESCRIPTION
				"Whether the action is successful."
			::= { extremeWingActionFileMD5sumOut 1 }

		
		-- 1.3.6.1.4.1.1916.2.131.50.1.5.2.2.2
		extremeWingActionFileMD5sumOutMessage OBJECT-TYPE
			SYNTAX DisplayString
			MAX-ACCESS read-only
			STATUS current
			DESCRIPTION
				"MD5 sum on success or Error message if the action is not successful."
			::= { extremeWingActionFileMD5sumOut 2 }

		
		-- 1.3.6.1.4.1.1916.2.131.50.1.5.2.3
		extremeWingActionFileMD5sumRun OBJECT-TYPE
			SYNTAX ExtremeWingDoActionNow
			MAX-ACCESS read-write
			STATUS current
			DESCRIPTION
				"Run action that compute checksum of file"
			::= { extremeWingActionFileMD5sum 3 }

		
-- Disassociate Client 
		-- 1.3.6.1.4.1.1916.2.131.50.1.5.3
		extremeWingActionDisassociateClient OBJECT IDENTIFIER ::= { extremeWingAction 3 }

		
-- Input objects for action.
		-- 1.3.6.1.4.1.1916.2.131.50.1.5.3.1
		extremeWingActionDisassociateClientIn OBJECT IDENTIFIER ::= { extremeWingActionDisassociateClient 1 }

		
		-- 1.3.6.1.4.1.1916.2.131.50.1.5.3.1.1
		extremeWingActionDisassociateClientInRfDomainName OBJECT-TYPE
			SYNTAX DisplayString
			MAX-ACCESS read-write
			STATUS current
			DESCRIPTION
				"RF domain name.
				
				"
			::= { extremeWingActionDisassociateClientIn 1 }

		
-- Input objects Choice for action either Client Mac or Wlan Name.
		-- 1.3.6.1.4.1.1916.2.131.50.1.5.3.1.2
		extremeWingActionDisassociateClientInWlanNameORClientMac OBJECT IDENTIFIER ::= { extremeWingActionDisassociateClientIn 2 }

		
		-- 1.3.6.1.4.1.1916.2.131.50.1.5.3.1.2.1
		extremeWingActionDisassociateClientInMac OBJECT-TYPE
			SYNTAX MacAddress
			MAX-ACCESS read-write
			STATUS current
			DESCRIPTION
				"wireless client mac-addresss, or string * to disassociate all clients in this rf-domain."
			::= { extremeWingActionDisassociateClientInWlanNameORClientMac 1 }

		
		-- 1.3.6.1.4.1.1916.2.131.50.1.5.3.1.2.2
		extremeWingActionDisassociateClientInWlanName OBJECT-TYPE
			SYNTAX DisplayString
			MAX-ACCESS read-write
			STATUS current
			DESCRIPTION
				"All wireless clients on the wlan would be disassociated,
				client_mac, if present, would be ignored."
			::= { extremeWingActionDisassociateClientInWlanNameORClientMac 2 }

		
-- Output objects for action.
		-- 1.3.6.1.4.1.1916.2.131.50.1.5.3.2
		extremeWingActionDisassociateClientOut OBJECT IDENTIFIER ::= { extremeWingActionDisassociateClient 2 }

		
		-- 1.3.6.1.4.1.1916.2.131.50.1.5.3.2.1
		extremeWingActionDisassociateClientOutStatus OBJECT-TYPE
			SYNTAX TruthValue
			MAX-ACCESS read-only
			STATUS current
			DESCRIPTION
				"Whether the action is successful."
			::= { extremeWingActionDisassociateClientOut 1 }

		
		-- 1.3.6.1.4.1.1916.2.131.50.1.5.3.2.2
		extremeWingActionDisassociateClientOutMessage OBJECT-TYPE
			SYNTAX DisplayString
			MAX-ACCESS read-only
			STATUS current
			DESCRIPTION
				"Detailed error message when requested action failed."
			::= { extremeWingActionDisassociateClientOut 2 }

		
		-- 1.3.6.1.4.1.1916.2.131.50.1.5.3.3
		extremeWingActionDisassociateClientRun OBJECT-TYPE
			SYNTAX ExtremeWingDoActionNow
			MAX-ACCESS read-write
			STATUS current
			DESCRIPTION
				"Run action that disassociate client."
			::= { extremeWingActionDisassociateClient 3 }

		
-- Halt and perform a warm reboot.
		-- 1.3.6.1.4.1.1916.2.131.50.1.5.4
		extremeWingActionReload OBJECT IDENTIFIER ::= { extremeWingAction 4 }

		
-- Input objects for action.
		-- 1.3.6.1.4.1.1916.2.131.50.1.5.4.1
		extremeWingActionReloadIn OBJECT IDENTIFIER ::= { extremeWingActionReload 1 }

		
		-- 1.3.6.1.4.1.1916.2.131.50.1.5.4.1.1
		extremeWingActionReloadInMac OBJECT-TYPE
			SYNTAX MacAddress
			MAX-ACCESS read-write
			STATUS current
			DESCRIPTION
				"Mac address of the device."
			::= { extremeWingActionReloadIn 1 }

		
		-- 1.3.6.1.4.1.1916.2.131.50.1.5.4.1.2
		extremeWingActionReloadInForce OBJECT-TYPE
			SYNTAX TruthValue
			MAX-ACCESS read-write
			STATUS current
			DESCRIPTION
				"Force reboot ignoring conditions like upgrade in progress,
				unsaved changes etc.
				
				The default value of this object is false."
			::= { extremeWingActionReloadIn 2 }

		
		-- 1.3.6.1.4.1.1916.2.131.50.1.5.4.1.3
		extremeWingActionReloadInTimeout OBJECT-TYPE
			SYNTAX Unsigned32 (1..999)
			UNITS "minutes"
			MAX-ACCESS read-write
			STATUS current
			DESCRIPTION
				"Delay before reload (minutes).
				
				The default delay is 2 minutes."
			::= { extremeWingActionReloadIn 3 }

		
		-- 1.3.6.1.4.1.1916.2.131.50.1.5.4.1.4
		extremeWingActionReloadInReason OBJECT-TYPE
			SYNTAX DisplayString
			MAX-ACCESS read-write
			STATUS current
			DESCRIPTION
				"Reason for reload. This is printed on the serial console
				prior to reloading."
			::= { extremeWingActionReloadIn 4 }

		
-- Output objects for action.
		-- 1.3.6.1.4.1.1916.2.131.50.1.5.4.2
		extremeWingActionReloadOut OBJECT IDENTIFIER ::= { extremeWingActionReload 2 }

		
		-- 1.3.6.1.4.1.1916.2.131.50.1.5.4.2.1
		extremeWingActionReloadOutStatus OBJECT-TYPE
			SYNTAX TruthValue
			MAX-ACCESS read-only
			STATUS current
			DESCRIPTION
				"Whether the action is successful."
			::= { extremeWingActionReloadOut 1 }

		
		-- 1.3.6.1.4.1.1916.2.131.50.1.5.4.2.2
		extremeWingActionReloadOutMessage OBJECT-TYPE
			SYNTAX DisplayString
			MAX-ACCESS read-only
			STATUS current
			DESCRIPTION
				"Error message if the action is not successful."
			::= { extremeWingActionReloadOut 2 }

		
		-- 1.3.6.1.4.1.1916.2.131.50.1.5.4.3
		extremeWingActionReloadRun OBJECT-TYPE
			SYNTAX ExtremeWingDoActionNow
			MAX-ACCESS read-write
			STATUS current
			DESCRIPTION
				"Run action that halts and performs a warm reboot."
			::= { extremeWingActionReload 3 }

		
-- Re elect tunnel controller for this AP or this group of APs.
		-- 1.3.6.1.4.1.1916.2.131.50.1.5.5
		extremeWingActionReElectTunnelController OBJECT IDENTIFIER ::= { extremeWingAction 5 }

		
-- Input objects for action.
		-- 1.3.6.1.4.1.1916.2.131.50.1.5.5.1
		extremeWingActionReElectTunnelControllerIn OBJECT IDENTIFIER ::= { extremeWingActionReElectTunnelController 1 }

		
		-- 1.3.6.1.4.1.1916.2.131.50.1.5.5.1.1
		extremeWingActionReElectTunnelControllerInMac OBJECT-TYPE
			SYNTAX MacAddress
			MAX-ACCESS read-write
			STATUS current
			DESCRIPTION
				"AP whose mac matches will re-elect it's tunnel controller."
			::= { extremeWingActionReElectTunnelControllerIn 1 }

		
		-- 1.3.6.1.4.1.1916.2.131.50.1.5.5.1.2
		extremeWingActionReElectTunnelControllerInName OBJECT-TYPE
			SYNTAX DisplayString
			MAX-ACCESS read-write
			STATUS current
			DESCRIPTION
				"all APs whose tunnel controller name matches will re-elect their tunnel controller."
			::= { extremeWingActionReElectTunnelControllerIn 2 }

		
-- Output objects for action.
		-- 1.3.6.1.4.1.1916.2.131.50.1.5.5.2
		extremeWingActionReElectTunnelControllerOut OBJECT IDENTIFIER ::= { extremeWingActionReElectTunnelController 2 }

		
		-- 1.3.6.1.4.1.1916.2.131.50.1.5.5.2.1
		extremeWingActionReElectTunnelControllerOutStatus OBJECT-TYPE
			SYNTAX TruthValue
			MAX-ACCESS read-only
			STATUS current
			DESCRIPTION
				"Whether the action is successful."
			::= { extremeWingActionReElectTunnelControllerOut 1 }

		
		-- 1.3.6.1.4.1.1916.2.131.50.1.5.5.2.2
		extremeWingActionReElectTunnelControllerOutMessage OBJECT-TYPE
			SYNTAX DisplayString
			MAX-ACCESS read-only
			STATUS current
			DESCRIPTION
				"Error message if the action is not successful."
			::= { extremeWingActionReElectTunnelControllerOut 2 }

		
		-- 1.3.6.1.4.1.1916.2.131.50.1.5.5.3
		extremeWingActionReElectTunnelControllerRun OBJECT-TYPE
			SYNTAX ExtremeWingDoActionNow
			MAX-ACCESS read-write
			STATUS current
			DESCRIPTION
				"Run action for Re elect tunnel controller for this AP or this group of APs."
			::= { extremeWingActionReElectTunnelController 3 }

		
-- Action clears the current state of OSPF process and re-initializes it.
		-- 1.3.6.1.4.1.1916.2.131.50.1.5.6
		extremeWingActionClearIpOspf OBJECT IDENTIFIER ::= { extremeWingAction 6 }

		
-- Input objects for action.
		-- 1.3.6.1.4.1.1916.2.131.50.1.5.6.1
		extremeWingActionClearIpOspfIn OBJECT IDENTIFIER ::= { extremeWingActionClearIpOspf 1 }

		
		-- 1.3.6.1.4.1.1916.2.131.50.1.5.6.1.1
		extremeWingActionClearIpOspfInMac OBJECT-TYPE
			SYNTAX MacAddress
			MAX-ACCESS read-write
			STATUS current
			DESCRIPTION
				"Device whose mac matches will restart its OSPF process."
			::= { extremeWingActionClearIpOspfIn 1 }

		
-- Output objects for action.
		-- 1.3.6.1.4.1.1916.2.131.50.1.5.6.2
		extremeWingActionClearIpOspfOut OBJECT IDENTIFIER ::= { extremeWingActionClearIpOspf 2 }

		
		-- 1.3.6.1.4.1.1916.2.131.50.1.5.6.2.1
		extremeWingActionClearIpOspfOutStatus OBJECT-TYPE
			SYNTAX TruthValue
			MAX-ACCESS read-only
			STATUS current
			DESCRIPTION
				"Whether the action is successful."
			::= { extremeWingActionClearIpOspfOut 1 }

		
		-- 1.3.6.1.4.1.1916.2.131.50.1.5.6.2.2
		extremeWingActionClearIpOspfOutMessage OBJECT-TYPE
			SYNTAX DisplayString
			MAX-ACCESS read-only
			STATUS current
			DESCRIPTION
				"Error message if the action is not successful."
			::= { extremeWingActionClearIpOspfOut 2 }

		
		-- 1.3.6.1.4.1.1916.2.131.50.1.5.6.3
		extremeWingActionClearIpOspfRun OBJECT-TYPE
			SYNTAX ExtremeWingDoActionNow
			MAX-ACCESS read-write
			STATUS current
			DESCRIPTION
				"Run action to clear the current state of OSPF process and re-initializes it."
			::= { extremeWingActionClearIpOspf 3 }

		
-- vrrp action group
		-- 1.3.6.1.4.1.1916.2.131.50.1.5.7
		extremeWingActionVrrp OBJECT IDENTIFIER ::= { extremeWingAction 7 }

		
-- Action clears the vrrp router statistics and re-initializes it
		-- 1.3.6.1.4.1.1916.2.131.50.1.5.7.1
		extremeWingActionClearVrrpRouterStats OBJECT IDENTIFIER ::= { extremeWingActionVrrp 1 }

		
-- Input objects for action.
		-- 1.3.6.1.4.1.1916.2.131.50.1.5.7.1.1
		extremeWingActionClearVrrpRouterStatsIn OBJECT IDENTIFIER ::= { extremeWingActionClearVrrpRouterStats 1 }

		
		-- 1.3.6.1.4.1.1916.2.131.50.1.5.7.1.1.1
		extremeWingActionClearVrrpRouterStatsInMac OBJECT-TYPE
			SYNTAX MacAddress
			MAX-ACCESS read-write
			STATUS current
			DESCRIPTION
				"Mac address of the device."
			::= { extremeWingActionClearVrrpRouterStatsIn 1 }

		
-- Output objects for action.
		-- 1.3.6.1.4.1.1916.2.131.50.1.5.7.1.2
		extremeWingActionClearVrrpRouterStatsOut OBJECT IDENTIFIER ::= { extremeWingActionClearVrrpRouterStats 2 }

		
		-- 1.3.6.1.4.1.1916.2.131.50.1.5.7.1.2.1
		extremeWingActionClearVrrpRouterStatsOutStatus OBJECT-TYPE
			SYNTAX TruthValue
			MAX-ACCESS read-only
			STATUS current
			DESCRIPTION
				"Whether the action is successful."
			::= { extremeWingActionClearVrrpRouterStatsOut 1 }

		
		-- 1.3.6.1.4.1.1916.2.131.50.1.5.7.1.2.2
		extremeWingActionClearVrrpRouterStatsOutMessage OBJECT-TYPE
			SYNTAX DisplayString
			MAX-ACCESS read-only
			STATUS current
			DESCRIPTION
				"Error message if the action is not successful."
			::= { extremeWingActionClearVrrpRouterStatsOut 2 }

		
		-- 1.3.6.1.4.1.1916.2.131.50.1.5.7.1.3
		extremeWingActionClearVrrpRouterStatsRun OBJECT-TYPE
			SYNTAX ExtremeWingDoActionNow
			MAX-ACCESS read-write
			STATUS current
			DESCRIPTION
				"Run action which clears the vrrp router statistics and re-initializes it."
			::= { extremeWingActionClearVrrpRouterStats 3 }

		
-- Action clears the vrrp error statistics and re-initializes it.
		-- 1.3.6.1.4.1.1916.2.131.50.1.5.7.2
		extremeWingActionClearVrrpGlobalErrStats OBJECT IDENTIFIER ::= { extremeWingActionVrrp 2 }

		
-- Input objects for action.
		-- 1.3.6.1.4.1.1916.2.131.50.1.5.7.2.1
		extremeWingActionClearVrrpGlobalErrStatsIn OBJECT IDENTIFIER ::= { extremeWingActionClearVrrpGlobalErrStats 1 }

		
		-- 1.3.6.1.4.1.1916.2.131.50.1.5.7.2.1.1
		extremeWingActionClearVrrpGlobalErrStatsInMac OBJECT-TYPE
			SYNTAX MacAddress
			MAX-ACCESS read-write
			STATUS current
			DESCRIPTION
				"Mac address of the device."
			::= { extremeWingActionClearVrrpGlobalErrStatsIn 1 }

		
-- Output objects for action.
		-- 1.3.6.1.4.1.1916.2.131.50.1.5.7.2.2
		extremeWingActionClearVrrpGlobalErrStatsOut OBJECT IDENTIFIER ::= { extremeWingActionClearVrrpGlobalErrStats 2 }

		
		-- 1.3.6.1.4.1.1916.2.131.50.1.5.7.2.2.1
		extremeWingActionClearVrrpGlobalErrStatsOutStatus OBJECT-TYPE
			SYNTAX TruthValue
			MAX-ACCESS read-only
			STATUS current
			DESCRIPTION
				"Whether the action is successful."
			::= { extremeWingActionClearVrrpGlobalErrStatsOut 1 }

		
		-- 1.3.6.1.4.1.1916.2.131.50.1.5.7.2.2.2
		extremeWingActionClearVrrpGlobalErrStatsOutMessage OBJECT-TYPE
			SYNTAX DisplayString
			MAX-ACCESS read-only
			STATUS current
			DESCRIPTION
				"Error message if the action is not successful."
			::= { extremeWingActionClearVrrpGlobalErrStatsOut 2 }

		
		-- 1.3.6.1.4.1.1916.2.131.50.1.5.7.2.3
		extremeWingActionClearVrrpGlobalErrStatsRun OBJECT-TYPE
			SYNTAX ExtremeWingDoActionNow
			MAX-ACCESS read-write
			STATUS current
			DESCRIPTION
				"Run action which clears the vrrp error statistics and re-initializes it."
			::= { extremeWingActionClearVrrpGlobalErrStats 3 }

		
-- l2tpv3 action group.
		-- 1.3.6.1.4.1.1916.2.131.50.1.5.8
		extremeWingActionL2pv3 OBJECT IDENTIFIER ::= { extremeWingAction 8 }

		
-- Action resets all or specified l2tpv3 tunnel.
		-- 1.3.6.1.4.1.1916.2.131.50.1.5.8.1
		extremeWingActionClearL2tpv3Tunnel OBJECT IDENTIFIER ::= { extremeWingActionL2pv3 1 }

		
-- Input objects for action.
		-- 1.3.6.1.4.1.1916.2.131.50.1.5.8.1.1
		extremeWingActionClearL2tpv3TunnelIn OBJECT IDENTIFIER ::= { extremeWingActionClearL2tpv3Tunnel 1 }

		
		-- 1.3.6.1.4.1.1916.2.131.50.1.5.8.1.1.1
		extremeWingActionClearL2tpv3TunnelInMac OBJECT-TYPE
			SYNTAX MacAddress
			MAX-ACCESS read-write
			STATUS current
			DESCRIPTION
				"Device whose mac matches will have its specified L2TPv3 tunnel(s) reset."
			::= { extremeWingActionClearL2tpv3TunnelIn 1 }

		
-- Output objects for action.
		-- 1.3.6.1.4.1.1916.2.131.50.1.5.8.1.2
		extremeWingActionClearL2tpv3TunnelOut OBJECT IDENTIFIER ::= { extremeWingActionClearL2tpv3Tunnel 2 }

		
		-- 1.3.6.1.4.1.1916.2.131.50.1.5.8.1.2.1
		extremeWingActionClearL2tpv3TunnelOutStatus OBJECT-TYPE
			SYNTAX TruthValue
			MAX-ACCESS read-only
			STATUS current
			DESCRIPTION
				"Whether the action is successful."
			::= { extremeWingActionClearL2tpv3TunnelOut 1 }

		
		-- 1.3.6.1.4.1.1916.2.131.50.1.5.8.1.2.2
		extremeWingActionClearL2tpv3TunnelOutMessage OBJECT-TYPE
			SYNTAX DisplayString
			MAX-ACCESS read-only
			STATUS current
			DESCRIPTION
				"Error message if the action is not successful."
			::= { extremeWingActionClearL2tpv3TunnelOut 2 }

		
		-- 1.3.6.1.4.1.1916.2.131.50.1.5.8.1.3
		extremeWingActionClearL2tpv3TunnelRun OBJECT-TYPE
			SYNTAX ExtremeWingDoActionNow
			MAX-ACCESS read-write
			STATUS current
			DESCRIPTION
				"Run action which resets all or specified l2tpv3 tunnel."
			::= { extremeWingActionClearL2tpv3Tunnel 3 }

		
-- Action re-establishes a specified l2tpv3 tunnel
		-- 1.3.6.1.4.1.1916.2.131.50.1.5.8.2
		extremeWingActionConnectL2tpv3Tunnel OBJECT IDENTIFIER ::= { extremeWingActionL2pv3 2 }

		
-- Input objects for action.
		-- 1.3.6.1.4.1.1916.2.131.50.1.5.8.2.1
		extremeWingActionConnectL2tpv3TunnelIn OBJECT IDENTIFIER ::= { extremeWingActionConnectL2tpv3Tunnel 1 }

		
		-- 1.3.6.1.4.1.1916.2.131.50.1.5.8.2.1.1
		extremeWingActionConnectL2tpv3TunnelInMac OBJECT-TYPE
			SYNTAX MacAddress
			MAX-ACCESS read-write
			STATUS current
			DESCRIPTION
				"Device whose mac matches will have its specified L2TPv3 tunnel re-established."
			::= { extremeWingActionConnectL2tpv3TunnelIn 1 }

		
-- Output objects for action.
		-- 1.3.6.1.4.1.1916.2.131.50.1.5.8.2.2
		extremeWingActionConnectL2tpv3TunnelOut OBJECT IDENTIFIER ::= { extremeWingActionConnectL2tpv3Tunnel 2 }

		
		-- 1.3.6.1.4.1.1916.2.131.50.1.5.8.2.2.1
		extremeWingActionConnectL2tpv3TunnelOutStatus OBJECT-TYPE
			SYNTAX TruthValue
			MAX-ACCESS read-only
			STATUS current
			DESCRIPTION
				"Whether the action is successful."
			::= { extremeWingActionConnectL2tpv3TunnelOut 1 }

		
		-- 1.3.6.1.4.1.1916.2.131.50.1.5.8.2.2.2
		extremeWingActionConnectL2tpv3TunnelOutMessage OBJECT-TYPE
			SYNTAX DisplayString
			MAX-ACCESS read-only
			STATUS current
			DESCRIPTION
				"Error message if the action is not successful."
			::= { extremeWingActionConnectL2tpv3TunnelOut 2 }

		
		-- 1.3.6.1.4.1.1916.2.131.50.1.5.8.2.3
		extremeWingActionConnectL2tpv3TunnelRun OBJECT-TYPE
			SYNTAX ExtremeWingDoActionNow
			MAX-ACCESS read-write
			STATUS current
			DESCRIPTION
				"Run action which re-establishes a specified l2tpv3 tunnel."
			::= { extremeWingActionConnectL2tpv3Tunnel 3 }

		
                -- 1.3.6.1.4.1.1916.2.131.50.1.5.9
                extremeWingActionLocator OBJECT IDENTIFIER ::= { extremeWingAction 9 }


                -- 1.3.6.1.4.1.1916.2.131.50.1.5.9.1
                extremeWingActionLocatorOn OBJECT IDENTIFIER ::= { extremeWingActionLocator 1 }


-- Input objects for action.
                -- 1.3.6.1.4.1.1916.2.131.50.1.5.9.1.1
                extremeWingActionLocatorOnIn OBJECT IDENTIFIER ::= { extremeWingActionLocatorOn 1 }


                -- 1.3.6.1.4.1.1916.2.131.50.1.5.9.1.1.1
                extremeWingActionLocatorOnInDuration OBJECT-TYPE
                        SYNTAX Unsigned32
                        MAX-ACCESS read-write
                        STATUS current
                        DESCRIPTION
                                "Minutes to flash LEDs"
                        ::= { extremeWingActionLocatorOnIn 1 }


                -- 1.3.6.1.4.1.1916.2.131.50.1.5.9.1.1.2
                extremeWingActionLocatorOnInMac OBJECT-TYPE
                        SYNTAX MacAddress
                        MAX-ACCESS read-write
                        STATUS current
                        DESCRIPTION
                                "Mac address of the device."
                        ::= { extremeWingActionLocatorOnIn 2 }


-- Output objects for action.
                -- 1.3.6.1.4.1.1916.2.131.50.1.5.9.1.2
                extremeWingActionLocatorOnOut OBJECT IDENTIFIER ::= { extremeWingActionLocatorOn 2 }


                -- 1.3.6.1.4.1.1916.2.131.50.1.5.9.1.2.1
                extremeWingActionLocatorOnOutStatus OBJECT-TYPE
                        SYNTAX TruthValue
                        MAX-ACCESS read-only
                        STATUS current
                        DESCRIPTION
                                "Whether the action is successful."
                        ::= { extremeWingActionLocatorOnOut 1 }


                -- 1.3.6.1.4.1.1916.2.131.50.1.5.9.1.2.2
                extremeWingActionLocatorOnOutMessage OBJECT-TYPE
                        SYNTAX DisplayString
                        MAX-ACCESS read-only
                        STATUS current
                        DESCRIPTION
                                "Error message if the action is not successful."
                        ::= { extremeWingActionLocatorOnOut 2 }


                -- 1.3.6.1.4.1.1916.2.131.50.1.5.9.1.3
                extremeWingActionLocatorOnRun OBJECT-TYPE
                        SYNTAX ExtremeWingDoActionNow
                        MAX-ACCESS read-write
                        STATUS current
                        DESCRIPTION
                                "Run action"
                        ::= { extremeWingActionLocatorOn 3 }


                -- 1.3.6.1.4.1.1916.2.131.50.1.5.9.2
                extremeWingActionLocatorOff OBJECT IDENTIFIER ::= { extremeWingActionLocator 2 }


-- Input objects for action.
                -- 1.3.6.1.4.1.1916.2.131.50.1.5.9.2.1
                extremeWingActionLocatorOffIn OBJECT IDENTIFIER ::= { extremeWingActionLocatorOff 1 }


                -- 1.3.6.1.4.1.1916.2.131.50.1.5.9.2.1.1
                extremeWingActionLocatorOffInMac OBJECT-TYPE
                        SYNTAX MacAddress
                        MAX-ACCESS read-write
                        STATUS current
                        DESCRIPTION
                                "Mac address of the device."
                        ::= { extremeWingActionLocatorOffIn 1 }


-- Output objects for action.
                -- 1.3.6.1.4.1.1916.2.131.50.1.5.9.2.2
                extremeWingActionLocatorOffOut OBJECT IDENTIFIER ::= { extremeWingActionLocatorOff 2 }


                -- 1.3.6.1.4.1.1916.2.131.50.1.5.9.2.2.1
                extremeWingActionLocatorOffOutStatus OBJECT-TYPE
                        SYNTAX TruthValue
                        MAX-ACCESS read-only
                        STATUS current
                        DESCRIPTION
                                "Whether the action is successful."
                        ::= { extremeWingActionLocatorOffOut 1 }


                -- 1.3.6.1.4.1.1916.2.131.50.1.5.9.2.2.2
                extremeWingActionLocatorOffOutMessage OBJECT-TYPE
                        SYNTAX DisplayString
                        MAX-ACCESS read-only
                        STATUS current
                        DESCRIPTION
                                "Error message if the action is not successful."
                        ::= { extremeWingActionLocatorOffOut 2 }


                -- 1.3.6.1.4.1.1916.2.131.50.1.5.9.2.3
                extremeWingActionLocatorOffRun OBJECT-TYPE
                        SYNTAX ExtremeWingDoActionNow
                        MAX-ACCESS read-write
                        STATUS current
                        DESCRIPTION
                                "Run action"
                        ::= { extremeWingActionLocatorOff 3 }


-- Loads the AP firmware upgrade image files onto controller.
		-- 1.3.6.1.4.1.1916.2.131.50.1.5.10
		extremeWingActionLoadApUpgradeImageFile OBJECT IDENTIFIER ::= { extremeWingAction 10 }


-- Input objects for action.
		-- 1.3.6.1.4.1.1916.2.131.50.1.5.10.1
		extremeWingActionLoadApUpgradeImageFileIn OBJECT IDENTIFIER ::= { extremeWingActionLoadApUpgradeImageFile 1 }


		-- 1.3.6.1.4.1.1916.2.131.50.1.5.10.1.1
		extremeWingActionLoadApUpgradeImageFileInProductName OBJECT-TYPE
			SYNTAX DisplayString
			MAX-ACCESS read-write
			STATUS current
			DESCRIPTION
				"ap621   Upgrade an AP4021 device
				ap622   Upgrade an AP4022 device
				ap650   Upgrade an AP4600 device
				ap6511  Upgrade an AP4511 device
				ap6521  Upgrade an AP4521 device
				ap6522  Upgrade an AP4522 device
				ap6532  Upgrade an AP4532 device
				ap71xx  Upgrade an AP71XX device
				ap81xx  Upgrade an AP81XX device"
			::= { extremeWingActionLoadApUpgradeImageFileIn 1 }


		-- 1.3.6.1.4.1.1916.2.131.50.1.5.10.1.2
		extremeWingActionLoadApUpgradeImageFileInFileUrl OBJECT-TYPE
			SYNTAX DisplayString
			MAX-ACCESS read-write
			STATUS current
			DESCRIPTION
				"The location of file in URL format.
				URL:  ftp://<user>:<passwd>@<hostname|IP>[:port]/path/file"
			::= { extremeWingActionLoadApUpgradeImageFileIn 2 }

		
-- Output objects for action.
		-- 1.3.6.1.4.1.1916.2.131.50.1.5.10.2
		extremeWingActionLoadApUpgradeImageFileOut OBJECT IDENTIFIER ::= { extremeWingActionLoadApUpgradeImageFile 2 }


		-- 1.3.6.1.4.1.1916.2.131.50.1.5.10.2.1
		extremeWingActionLoadApUpgradeImageFileOutStatus OBJECT-TYPE
			SYNTAX TruthValue
			MAX-ACCESS read-only
			STATUS current
			DESCRIPTION
				"Whether the action is successful."
			::= { extremeWingActionLoadApUpgradeImageFileOut 1 }


		-- 1.3.6.1.4.1.1916.2.131.50.1.5.10.2.2
		extremeWingActionLoadApUpgradeImageFileOutMessage OBJECT-TYPE
			SYNTAX DisplayString
			MAX-ACCESS read-only
			STATUS current
			DESCRIPTION
				"Error message if the action is not successful."
			::= { extremeWingActionLoadApUpgradeImageFileOut 2 }


		-- 1.3.6.1.4.1.1916.2.131.50.1.5.10.3
		extremeWingActionLoadApUpgradeImageFileRun OBJECT-TYPE
			SYNTAX ExtremeWingDoActionNow
			MAX-ACCESS read-write
			STATUS current
			DESCRIPTION
				"Run action that Loads the AP firmware upgrade image files onto controller."
			::= { extremeWingActionLoadApUpgradeImageFile 3 }


-- Removes the ap-upgrade history
		-- 1.3.6.1.4.1.1916.2.131.50.1.5.11
		extremeWingActionClearApUpgradeHistory OBJECT IDENTIFIER ::= { extremeWingAction 11 }


-- Input objects for action.
		-- 1.3.6.1.4.1.1916.2.131.50.1.5.11.1
		extremeWingActionClearApUpgradeHistoryIn OBJECT IDENTIFIER ::= { extremeWingActionClearApUpgradeHistory 1 }


		-- 1.3.6.1.4.1.1916.2.131.50.1.5.11.1.1
		extremeWingActionClearApUpgradeHistoryInRfDomainName OBJECT-TYPE
			SYNTAX DisplayString
			MAX-ACCESS read-write
			STATUS current
			DESCRIPTION
				"Name of the rf-domain"
			::= { extremeWingActionClearApUpgradeHistoryIn 1 }


		-- 1.3.6.1.4.1.1916.2.131.50.1.5.11.1.2
		extremeWingActionClearApUpgradeHistoryInScope OBJECT-TYPE
			SYNTAX DisplayString
			MAX-ACCESS read-write
			STATUS current
			DESCRIPTION
				"special parameter to force execution on the NoC controller"
			::= { extremeWingActionClearApUpgradeHistoryIn 2 }


		-- 1.3.6.1.4.1.1916.2.131.50.1.5.11.3
		extremeWingActionClearApUpgradeHistoryRun OBJECT-TYPE
			SYNTAX ExtremeWingDoActionNow
			MAX-ACCESS read-write
			STATUS current
			DESCRIPTION
				"Run action that clears the AP firmware upgrade files history from controller."
			::= { extremeWingActionClearApUpgradeHistory 3 }


-- Upgrade adopted APs, invidual or a list of APs. The combination of the inputs decide which APs are upgraded
		-- 1.3.6.1.4.1.1916.2.131.50.1.5.12
		extremeWingActionApUpgrade OBJECT IDENTIFIER ::= { extremeWingAction 12 }


-- Input objects for action.
		-- 1.3.6.1.4.1.1916.2.131.50.1.5.12.1
		extremeWingActionApUpgradeIn OBJECT IDENTIFIER ::= { extremeWingActionApUpgrade 1 }


		-- 1.3.6.1.4.1.1916.2.131.50.1.5.12.1.1
		extremeWingActionApUpgradeInApList OBJECT-TYPE
			SYNTAX DisplayString
			MAX-ACCESS read-write
			STATUS current
			DESCRIPTION
				"all for all aps, mac address for individual aps."
			::= { extremeWingActionApUpgradeIn 1 }


		-- 1.3.6.1.4.1.1916.2.131.50.1.5.12.1.2
		extremeWingActionApUpgradeInApProduct OBJECT-TYPE
			SYNTAX DisplayString
			MAX-ACCESS read-write
			STATUS current
			DESCRIPTION
				"ap621   Upgrade an AP4021 device
				ap622   Upgrade an AP4022 device
				ap650   Upgrade an AP4600 device
				ap6511  Upgrade an AP4511 device
				ap6521  Upgrade an AP4521 device
				ap6522  Upgrade an AP4522 device
				ap6532  Upgrade an AP4532 device
				ap71xx  Upgrade an AP71XX device
				ap81xx  Upgrade an AP81XX device"
			::= { extremeWingActionApUpgradeIn 2 }


		-- 1.3.6.1.4.1.1916.2.131.50.1.5.12.1.3
		extremeWingActionApUpgradeInNoViaRfDomain OBJECT-TYPE
			SYNTAX  TruthValue
			MAX-ACCESS read-write
			STATUS current
			DESCRIPTION
				"AP upgrade will not get initiated on rf domain manager, if this is set True"
			::= { extremeWingActionApUpgradeIn 3 }


		-- 1.3.6.1.4.1.1916.2.131.50.1.5.12.1.4
		extremeWingActionApUpgradeInRfDomainName OBJECT-TYPE
			SYNTAX DisplayString
			MAX-ACCESS read-write
			STATUS current
			DESCRIPTION
				"Name of the rf-domain"
			::= { extremeWingActionApUpgradeIn 4 }


-- Input objects for action schedule type
		-- 1.3.6.1.4.1.1916.2.131.50.1.5.12.1.5
		extremeWingActionApUpgradeInSchedule OBJECT IDENTIFIER ::= { extremeWingActionApUpgradeIn 5 }


		-- 1.3.6.1.4.1.1916.2.131.50.1.5.12.1.5.1
		extremeWingActionApUpgradeInUpgradeTime OBJECT-TYPE
			SYNTAX Unsigned32
			MAX-ACCESS read-write
			STATUS current
			DESCRIPTION
				"The time(expressed in seconds since the epoch) after which the AP will be upgraded,
				This parameter is NOT mandatory"
			::= { extremeWingActionApUpgradeInSchedule 1 }


		-- 1.3.6.1.4.1.1916.2.131.50.1.5.12.1.5.2
		extremeWingActionApUpgradeInRebootTime OBJECT-TYPE
			SYNTAX Unsigned32
			MAX-ACCESS read-write
			STATUS current
			DESCRIPTION
				"The time(expressed in seconds since the epoch) after which the AP will be rebooted
				after upgrading, This parameter is NOT mandatory"
			::= { extremeWingActionApUpgradeInSchedule 2 }


		-- 1.3.6.1.4.1.1916.2.131.50.1.5.12.1.5.3
		extremeWingActionApUpgradeInNoReboot OBJECT-TYPE
			SYNTAX TruthValue
			MAX-ACCESS read-write
			STATUS current
			DESCRIPTION
				"The AP will not be rebooted after the upgrade, if this is set true"
			::= { extremeWingActionApUpgradeInSchedule 3 }


		-- 1.3.6.1.4.1.1916.2.131.50.1.5.12.1.5.4
		extremeWingActionApUpgradeInStaggeredReboot OBJECT-TYPE
			SYNTAX TruthValue
			MAX-ACCESS read-write
			STATUS current
			DESCRIPTION
				"Enabling this will reboot one AP at a time after the upgrade,
				if any error rebooting one AP upgrade, is aborted on the rest"
			::= { extremeWingActionApUpgradeInSchedule 4 }


		-- 1.3.6.1.4.1.1916.2.131.50.1.5.12.1.6
		extremeWingActionApUpgradeInScope OBJECT-TYPE
			SYNTAX DisplayString
			MAX-ACCESS read-write
			STATUS current
			DESCRIPTION
				"special parameter to force execution on the NoC controller"
			::= { extremeWingActionApUpgradeIn 6 }


		-- 1.3.6.1.4.1.1916.2.131.50.1.5.12.3
		extremeWingActionApUpgradeRun OBJECT-TYPE
			SYNTAX ExtremeWingDoActionNow
			MAX-ACCESS read-write
			STATUS current
			DESCRIPTION
				"Run action that Loads the AP firmware upgrade image file onto AP."
			::= { extremeWingActionApUpgrade 3 }


-- Cancel an already scheduled upgrade request.
		-- 1.3.6.1.4.1.1916.2.131.50.1.5.13
		extremeWingActionApUpgradeCancel OBJECT IDENTIFIER ::= { extremeWingAction 13 }


		-- Input objects for action.
		-- 1.3.6.1.4.1.1916.2.131.50.1.5.13.1
		extremeWingActionApUpgradeCancelIn OBJECT IDENTIFIER ::= { extremeWingActionApUpgradeCancel 1 }


		-- 1.3.6.1.4.1.1916.2.131.50.1.5.13.1.1
		extremeWingActionApUpgradeCancelInApList OBJECT-TYPE
			SYNTAX DisplayString
			MAX-ACCESS read-write
			STATUS current
			DESCRIPTION
				"all for all aps, mac address for individual aps."
			::= { extremeWingActionApUpgradeCancelIn 1 }


		-- 1.3.6.1.4.1.1916.2.131.50.1.5.12.1.2
		extremeWingActionApUpgradeCancelInApProduct OBJECT-TYPE
			SYNTAX DisplayString
			MAX-ACCESS read-write
			STATUS current
			DESCRIPTION
				"ap621   Upgrade an AP4021 device
				ap622   Upgrade an AP4022 device
				ap650   Upgrade an AP4600 device
				ap6511  Upgrade an AP4511 device
				ap6521  Upgrade an AP4521 device
				ap6522  Upgrade an AP4522 device
				ap6532  Upgrade an AP4532 device
				ap71xx  Upgrade an AP71XX device
				ap81xx  Upgrade an AP81XX device"
			::= { extremeWingActionApUpgradeCancelIn 2 }


		-- 1.3.6.1.4.1.1916.2.131.50.1.5.13.1.3
		extremeWingActionApUpgradeCancelInRfDomainName OBJECT-TYPE
			SYNTAX DisplayString
			MAX-ACCESS read-write
			STATUS current
			DESCRIPTION
				"Name of the rf-domain"
			::= { extremeWingActionApUpgradeCancelIn 3 }


		-- 1.3.6.1.4.1.1916.2.131.50.1.5.13.1.4
		extremeWingActionApUpgradeCancelInScope OBJECT-TYPE
			SYNTAX DisplayString
			MAX-ACCESS read-write
			STATUS current
			DESCRIPTION
				"special parameter to force execution on the NoC controller"
			::= { extremeWingActionApUpgradeCancelIn 4 }


-- Output objects for action.
		-- 1.3.6.1.4.1.1916.2.131.50.1.5.13.2
		extremeWingActionApUpgradeCancelOut OBJECT IDENTIFIER ::= { extremeWingActionApUpgradeCancel 2 }


		-- 1.3.6.1.4.1.1916.2.131.50.1.5.12.2.1
		extremeWingActionApUpgradeCancelOutStatus OBJECT-TYPE
			SYNTAX TruthValue
			MAX-ACCESS read-only
			STATUS current
			DESCRIPTION
				"Whether the action is successful."
			::= { extremeWingActionApUpgradeCancelOut 1 }


		-- 1.3.6.1.4.1.1916.2.131.50.1.5.12.2.2
		extremeWingActionApUpgradeCancelOutMessage OBJECT-TYPE
			SYNTAX DisplayString
			MAX-ACCESS read-only
			STATUS current
			DESCRIPTION
				"Error message if the action is not successful."
			::= { extremeWingActionApUpgradeCancelOut 2 }


		-- 1.3.6.1.4.1.1916.2.131.50.1.5.12.3
		extremeWingActionApUpgradeCancelRun OBJECT-TYPE
			SYNTAX ExtremeWingDoActionNow
			MAX-ACCESS read-write
			STATUS current
			DESCRIPTION
				"Run action that Cancel an already scheduled upgrade request."
			::= { extremeWingActionApUpgradeCancel 3 }


                -- 1.3.6.1.4.1.1916.2.131.50.1.5.14
                extremeWingActionDynamicRegistration OBJECT IDENTIFIER ::= { extremeWingAction 14 }


                -- 1.3.6.1.4.1.1916.2.131.50.1.5.14.1
                extremeWingActionExportMacUserDB OBJECT IDENTIFIER ::= { extremeWingActionDynamicRegistration 1 }


-- Input objects for action.
                -- 1.3.6.1.4.1.1916.2.131.50.1.5.14.1.1
                extremeWingActionExportMacUserDBIn OBJECT IDENTIFIER ::= { extremeWingActionExportMacUserDB 1 }


                -- 1.3.6.1.4.1.1916.2.131.50.1.5.14.1.1.1
                extremeWingActionExportMacUserDBInFileURL OBJECT-TYPE
                        SYNTAX DisplayString
                        MAX-ACCESS read-write
                        STATUS current
                        DESCRIPTION
                                "The path of file (in csv format) to import the MAC user database."
                        ::= { extremeWingActionExportMacUserDBIn 1 }


-- Output objects for action.
                -- 1.3.6.1.4.1.1916.2.131.50.1.5.14.1.2
                extremeWingActionExportMacUserDBOut OBJECT IDENTIFIER ::= { extremeWingActionExportMacUserDB 2 }


                -- 1.3.6.1.4.1.1916.2.131.50.1.5.14.1.2.1
                extremeWingActionExportMacUserDBOutStatus OBJECT-TYPE
                        SYNTAX TruthValue
                        MAX-ACCESS read-only
                        STATUS current
                        DESCRIPTION
                                "Whether the action is successful."
                        ::= { extremeWingActionExportMacUserDBOut 1 }


                -- 1.3.6.1.4.1.1916.2.131.50.1.5.14.1.2.2
                extremeWingActionExportMacUserDBOutMessage OBJECT-TYPE
                        SYNTAX DisplayString
                        MAX-ACCESS read-only
                        STATUS current
                        DESCRIPTION
                                "Error message if the action is not successful."
                        ::= { extremeWingActionExportMacUserDBOut 2 }


                -- 1.3.6.1.4.1.1916.2.131.50.1.5.14.1.3
                extremeWingActionExportMacUserDBRun OBJECT-TYPE
                        SYNTAX Integer32
                        MAX-ACCESS read-write
                        STATUS current
                        DESCRIPTION
                                "Run action"
                        ::= { extremeWingActionExportMacUserDB 3 }


                -- 1.3.6.1.4.1.1916.2.131.50.1.5.14.2
                extremeWingActionImportMacUserDB OBJECT IDENTIFIER ::= { extremeWingActionDynamicRegistration 2 }


-- Input objects for action.
                -- 1.3.6.1.4.1.1916.2.131.50.1.5.14.2.1
                extremeWingActionImportMacUserDBIn OBJECT IDENTIFIER ::= { extremeWingActionImportMacUserDB 1 }


                -- 1.3.6.1.4.1.1916.2.131.50.1.5.14.2.1.1
                extremeWingActionImportMacUserDBInFileURL OBJECT-TYPE
                        SYNTAX DisplayString
                        MAX-ACCESS read-write
                        STATUS current
                        DESCRIPTION
                                "The path of file (in csv format) to import the MAC user database."
                        ::= { extremeWingActionImportMacUserDBIn 1 }


-- Output objects for action.
                -- 1.3.6.1.4.1.1916.2.131.50.1.5.14.2.2
                extremeWingActionImportMacUserDBOut OBJECT IDENTIFIER ::= { extremeWingActionImportMacUserDB 2 }


                -- 1.3.6.1.4.1.1916.2.131.50.1.5.14.2.2.1
                extremeWingActionImportMacUserDBOutStatus OBJECT-TYPE
                        SYNTAX TruthValue
                        MAX-ACCESS read-only
                        STATUS current
                        DESCRIPTION
                                "Whether the action is successful."
                        ::= { extremeWingActionImportMacUserDBOut 1 }


                -- 1.3.6.1.4.1.1916.2.131.50.1.5.14.2.2.2
                extremeWingActionImportMacUserDBOutMessage OBJECT-TYPE
                        SYNTAX DisplayString
                        MAX-ACCESS read-only
                        STATUS current
                        DESCRIPTION
                                "Error message if the action is not successful."
                        ::= { extremeWingActionImportMacUserDBOut 2 }


                -- 1.3.6.1.4.1.1916.2.131.50.1.5.14.2.3
                extremeWingActionImportMacUserDBRun OBJECT-TYPE
                        SYNTAX Integer32
                        MAX-ACCESS read-write
                        STATUS current
                        DESCRIPTION
                                "Run action"
                        ::= { extremeWingActionImportMacUserDB 3 }


                -- 1.3.6.1.4.1.1916.2.131.50.1.5.14.3
                extremeWingActionDeleteUserFromMacUserDB OBJECT IDENTIFIER ::= { extremeWingActionDynamicRegistration 3 }


-- Input objects for action.
                -- 1.3.6.1.4.1.1916.2.131.50.1.5.14.3.1
                extremeWingActionDeleteUserFromMacUserDBIn OBJECT IDENTIFIER ::= { extremeWingActionDeleteUserFromMacUserDB 1 }


                -- 1.3.6.1.4.1.1916.2.131.50.1.5.14.3.1.1
                extremeWingActionDeleteUserFromMacUserDBInUser OBJECT-TYPE
                        SYNTAX DisplayString
                        MAX-ACCESS read-write
                        STATUS current
                        DESCRIPTION
                                "User name to delete. Either a single user name or (all) to delete all."
                        ::= { extremeWingActionDeleteUserFromMacUserDBIn 1 }


-- Output objects for action.
                -- 1.3.6.1.4.1.1916.2.131.50.1.5.14.3.2
                extremeWingActionDeleteUserFromMacUserDBOut OBJECT IDENTIFIER ::= { extremeWingActionDeleteUserFromMacUserDB 2 }


                -- 1.3.6.1.4.1.1916.2.131.50.1.5.14.3.2.1
                extremeWingActionDeleteUserFromMacUserDBOutStatus OBJECT-TYPE
                        SYNTAX TruthValue
                        MAX-ACCESS read-only
                        STATUS current
                        DESCRIPTION
                                "Whether the action is successful."
                        ::= { extremeWingActionDeleteUserFromMacUserDBOut 1 }


                -- 1.3.6.1.4.1.1916.2.131.50.1.5.14.3.2.2
                extremeWingActionDeleteUserFromMacUserDBOutMessage OBJECT-TYPE
                        SYNTAX DisplayString
                        MAX-ACCESS read-only
                        STATUS current
                        DESCRIPTION
                                "Error message if the action is not successful."
                        ::= { extremeWingActionDeleteUserFromMacUserDBOut 2 }


                -- 1.3.6.1.4.1.1916.2.131.50.1.5.14.3.3
                extremeWingActionDeleteUserFromMacUserDBRun OBJECT-TYPE
                        SYNTAX Integer32
                        MAX-ACCESS read-write
                        STATUS current
                        DESCRIPTION
                                "Run action"
                        ::= { extremeWingActionDeleteUserFromMacUserDB 3 }

		-- 1.3.6.1.4.1.1916.2.131.50.1.5.15
		extremeWingActionDeviceUpgrade OBJECT IDENTIFIER ::= { extremeWingAction 15 }

		
		-- 1.3.6.1.4.1.1916.2.131.50.1.5.15.1
		extremeWingActionDeviceStartUpgrade OBJECT IDENTIFIER ::= { extremeWingActionDeviceUpgrade 1 }

		
		-- 1.3.6.1.4.1.1916.2.131.50.1.5.15.1.1
		extremeWingActionDeviceStartUpgradeIn OBJECT IDENTIFIER ::= { extremeWingActionDeviceStartUpgrade 1 }

		
		-- 1.3.6.1.4.1.1916.2.131.50.1.5.15.1.1.1
		extremeWingActionDeviceStartUpgradeInMac OBJECT-TYPE
			SYNTAX DisplayString
			MAX-ACCESS read-write
			STATUS current
			DESCRIPTION
				"mac-address of the device."
			::= { extremeWingActionDeviceStartUpgradeIn 1 }

		
		-- 1.3.6.1.4.1.1916.2.131.50.1.5.15.1.1.2
		extremeWingActionDeviceStartUpgradeInUrlPath OBJECT-TYPE
			SYNTAX DisplayString
			MAX-ACCESS read-write
			STATUS current
			DESCRIPTION
				"URL PATH"
			::= { extremeWingActionDeviceStartUpgradeIn 2 }

		
		-- 1.3.6.1.4.1.1916.2.131.50.1.5.15.1.2
		extremeWingActionDeviceStartUpgradeOut OBJECT IDENTIFIER ::= { extremeWingActionDeviceStartUpgrade 2 }

		
		-- 1.3.6.1.4.1.1916.2.131.50.1.5.15.1.2.1
		extremeWingActionDeviceStartUpgradeOutStatus OBJECT-TYPE
			SYNTAX TruthValue
			MAX-ACCESS read-only
			STATUS current
			DESCRIPTION
				"Whether the action is successful."
			::= { extremeWingActionDeviceStartUpgradeOut 1 }

		
		-- 1.3.6.1.4.1.1916.2.131.50.1.5.15.1.2.2
		extremeWingActionDeviceStartUpgradeOutMessage OBJECT-TYPE
			SYNTAX DisplayString
			MAX-ACCESS read-only
			STATUS current
			DESCRIPTION
				"Error message if the action is not successful."
			::= { extremeWingActionDeviceStartUpgradeOut 2 }

		
		-- 1.3.6.1.4.1.1916.2.131.50.1.5.15.1.3
		extremeWingActionDeviceStartUpgradeRun OBJECT-TYPE
			SYNTAX ExtremeWingDoActionNow
			MAX-ACCESS read-write
			STATUS current
			DESCRIPTION
				"Run action that initiate the upgrade request"
			::= { extremeWingActionDeviceStartUpgrade 3 }

		
		-- 1.3.6.1.4.1.1916.2.131.50.1.5.15.2
		extremeWingActionDeviceAbortUpgrade OBJECT IDENTIFIER ::= { extremeWingActionDeviceUpgrade 2 }

		
		-- 1.3.6.1.4.1.1916.2.131.50.1.5.15.2.1
		extremeWingActionDeviceAbortUpgradeIn OBJECT IDENTIFIER ::= { extremeWingActionDeviceAbortUpgrade 1 }

		
		-- 1.3.6.1.4.1.1916.2.131.50.1.5.15.2.1.1
		extremeWingActionDeviceAbortUpgradeInMac OBJECT-TYPE
			SYNTAX DisplayString
			MAX-ACCESS read-write
			STATUS current
			DESCRIPTION
				"mac-address of the device."
			::= { extremeWingActionDeviceAbortUpgradeIn 1 }

		
		-- 1.3.6.1.4.1.1916.2.131.50.1.5.15.2.2
		extremeWingActionDeviceAbortUpgradeOut OBJECT IDENTIFIER ::= { extremeWingActionDeviceAbortUpgrade 2 }

		
		-- 1.3.6.1.4.1.1916.2.131.50.1.5.15.2.2.1
		extremeWingActionDeviceAbortUpgradeOutStatus OBJECT-TYPE
			SYNTAX TruthValue
			MAX-ACCESS read-only
			STATUS current
			DESCRIPTION
				"Whether the action is successful."
			::= { extremeWingActionDeviceAbortUpgradeOut 1 }

		
		-- 1.3.6.1.4.1.1916.2.131.50.1.5.15.2.2.2
		extremeWingActionDeviceAbortUpgradeOutMessage OBJECT-TYPE
			SYNTAX DisplayString
			MAX-ACCESS read-only
			STATUS current
			DESCRIPTION
				"Error message if the action is not successful"
			::= { extremeWingActionDeviceAbortUpgradeOut 2 }

		
		-- 1.3.6.1.4.1.1916.2.131.50.1.5.15.2.3
		extremeWingActionDeviceAbortUpgradeRun OBJECT-TYPE
			SYNTAX ExtremeWingDoActionNow
			MAX-ACCESS read-write
			STATUS current
			DESCRIPTION
				"Run action that stops the already initiated upgrade request"
			::= { extremeWingActionDeviceAbortUpgrade 3 }


                -- 1.3.6.1.4.1.1916.2.131.50.1.5.16
                extremeWingActionRaidManage OBJECT IDENTIFIER ::= { extremeWingAction 16 }


                -- 1.3.6.1.4.1.1916.2.131.50.1.5.16.1
                extremeWingActionRaidManageArray OBJECT IDENTIFIER ::= { extremeWingActionRaidManage 1 }


-- Input objects for action.
                -- 1.3.6.1.4.1.1916.2.131.50.1.5.16.1.1
                extremeWingActionRaidManageArrayIn OBJECT IDENTIFIER ::= { extremeWingActionRaidManageArray 1 }


                -- 1.3.6.1.4.1.1916.2.131.50.1.5.16.1.1.1
                extremeWingActionRaidManageArrayCommand  OBJECT-TYPE
                        SYNTAX DisplayString
                        MAX-ACCESS read-write
                        STATUS current
                        DESCRIPTION
                                "."
                        ::= { extremeWingActionRaidManageArrayIn 1 }

-- Output objects for action.
                -- 1.3.6.1.4.1.1916.2.131.50.1.5.16.1.2
                extremeWingActionRaidManageArrayOut OBJECT IDENTIFIER ::= { extremeWingActionRaidManageArray 2 }


                -- 1.3.6.1.4.1.1916.2.131.50.1.5.16.1.2.1
                extremeWingActionRaidManageArrayStatus OBJECT-TYPE
                        SYNTAX TruthValue
                        MAX-ACCESS read-only
                        STATUS current
                        DESCRIPTION
                                "Whether the action is successful."
                        ::= { extremeWingActionRaidManageArrayOut 1 }


                -- 1.3.6.1.4.1.1916.2.131.50.1.5.16.1.2.2
                extremeWingActionRaidManageArrayMessage OBJECT-TYPE
                        SYNTAX DisplayString
                        MAX-ACCESS read-only
                        STATUS current
                        DESCRIPTION
                                "Error message if the action is not successful."
                        ::= { extremeWingActionRaidManageArrayOut 2 }


                -- 1.3.6.1.4.1.1916.2.131.50.1.5.16.1.3
                extremeWingActionRaidManageArrayRun OBJECT-TYPE
                        SYNTAX ExtremeWingDoActionNow
                        MAX-ACCESS read-write
                        STATUS current
                        DESCRIPTION
                                "Run action upgrade request."
                        ::= { extremeWingActionRaidManageArray 3 }

                -- 1.3.6.1.4.1.1916.2.131.50.1.5.16.2
                extremeWingActionRaidManageDrive  OBJECT IDENTIFIER ::= { extremeWingActionRaidManage 2 }


-- Input objects for action.
                -- 1.3.6.1.4.1.1916.2.131.50.1.5.16.2.1
                extremeWingActionRaidManageDriveIn OBJECT IDENTIFIER ::= { extremeWingActionRaidManageDrive 1 }


                -- 1.3.6.1.4.1.1916.2.131.50.1.5.16.2.1.1
                extremeWingActionRaidManageDriveSelect OBJECT-TYPE
                        SYNTAX Unsigned32
                        MAX-ACCESS read-write
                        STATUS current
                        DESCRIPTION
                                "."
                        ::= { extremeWingActionRaidManageDriveIn 1 }

                -- 1.3.6.1.4.1.1916.2.131.50.1.5.16.2.1.2
                extremeWingActionRaidManageDriveCommand  OBJECT-TYPE
                        SYNTAX DisplayString
                        MAX-ACCESS read-write
                        STATUS current
                        DESCRIPTION
                                "."
                        ::= { extremeWingActionRaidManageDriveIn 2 }


-- Output objects for action.
                -- 1.3.6.1.4.1.1916.2.131.50.1.5.16.2.2
                extremeWingActionRaidManageDriveOut OBJECT IDENTIFIER ::= { extremeWingActionRaidManageDrive 2 }


                -- 1.3.6.1.4.1.1916.2.131.50.1.5.16.2.2.1
                extremeWingActionRaidManageDriveStatus OBJECT-TYPE
                        SYNTAX TruthValue
                        MAX-ACCESS read-only
                        STATUS current
                        DESCRIPTION
                                "Whether the action is successful."
                        ::= { extremeWingActionRaidManageDriveOut 1 }


                -- 1.3.6.1.4.1.1916.2.131.50.1.5.16.2.2.2
                extremeWingActionRaidManageDriveMessage OBJECT-TYPE
                        SYNTAX DisplayString
                        MAX-ACCESS read-only
                        STATUS current
                        DESCRIPTION
                                "Error message if the action is not successful."
                        ::= { extremeWingActionRaidManageDriveOut 2 }

                -- 1.3.6.1.4.1.1916.2.131.50.1.5.16.2.3
                extremeWingActionRaidManageDriveRun OBJECT-TYPE
                        SYNTAX ExtremeWingDoActionNow
                        MAX-ACCESS read-write
                        STATUS current
                        DESCRIPTION
                                "Run action abort upgrade request."
                        ::= { extremeWingActionRaidManageDrive 3 }


		-- 1.3.6.1.4.1.1916.2.131.50.2
		extremeWingConformance OBJECT IDENTIFIER ::= { extremeWingMIB 2 }

		
		-- 1.3.6.1.4.1.1916.2.131.50.2.1
		extremeWingCompliances OBJECT IDENTIFIER ::= { extremeWingConformance 1 }

		
		-- 1.3.6.1.4.1.1916.2.131.50.2.1.1
		extremeWingCompliance MODULE-COMPLIANCE
			STATUS current
			DESCRIPTION 
				"The compliance statement for agents that support the WiNG MIB."
			MODULE -- this module
				MANDATORY-GROUPS { extremeWingObjectGroup, extremeWingNotificationGroup }
			::= { extremeWingCompliances 1 }

		
		-- 1.3.6.1.4.1.1916.2.131.50.2.2
		extremeWingGroups OBJECT IDENTIFIER ::= { extremeWingConformance 2 }

		
		-- 1.3.6.1.4.1.1916.2.131.50.2.2.1
		extremeWingObjectGroup OBJECT-GROUP
			OBJECTS { extremeWingEventMnemonic, extremeWingEventModule, extremeWingEventSeverity, extremeWingEventMsg, extremeWingEventSourceAddr, 
				extremeWingConfigSysMacAddr, extremeWingStatsDevMac, extremeWingStatsDevType, extremeWingStatsDevHostname,
				extremeWingStatsDevVersion, extremeWingStatsDevSerialNo, extremeWingStatsDevRfDomainName, extremeWingStatsDevOnline,
				extremeWingStatsDevAdoptDevMac, extremeWingStatsDevAdoptDevType, extremeWingStatsDevAdoptDevHostname,
				extremeWingStatsDevAdoptDevVersion, extremeWingStatsDevAdoptDevSerialNo, extremeWingStatsDevAdoptDevRfDomainName,
				extremeWingStatsDevAdoptDevOnline, extremeWingStatsRfdName, extremeWingStatsRfdManager, extremeWingStatsRfdWlClientMac,
				extremeWingStatsRfdWlClientMacName, extremeWingStatsRfdWlClientVendor, extremeWingStatsRfdWlClientBss,
				extremeWingStatsRfdWlClientAp, extremeWingStatsRfdWlClientRadioNum, extremeWingStatsRfdWlClientRadioType,
				extremeWingStatsRfdWlClientRadioEnc, extremeWingStatsRfdWlClientRadioAuth, extremeWingStatsRfdWlClientWlan,
				extremeWingStatsRfdWlClientState, extremeWingStatsRfdWlClientHotspotAuthed, extremeWingStatsRfdWlClientVlan,
				extremeWingStatsRfdWlClientUserName, extremeWingStatsRfdWlClientIp, extremeWingStatsRfdWlClientRfdName,
				extremeWingStatsRfdWlClientHostname, extremeWingStatsRfdWlClientLocation, extremeWingStatsRfdWlClientRadioId,
				extremeWingStatsRfdWlClientRadioAlias, extremeWingStatsRfdWlApInfoMac, extremeWingStatsRfdWlApInfoFaultDetected,
				extremeWingStatsRfdWlApInfoNumRadios, extremeWingStatsRfdWlApInfoNumClients, extremeWingStatsRfdWlApInfoLastCalTime,
				extremeWingStatsRfdWlApInfoType, extremeWingStatsRfdWlApInfoStatsMode, extremeWingStatsRfdWlApInfoStatsInterval,
				extremeWingStatsRfdWlApInfoHostname, extremeWingStatsRfdWlApInfoRfDomainName, extremeWingStatsRfdWlApInfoLocation,
				extremeWingStatsRfdWlApInfoAdoptedTo, extremeWingStatsDevAdoptPendingDevMac, extremeWingStatsDevAdoptPendingDevType,
				extremeWingStatsDevAdoptPendingDevTarget, extremeWingStatsDevAdoptPendingDevDisOption, extremeWingStatsDevAdoptPendingDevVersion,
				extremeWingStatsDevAdoptPendingDevSerialNumber, extremeWingStatsDevAdoptPendingDevReason, extremeWingStatsDevAdoptPendingDevNumRadios,
				extremeWingStatsDevAdoptPendingDevIp, extremeWingStatsDevAdoptPendingDevVlan, extremeWingStatsRfdWlClientDetailMac,
				extremeWingStatsRfdWlClientDetailMacName, extremeWingStatsRfdWlClientDetailVendor, extremeWingStatsRfdWlClientDetailBss,
				extremeWingStatsRfdWlClientDetailAp, extremeWingStatsRfdWlClientDetailRadioNum, extremeWingStatsRfdWlClientDetailRadioType,
				extremeWingStatsRfdWlClientDetailEnc, extremeWingStatsRfdWlClientDetailAuth, extremeWingStatsRfdWlClientDetailWlan,
				extremeWingStatsRfdWlClientDetailState, extremeWingStatsRfdWlClientDetailHotspotAuthed, extremeWingStatsRfdWlClientDetailVlan,
				extremeWingStatsRfdWlClientDetailUsername, extremeWingStatsRfdWlClientDetailIp, extremeWingStatsRfdWlClientDetailRfDomainName,
				extremeWingStatsRfdWlClientDetailMc2ucStreams, extremeWingStatsRfdWlClientDetailHostname, extremeWingStatsRfdWlClientDetailLocation,
				extremeWingStatsRfdWlClientDetailRadioId, extremeWingStatsRfdWlClientDetailRadioAlias, extremeWingStatsRfdWlClientDetailSsid,
				extremeWingStatsRfdWlClientDetailAid, extremeWingStatsRfdWlClientDetailRates, extremeWingStatsRfdWlClientDetailInPsp,
				extremeWingStatsRfdWlClientDetailIsWmm, extremeWingStatsRfdWlClientDetailUapsd, extremeWingStatsRfdWlClientDetailSmPowersave,
				extremeWingStatsRfdWlClientDetailHtCapable, extremeWingStatsRfdWlClientDetailShortGi, extremeWingStatsRfdWlClientDetailCurWidth40,
				extremeWingStatsRfdWlClientDetailAmsduSize, extremeWingStatsRfdWlClientDetailAmpduSize, extremeWingStatsRfdWlClientDetailAmpduSpacing,
				extremeWingStatsRfdWlClientDetailRifs, extremeWingStatsRfdWlClientDetailLastActive, extremeWingStatsRfdWlClientDetailLastAssoc,
				extremeWingStatsRfdWlClientDetailSessTime, extremeWingStatsRfdWlClientDetailIdleTime, extremeWingStatsRfdWlClientDetailMaxPhyRate,
				extremeWingStatsRfdWlClientDetailMaxUserRate, extremeWingStatsRfdWlClientDetailIsVoice, extremeWingStatsRfdWlClientDetailIsCallActive,
				extremeWingStatsRfdWlClientStatMac, extremeWingStatsRfdWlClientStatMacName, extremeWingStatsRfdWlClientStatVendor, extremeWingStatsRfdWlClientStatAp,
				extremeWingStatsRfdWlClientStatTxPkts, extremeWingStatsRfdWlClientStatRxPkts, extremeWingStatsRfdWlClientStatTxDropped,
				extremeWingStatsRfdWlClientStatRxErrors, extremeWingStatsRfdWlClientStatTIndex, extremeWingStatsRfdWlClientStatTxBps,
				extremeWingStatsRfdWlClientStatRxBps, extremeWingStatsRfdWlClientStatSignal, extremeWingStatsRfdWlClientStatNoise, extremeWingStatsRfdWlClientStatSnr,
				extremeWingStatsRfdWlClientStatTxRate, extremeWingStatsRfdWlClientStatRxRate, extremeWingStatsRfdWlClientStatErrorRate,
				extremeWingStatsRfdWlClientStatQIndex, extremeWingStatsRfdWlClientStatDetailMac, extremeWingStatsRfdWlClientStatDetailMacName,
				extremeWingStatsRfdWlClientStatDetailVendor, extremeWingStatsRfdWlClientStatDetailTxPkts, extremeWingStatsRfdWlClientStatDetailRxPkts,
				extremeWingStatsRfdWlClientStatDetailTxDropped, extremeWingStatsRfdWlClientStatDetailRxErrors, extremeWingStatsRfdWlClientStatDetailTIndex,
				extremeWingStatsRfdWlClientStatDetailTxBps, extremeWingStatsRfdWlClientStatDetailRxBps, extremeWingStatsRfdWlClientStatDetailSignal,
				extremeWingStatsRfdWlClientStatDetailNoise, extremeWingStatsRfdWlClientStatDetailSnr, extremeWingStatsRfdWlClientStatDetailTxRate,
				extremeWingStatsRfdWlClientStatDetailRxRate, extremeWingStatsRfdWlClientStatDetailErrorRate, extremeWingStatsRfdWlClientStatDetailQIndex,
				extremeWingStatsRfdWlClientStatDetailRawTxPkts, extremeWingStatsRfdWlClientStatDetailRawRxPkts, extremeWingStatsRfdWlClientStatDetailRawTotalPkts,
				extremeWingStatsRfdWlClientStatDetailRawTxBps, extremeWingStatsRfdWlClientStatDetailRawRxBps, extremeWingStatsRfdWlClientStatDetailRawTotalBps,
				extremeWingStatsRfdWlClientStatDetailRawTxPps, extremeWingStatsRfdWlClientStatDetailRawRxPps, extremeWingStatsRfdWlClientStatDetailRawTotalPps,
				extremeWingStatsRfdWlClientStatDetailRawTxRate, extremeWingStatsRfdWlClientStatDetailRawRxRate, extremeWingStatsRfdWlClientStatDetailRawOverallRate,
				extremeWingStatsRfdWlClientStatDetailTxPps, extremeWingStatsRfdWlClientStatDetailRxPps, extremeWingStatsRfdWlClientStatDetailTotalPps,
				extremeWingStatsRfdWlClientStatDetailRxProbes, extremeWingStatsRfdWlClientStatDetailRxActions, extremeWingStatsRfdWlClientStatDetailRxPsPoll,
				extremeWingStatsRfdWlClientStatDetailLastCallStatus, extremeWingStatsRfdWlClientStatDetailCallTotal, extremeWingStatsRfdWlClientStatDetailCallStatOk,
				extremeWingStatsRfdWlClientStatDetailCallStatBusy, extremeWingStatsRfdWlClientStatDetailCallStatNoAnswer,
				extremeWingStatsRfdWlClientStatDetailCallStatUnknownDest, extremeWingStatsRfdWlClientStatDetailCallStatAdmDenied,
				extremeWingStatsRfdWlClientStatDetailCallStatDeclined, extremeWingStatsRfdWlClientStatDetailCallStatUnauth,
				extremeWingStatsRfdWlClientStatDetailCallStatUnsuppMedia, extremeWingStatsRfdWlClientStatDetailCallStatTempUnavail,
				extremeWingStatsRfdWlClientStatDetailCallStatNoForkAllowed, extremeWingStatsRfdWlClientStatDetailCallStatSessInactive,
				extremeWingStatsRfdWlClientStatDetailCallStatOther, extremeWingStatsRfdWlClientStatDetailTotalPkts, extremeWingStatsDevWlClientMac,
				extremeWingStatsDevWlClientMacName, extremeWingStatsDevWlClientVendor, extremeWingStatsDevWlClientBss, extremeWingStatsDevWlClientAp, extremeWingStatsDevWlClientRadioNum,
				extremeWingStatsDevWlClientRadioType, extremeWingStatsDevWlClientRadioEnc, extremeWingStatsDevWlClientRadioAuth, extremeWingStatsDevWlClientWlan,
				extremeWingStatsDevWlClientState, extremeWingStatsDevWlClientHotspotAuthed, extremeWingStatsDevWlClientVlan, extremeWingStatsDevWlClientUserName,
				extremeWingStatsDevWlClientIp, extremeWingStatsDevWlClientRfdName, extremeWingStatsDevWlClientHostname, extremeWingStatsDevWlClientLocation,
				extremeWingStatsDevWlClientRadioId, extremeWingStatsDevWlClientRadioAlias, extremeWingStatsRfdWlRadioId, extremeWingStatsRfdWlRadioDeviceMac,
				extremeWingStatsRfdWlRadioAlias, extremeWingStatsRfdWlRadioMac, extremeWingStatsRfdWlRadioType, extremeWingStatsRfdWlRadioHostname, extremeWingStatsRfdWlRadioRfdName,
				extremeWingStatsRfdWlRadioLocation, extremeWingStatsRfdWlRadioState, extremeWingStatsRfdWlRadioCurChannel, extremeWingStatsRfdWlRadioConfigChannel,
				extremeWingStatsRfdWlRadioCurPower, extremeWingStatsRfdWlRadioConfigPower, extremeWingStatsRfdWlRadioMaxUserRate, extremeWingStatsRfdWlRadioNumClient,
				extremeWingStatsRfdWlRadioStatId, extremeWingStatsRfdWlRadioStatDeviceMac, extremeWingStatsRfdWlRadioStatAlias, extremeWingStatsRfdWlRadioStatMac,
				extremeWingStatsRfdWlRadioStatType, extremeWingStatsRfdWlRadioStatTxPkts, extremeWingStatsRfdWlRadioStatRxPkts, extremeWingStatsRfdWlRadioStatTxDropped,
				extremeWingStatsRfdWlRadioStatRxErrors, extremeWingStatsRfdWlRadioStatTIndex, extremeWingStatsRfdWlRadioStatTxBps, extremeWingStatsRfdWlRadioStatRxBps,
				extremeWingStatsRfdWlRadioStatSignal, extremeWingStatsRfdWlRadioStatNoise, extremeWingStatsRfdWlRadioStatSnr, extremeWingStatsRfdWlRadioStatTxRate,
				extremeWingStatsRfdWlRadioStatRxRate, extremeWingStatsRfdWlRadioStatErrorRate, extremeWingStatsRfdWlRadioStatQIndex, extremeWingStatsRfdWlRadioStatNumClients,
				extremeWingStatsRfdWlRadioStatNumBClients, extremeWingStatsRfdWlRadioStatNumBgClients, extremeWingStatsRfdWlRadioStatNumBgnClients,
				extremeWingStatsRfdWlRadioStatNumAClients, extremeWingStatsRfdWlRadioStatNumAnClients, extremeWingStatsRfdWlRadioStatMediumErrorRate,
				extremeWingStatsRfdWlRadioDetailId, extremeWingStatsRfdWlRadioDetailDeviceMac, extremeWingStatsRfdWlRadioDetailAlias, extremeWingStatsRfdWlRadioDetailMac,
				extremeWingStatsRfdWlRadioDetailType, extremeWingStatsRfdWlRadioDetailHostname, extremeWingStatsRfdWlRadioDetailRfdName, extremeWingStatsRfdWlRadioDetailLocation,
				extremeWingStatsRfdWlRadioDetailState, extremeWingStatsRfdWlRadioDetailCurChannel, extremeWingStatsRfdWlRadioDetailConfigChannel,
				extremeWingStatsRfdWlRadioDetailCurPower, extremeWingStatsRfdWlRadioDetailConfigPower, extremeWingStatsRfdWlRadioDetailMaxUserRate,
				extremeWingStatsRfdWlRadioDetailNumClient, extremeWingStatsRfdWlRadioDetailSpectrumMgmt, extremeWingStatsRfdWlRadioDetailShortPreamble,
				extremeWingStatsRfdWlRadioDetailNonErpPresent, extremeWingStatsRfdWlRadioDetailErpProtectionOn, extremeWingStatsRfdWlRadioDetailNonErpDetected,
				extremeWingStatsRfdWlRadioDetailHtProtectionOn, extremeWingStatsRfdWlRadioDetailHt20Present, extremeWingStatsRfdWlRadioDetailNonHtDetected,
				extremeWingStatsRfdWlRadioDetailDualChannelOn, extremeWingStatsRfdWlRadioDetailTxAntennaUsed, extremeWingStatsRfdWlRadioDetailRxAntennaUsed,
				extremeWingStatsRfdWlRadioDetailMaxPhyRate, extremeWingStatsRfdWlRadioDetailCurMcastStreams, extremeWingStatsRfdWlRadioDetailMaxMcastStreams,
				extremeWingStatsRfdWlRadioDetailMcastStreams, extremeWingStatsRfdWlRadioDetailLastError, extremeWingStatsRfdWlRadioStatDetailId,
				extremeWingStatsRfdWlRadioStatDetailDeviceMac, extremeWingStatsRfdWlRadioStatDetailAlias, extremeWingStatsRfdWlRadioStatDetailMac,
				extremeWingStatsRfdWlRadioStatDetailType, extremeWingStatsRfdWlRadioStatDetailTxPkts, extremeWingStatsRfdWlRadioStatDetailRxPkts,
				extremeWingStatsRfdWlRadioStatDetailTxDropped, extremeWingStatsRfdWlRadioStatDetailRxErrors, extremeWingStatsRfdWlRadioStatDetailTIndex,
				extremeWingStatsRfdWlRadioStatDetailTxBps, extremeWingStatsRfdWlRadioStatDetailRxBps, extremeWingStatsRfdWlRadioStatDetailSignal,
				extremeWingStatsRfdWlRadioStatDetailNoise, extremeWingStatsRfdWlRadioStatDetailSnr, extremeWingStatsRfdWlRadioStatDetailTxRate,
				extremeWingStatsRfdWlRadioStatDetailRxRate, extremeWingStatsRfdWlRadioStatDetailErrorRate, extremeWingStatsRfdWlRadioStatDetailQIndex,
				extremeWingStatsRfdWlRadioStatDetailNumClients, extremeWingStatsRfdWlRadioStatDetailNumBClients, extremeWingStatsRfdWlRadioStatDetailNumBgClients,
				extremeWingStatsRfdWlRadioStatDetailNumBgnClients, extremeWingStatsRfdWlRadioStatDetailNumAClients, extremeWingStatsRfdWlRadioStatDetailNumAnClients,
				extremeWingStatsRfdWlRadioStatDetailMediumErrorRate, extremeWingStatsRfdWlRadioStatDetailRawTxPkts, extremeWingStatsRfdWlRadioStatDetailRawRxPkts,
				extremeWingStatsRfdWlRadioStatDetailRawTotalPkts, extremeWingStatsRfdWlRadioStatDetailRawTxBps, extremeWingStatsRfdWlRadioStatDetailRawRxBps,
				extremeWingStatsRfdWlRadioStatDetailRawTotalBps, extremeWingStatsRfdWlRadioStatDetailRawTxPps, extremeWingStatsRfdWlRadioStatDetailRawRxPps,
				extremeWingStatsRfdWlRadioStatDetailRawTotalPps, extremeWingStatsRfdWlRadioStatDetailRawTxRate, extremeWingStatsRfdWlRadioStatDetailRawRxRate,
				extremeWingStatsRfdWlRadioStatDetailRawOverallRate, extremeWingStatsRfdWlRadioStatDetailTxPps, extremeWingStatsRfdWlRadioStatDetailRxPps,
				extremeWingStatsRfdWlRadioStatDetailTotalPps, extremeWingStatsRfdWlRadioStatDetailRxProbes, extremeWingStatsRfdWlRadioStatDetailRxActions,
				extremeWingStatsRfdWlRadioStatDetailRxPsPoll, extremeWingStatsRfdWlRadioStatDetailLastCallStatus, extremeWingStatsRfdWlRadioStatDetailCallTotal,
				extremeWingStatsRfdWlRadioStatDetailCallStatOk, extremeWingStatsRfdWlRadioStatDetailCallStatBusy, extremeWingStatsRfdWlRadioStatDetailCallStatNoAnswer,
				extremeWingStatsRfdWlRadioStatDetailCallStatUnknownDest, extremeWingStatsRfdWlRadioStatDetailCallStatAdmDenied,
				extremeWingStatsRfdWlRadioStatDetailCallStatDeclined, extremeWingStatsRfdWlRadioStatDetailCallStatUnauth,
				extremeWingStatsRfdWlRadioStatDetailCallStatUnsuppMedia, extremeWingStatsRfdWlRadioStatDetailCallStatTempUnavail,
				extremeWingStatsRfdWlRadioStatDetailCallStatNoForkAllowed, extremeWingStatsRfdWlRadioStatDetailCallStatSessInactive,
				extremeWingStatsRfdWlRadioStatDetailCallStatOther, extremeWingStatsRfdWlRadioStatDetailTotalPkts, extremeWingStatsRfdWlRadioStatDetailRxCrcErrors,
				extremeWingStatsRfdWlRadioStatDetailRxUndecryptable, extremeWingStatsRfdWlRadioStatDetailRxIncomplete, extremeWingStatsRfdWlRadioStatDetailRxLengthErrors,
				extremeWingStatsRfdWlRadioStatDetailRxOtherErrors, extremeWingStatsRfdWlRadioStatDetailLongPreambleClients, extremeWingStatsRfdWlRadioStatDetailLtClients,
				extremeWingStatsRfdWlRadioStatDetailHt20Clients, extremeWingStatsRfdWlRadioStatDetailLongSlotClients, extremeWingCfgWlanName, extremeWingCfgWlanShutdown,
				extremeWingCfgWlanSsid, extremeWingCfgWlanDescr, extremeWingCfgWlanEncType, extremeWingCfgWlanAuthType, extremeWingCfgWlanCaptivePortalEnforcement, extremeWingCfgWlanClientPower,
				extremeWingCfgWlanNasId, extremeWingCfgWlanNasPortId, extremeWingCfgWlanBroadcastSsid, extremeWingCfgWlanAnswerBroadcastProbes, extremeWingCfgWlanClientClientCommunication,
				extremeWingCfgWlanHoldTime, extremeWingCfgWlanInactivityTimeout, extremeWingCfgWlanCredCacheAgeout, extremeWingCfgWlanVlanCacheAgeout, extremeWingCfgWlanMaxFirewallSessions,
				extremeWingCfgWlanReauth, extremeWingCfgWlanPmfMode, extremeWingCfgWlanPmfSaQueryTimeout, extremeWingCfgWlanPmfSaQueryAttempts, extremeWingCfgWlanWpaWpa2Psk,
				extremeWingCfgWlanWpaWpa2ExcludeWpa2Tkip, extremeWingCfgWlanWpaWpa2KeyRotationUnicast, extremeWingCfgWlanWpaWpa2KeyRotationBroadcast, extremeWingCfgWlanWpaWpa2PmkCaching,
				extremeWingCfgWlanWpaWpa2OpmkCaching, extremeWingCfgWlanWpaWpa2Preauth, extremeWingCfgWlanWpaWpa2TkipCntrmeasHoldTime, extremeWingCfgWlanWep64TransmitKey,
				extremeWingCfgWlanWep128TransmitKey, extremeWingCfgWlanRadiusAssignedVlans, extremeWingCfgWlanRadiusDynamicAuthorization,
				extremeWingCfgWlanAccountingRadius, extremeWingCfgWlanMotoExtnMoveCmd, extremeWingCfgWlanMotoExtnSmartScan, extremeWingCfgWlanMotoExtnWmmLoadBalance,
				extremeWingCfgWlanMotoExtnSymbolLoadInfo, extremeWingCfgWlanClientLoadBal, extremeWingCfgWlanClientLoadBalSingleBandClients5ghz,
				extremeWingCfgWlanClientLoadBalSingleBandClients24ghz, extremeWingCfgWlanClientLoadBalMaxProbeReq24ghz, extremeWingCfgWlanClientLoadBalMaxProbeReq5ghz,
				extremeWingCfgWlanClientLoadBalProbeReqIntvl5ghz, extremeWingCfgWlanClientLoadBalProbeReqIntvl24ghz, extremeWingCfgWlanClientLoadBalBandDiscoveryIntvl,
				extremeWingCfgWlanClientLoadBalCapabilityAgeoutTime, extremeWingCfgWlanQosPolicy, extremeWingCfgWlanAaaPolicy, extremeWingCfgWlanCaptivePortal, extremeWingCfgWlanAssocAcl,
				extremeWingCfgWlanIpInAcl, extremeWingCfgWlanMacInAcl, extremeWingCfgWlanIpOutAcl, extremeWingCfgWlanMacOutAcl, extremeWingCfgWlanArpTrust, extremeWingCfgWlanDhcpTrust,
				extremeWingCfgWlanArpHeaderMismatchValidation, extremeWingCfgWlanServiceAllowHtOnly, extremeWingCfgWlanEnforceDhcp, extremeWingCfgWlanProxyArpMode,
				extremeWingCfgWlanBroadcastDhcpValidateOffer, extremeWingCfgWlanKerberosRealm, extremeWingCfgWlanKerberosTimeout, extremeWingCfgWlanKerberosPassword,
				extremeWingCfgWlanKerberosPrimaryServer, extremeWingCfgWlanKerberosPrimaryServerPort, extremeWingCfgWlanKerberosSecondaryServer, extremeWingCfgWlanKerberosSecondaryServerPort,
				extremeWingCfgWlanAcctSyslogEnable, extremeWingCfgWlanAcctSyslogHost, extremeWingCfgWlanAcctSyslogPort, extremeWingCfgWlanClientDenyLimitThresholdRate,
				extremeWingCfgWlanClientDenyLimitAction, extremeWingCfgWlanClientDenyLimitBlacklistAgeout, extremeWingCfgWlanQosName, extremeWingCfgWlanQosClassification,
				extremeWingCfgWlanQosNonWmmClassification, extremeWingCfgWlanQosMulticastMaskPrimary, extremeWingCfgWlanQosMulticastMaskSecondary, extremeWingCfgWlanQosMulticastMaskAc,
				extremeWingCfgWlanQosVoicePrioritization, extremeWingCfgWlanQosSvpPrioritization, extremeWingCfgWlanQosWmmPowerSave, extremeWingCfgWlanQosWmmQbssLoadElement,
				extremeWingCfgWlanQosWmmBestEffortTxopLimit, extremeWingCfgWlanQosWmmBestEffortAifsn, extremeWingCfgWlanQosWmmBestEffortCwMin, extremeWingCfgWlanQosWmmBestEffortCwMax,
				extremeWingCfgWlanQosWmmBackgroundTxopLimit, extremeWingCfgWlanQosWmmBackgroundAifsn, extremeWingCfgWlanQosWmmBackgroundCwMin, extremeWingCfgWlanQosWmmBackgroundCwMax,
				extremeWingCfgWlanQosWmmVideoTxopLimit, extremeWingCfgWlanQosWmmVideoAifsn, extremeWingCfgWlanQosWmmVideoCwMin, extremeWingCfgWlanQosWmmVideoCwMax,
				extremeWingCfgWlanQosWmmVoiceTxopLimit, extremeWingCfgWlanQosWmmVoiceAifsn, extremeWingCfgWlanQosWmmVoiceCwMin, extremeWingCfgWlanQosWmmVoiceCwMax,
				extremeWingCfgWlanQosWlanRlDownEnable, extremeWingCfgWlanQosWlanRlDownRate, extremeWingCfgWlanQosWlanRlDownBurstSize, extremeWingCfgWlanQosWlanRlDownThreshBackground,
				extremeWingCfgWlanQosWlanRlDownThreshBestEffort, extremeWingCfgWlanQosWlanRlDownThreshVoice, extremeWingCfgWlanQosWlanRlDownThreshVideo, extremeWingCfgWlanQosWlanRlUpEnable,
				extremeWingCfgWlanQosWlanRlUpRate, extremeWingCfgWlanQosWlanRlUpBurstSize, extremeWingCfgWlanQosWlanRlUpThreshBackground, extremeWingCfgWlanQosWlanRlUpThreshBestEffort,
				extremeWingCfgWlanQosWlanRlUpThreshVoice, extremeWingCfgWlanQosWlanRlUpThreshVideo, extremeWingCfgWlanQosMuRlDownEnable, extremeWingCfgWlanQosMuRlDownRate,
				extremeWingCfgWlanQosMuRlDownBurstSize, extremeWingCfgWlanQosMuRlDownThreshBackground, extremeWingCfgWlanQosMuRlDownThreshBestEffort,
				extremeWingCfgWlanQosMuRlDownThreshVoice, extremeWingCfgWlanQosMuRlDownThreshVideo, extremeWingCfgWlanQosMuRlUpEnable, extremeWingCfgWlanQosMuRlUpRate,
				extremeWingCfgWlanQosMuRlUpBurstSize, extremeWingCfgWlanQosMuRlUpThreshBackground, extremeWingCfgWlanQosMuRlUpThreshBestEffort, extremeWingCfgWlanQosMuRlUpThreshVoice,
				extremeWingCfgWlanQosMuRlUpThreshVideo, extremeWingCfgWlanQosQosTrustDscp, extremeWingCfgWlanQosQosTrustWmm, extremeWingCfgWlanQosMcastStreamAddr,
				extremeWingCfgWlanQosMcastStreamPriority, extremeWingCfgRadioQosName, extremeWingCfgRadioQosWmmBestEffortTxopLimit, extremeWingCfgRadioQosWmmBestEffortAifsn,
				extremeWingCfgRadioQosWmmBestEffortCwMin, extremeWingCfgRadioQosWmmBestEffortCwMax, extremeWingCfgRadioQosWmmBackgroundTxopLimit, extremeWingCfgRadioQosWmmBackgroundAifsn,
				extremeWingCfgRadioQosWmmBackgroundCwMin, extremeWingCfgRadioQosWmmBackgroundCwMax, extremeWingCfgRadioQosWmmVideoTxopLimit, extremeWingCfgRadioQosWmmVideoAifsn,
				extremeWingCfgRadioQosWmmVideoCwMin, extremeWingCfgRadioQosWmmVideoCwMax, extremeWingCfgRadioQosWmmVoiceTxopLimit, extremeWingCfgRadioQosWmmVoiceAifsn,
				extremeWingCfgRadioQosWmmVoiceCwMin, extremeWingCfgRadioQosWmmVoiceCwMax, extremeWingCfgRadioQosAdmCtrlFirewallDetectedTraffic, extremeWingCfgRadioQosAdmCtrlImplicitTspec,
				extremeWingCfgRadioQosAdmCtrlVoiceEnable, extremeWingCfgRadioQosAdmCtrlVoiceMaxClients, extremeWingCfgRadioQosAdmCtrlVoiceMaxRoamedClients,
				extremeWingCfgRadioQosAdmCtrlVoiceMaxAirtimePercent, extremeWingCfgRadioQosAdmCtrlVoiceReservedForRoamPercent, extremeWingCfgRadioQosAdmCtrlVideoEnable,
				extremeWingCfgRadioQosAdmCtrlVideoMaxClients, extremeWingCfgRadioQosAdmCtrlVideoMaxRoamedClients, extremeWingCfgRadioQosAdmCtrlVideoMaxAirtimePercent,
				extremeWingCfgRadioQosAdmCtrlVideoReservedForRoamPercent, extremeWingCfgRadioQosAdmCtrlBestEffortEnable, extremeWingCfgRadioQosAdmCtrlBestEffortMaxClients,
				extremeWingCfgRadioQosAdmCtrlBestEffortMaxRoamedClients, extremeWingCfgRadioQosAdmCtrlBestEffortMaxAirtimePercent,
				extremeWingCfgRadioQosAdmCtrlBestEffortReservedForRoamPercent, extremeWingCfgRadioQosAdmCtrlBackgroundEnable, extremeWingCfgRadioQosAdmCtrlBackgroundMaxClients,
				extremeWingCfgRadioQosAdmCtrlBackgroundMaxRoamedClients, extremeWingCfgRadioQosAdmCtrlBackgroundMaxAirtimePercent,
				extremeWingCfgRadioQosAdmCtrlBackgroundReservedForRoamPercent, extremeWingCfgRadioQosAccelMcastMaxStreams, extremeWingCfgRadioQosAccelMcastOverflowPolicy,
				extremeWingCfgRadioQosAccelMcastMaxClientStreams, extremeWingCfgRadioQosAccelMcastStreamThreshold, extremeWingCfgRadioQosAccelMcastClientTimeout, extremeWingCfgAaaName,
				extremeWingCfgAaaServerPoolingMode, extremeWingCfgAaaMacAddrFormat, extremeWingCfgAaaMacAddrCase, extremeWingCfgAaaMacAddrAttributes, extremeWingCfgAaaEapClientTimeout,
				extremeWingCfgAaaEapClientAttempts, extremeWingCfgAaaEapClientRetryFactor, extremeWingCfgAaaEapClientIdReqTimeout, extremeWingCfgAaaAuthProtocol, extremeWingCfgAaaAccountingType,
				extremeWingCfgAaaInterimAccountingInterval, extremeWingCfgAaaNacList, extremeWingCfgAssocAclName, extremeWingCfgSmartRfName, extremeWingCfgSmartRfEnable,
				extremeWingCfgSmartRfSensitivity, extremeWingCfgSmartRfAutoAssignSensor, extremeWingCfgSmartRfMinPowerA, extremeWingCfgSmartRfMaxPowerA, extremeWingCfgSmartRfMinPowerBg,
				extremeWingCfgSmartRfMaxPowerBg, extremeWingCfgSmartRfChannelWidthA, extremeWingCfgSmartRfChannelWidthBg, extremeWingCfgSmartRfGroupByArea, extremeWingCfgSmartRfGroupByFloor,
				extremeWingCfgSmartRfSmartOcsMonitoring, extremeWingCfgSmartRfOcsDurationA, extremeWingCfgSmartRfOcsDurationBg, extremeWingCfgSmartRfOcsFrequencyA,
				extremeWingCfgSmartRfOcsFrequencyBg, extremeWingCfgSmartRfOcsSampleCountA, extremeWingCfgSmartRfOcsSampleCountBg, extremeWingCfgSmartRfOcsExtendedScanFrequencyA,
				extremeWingCfgSmartRfOcsExtendedScanFrequencyBg, extremeWingCfgSmartRfOcsVoiceAwareA, extremeWingCfgSmartRfOcsVoiceAwareBg, extremeWingCfgSmartRfOcsPspAwareA,
				extremeWingCfgSmartRfOcsPspAwareBg, extremeWingCfgSmartRfInterferenceRecovery, extremeWingCfgSmartRfIrNoise, extremeWingCfgSmartRfIrInterference,
				extremeWingCfgSmartRfIrClientThreshold, extremeWingCfgSmartRfIrChannelSwitchDeltaA, extremeWingCfgSmartRfIrChannelSwitchDeltaBg, extremeWingCfgSmartRfNeighborRecovery,
				extremeWingCfgSmartRfNrPowerThresholdA, extremeWingCfgSmartRfNrPowerThresholdBg, extremeWingCfgSmartRfCoverageHoleRecovery, extremeWingCfgSmartRfChrIntervalA,
				extremeWingCfgSmartRfChrIntervalBg, extremeWingCfgSmartRfChrCovIntervalA, extremeWingCfgSmartRfChrCovIntervalBg, extremeWingCfgSmartRfChrSnrThresholdA,
				extremeWingCfgSmartRfChrSnrThresholdBg, extremeWingCfgSmartRfChrClientThresholdA, extremeWingCfgSmartRfChrClientThresholdBg, extremeWingCfgSmartRfChannelHoldTime,
				extremeWingCfgSmartRfPowerHoldTime, extremeWingCfgCaptPrtlName, extremeWingCfgCaptPrtlAccessType, extremeWingCfgCaptPrtlAccessTime, extremeWingCfgCaptPrtlCustomAuthInfo,
				extremeWingCfgCaptPrtlConnectionMode, extremeWingCfgCaptPrtlInactivityTimeout, extremeWingCfgCaptPrtlServer, extremeWingCfgCaptPrtlServerMode, extremeWingCfgCaptPrtlSimultaneousUsers,
				extremeWingCfgCaptPrtlTermsAgreement, extremeWingCfgCaptPrtlWebpageLocation, extremeWingCfgCaptPrtlAccountingRadius, extremeWingCfgCaptPrtlAaaPolicy,
				extremeWingCfgCaptPrtlDnsWhitelist, extremeWingCfgCaptPrtlAcctSyslogEnable, extremeWingCfgCaptPrtlAcctSyslogHost, extremeWingCfgCaptPrtlAcctSyslogPort, extremeWingCfgDnsWhitelistName, extremeWingCfgCaptPrtlWebpageAutoUpload,
				extremeWingCfgDnsWhitelistInstName, extremeWingCfgDnsWhitelistInstSuffix, extremeWingCfgIpAclName, extremeWingCfgDhcpSvrName, extremeWingCfgDhcpSvrIgnoreBootp, extremeWingCfgDhcpSvrPingInterval,
				extremeWingCfgDhcpSvrClassName, extremeWingCfgDhcpSvrClassMultipleUserClass, extremeWingCfgMacAclName, extremeWingCfgProfName, extremeWingCfgProfType, extremeWingCfgProfDomainLookup,
				extremeWingCfgProfDomainName, extremeWingCfgProfArpTimeout, extremeWingCfgProfApIpAddr, extremeWingCfgProfAutoConfUpdate, extremeWingCfgProfAutoFwUpdate,
				extremeWingCfgProfAutoupgradeCount, extremeWingCfgProfServiceWatchdog, extremeWingCfgProfRadiusServerPolicy, extremeWingCfgProfDhcpServerPolicy, extremeWingCfgProfManagementPolicy,
				extremeWingCfgProfFirewallPolicy, extremeWingCfgProfAdvancedWipsPolicy, extremeWingCfgProfRolePolicy, extremeWingCfgProfAdoptionPolicy, extremeWingCfgProfBridgingPolicy,
				extremeWingCfgProfEventSystemPolicy, extremeWingCfgProfRoutingPolicy, extremeWingCfgProfRfDomainMgrCapable, extremeWingCfgProfRfDomainMgrPriority, extremeWingCfgProfDhcpcSendHostname, 
				extremeWingCfgProfDhcpcPersistentLease, extremeWingCfgProfDnsServerForward, extremeWingCfgProfBridgeAgingTime, extremeWingCfgProfLogging, extremeWingCfgProfAggregationTime,
				extremeWingCfgProfConsole, extremeWingCfgProfBuffered, extremeWingCfgProfSyslog, extremeWingCfgProfFacility, extremeWingCfgProfEvents, extremeWingCfgProfEventsForward,
				extremeWingCfgProfRemoteLogging, extremeWingCfgProfPowerConfig3afOption, extremeWingCfgProfPowerConfig3atOption, extremeWingCfgProfPowerConfigMode, extremeWingCfgProfCriticalResourcePolicy, 
				extremeWingCfgProfControllerApSupported, extremeWingCfgProfControllerVlan, extremeWingCfgProfControllerGroup, extremeWingCfgProfPreferredControllerGroup, 
				extremeWingCfgProfIpRouting, extremeWingCfgProfIfRadioRfMode, extremeWingCfgProfIfRadioChannel, extremeWingCfgProfIfRadioPower, extremeWingCfgProfIfRadioPlacement,
				extremeWingCfgProfIfRadioBeaconInterval, extremeWingCfgProfIfRadioRtsThreshold, extremeWingCfgProfIfRadioOffChannelScan, extremeWingCfgProfIfRadioPreambleShort,
				extremeWingCfgProfIfRadioGuardInterval, extremeWingCfgProfIfRadioAmpduMode, extremeWingCfgProfIfRadioAmsduMode, extremeWingCfgProfIfRadioRifsMode, extremeWingCfgProfIfRadioAmpduMaxAggrSizeRx,
				extremeWingCfgProfIfRadioAmpduMaxAggrSizeTx, extremeWingCfgProfIfRadioAmpduMinSpacing, extremeWingCfgProfIfRadioAntennaMode, extremeWingCfgProfIfRadioNonUnicastForwarding,
				extremeWingCfgProfIfRadioDynamicChainSelection, extremeWingCfgProfIfRadioLockRfMode, extremeWingCfgProfIfRadioSnifferRedirHost, extremeWingCfgProfIfRadioSnifferRedirChannel,
				extremeWingCfgProfIfRadioMesh, extremeWingCfgProfIfRadioMeshLinks, extremeWingCfgProfIfRadioProbeResponseRetry, extremeWingCfgProfIfRadioProbeResponseRate,
				extremeWingCfgProfIfRadioMaxClients, extremeWingCfgProfIfRadioRadioTapMode, extremeWingCfgProfIfRadioWirelessClientPower, extremeWingCfgProfIfRadioLoadBalLfCount,
				extremeWingCfgProfIfRadioLoadBalLfThroughput, extremeWingCfgProfIfRadioLoadBalWmCount, extremeWingCfgProfIfRadioLoadBalWmTput, extremeWingCfgProfIfRadioAssocAcl,
				extremeWingCfgProfDot11WepSharedKeyAuth, extremeWingCfgProfDot11LegacyAutoUpdateAp650, extremeWingCfgProfDot11LegacyAutoUpdateImgAp7131, 	extremeWingCfgProfDot11LegacyAutoDowngrade,
				extremeWingCfgProfDot11NasIdentifier, extremeWingCfgProfDot11NasPortId, extremeWingCfgProfDot11NasIdentifier,
				extremeWingCfgProfDot11NasPortId, extremeWingCfgRfdName, extremeWingCfgRfdLocation, extremeWingCfgRfdContact, extremeWingCfgRfdTimezone, extremeWingCfgRfdCountryCode, extremeWingCfgRfdSmartRfPolicy,
				extremeWingCfgRfdWipsPolicyName, extremeWingCfgRfdNocUpdateInterval, extremeWingCfgRfdControlVlan, extremeWingCfgRfdSmartscanChanlistDynamic, extremeWingCfgRfdStatsUpdateInterval,
				extremeWingCfgDevMac, extremeWingCfgDevHostname, extremeWingCfgDevBuilding, extremeWingCfgDevFloor, extremeWingCfgDevNumRadios, extremeWingCfgDevProfileName, extremeWingCfgDevRfDomainName,
				extremeWingCfgDevHttpsTrustpoint, extremeWingCfgDevRadiusCaTrustpoint, extremeWingCfgDevRadiusServerTrustpoint, extremeWingCfgDevSshRsaKey, extremeWingCfgDevHasOverrides,
				extremeWingCfgDevDot11WepSharedKeyAuth, extremeWingCfgDevDot11LegacyAutoUpdateAp650, extremeWingCfgDevDot11LegacyAutoUpdateImgAp7131, extremeWingCfgDevDot11LegacyAutoDowngrade,
				extremeWingCfgDevDot11NasIdentifier, extremeWingCfgDevDot11NasPortId,	extremeWingCfgMgmtName, extremeWingCfgMgmtTelnetEnable, extremeWingCfgMgmtTelnetPort, extremeWingCfgMgmtHttpEnable,
				extremeWingCfgMgmtHttpsEnable, extremeWingCfgMgmtSshEnable, extremeWingCfgMgmtSshPort, extremeWingCfgMgmtSnmpV1Enable, extremeWingCfgMgmtSnmpV2Enable, extremeWingCfgMgmtSnmpV3Enable, extremeWingCfgMgmtSnmpTrapEnable,
				extremeWingCfgMgmtSnmpCommunityName, extremeWingCfgMgmtSnmpCommunityAccess, extremeWingCfgMgmtAdminUsername, extremeWingCfgMgmtAdminPassword, extremeWingCfgMgmtAdminRole,
				extremeWingCfgDhcpSvrOptionName, extremeWingCfgDhcpSvrOptionCode, extremeWingCfgDhcpSvrOptionType, extremeWingCfgDhcpSvrPoolName, extremeWingCfgDhcpSvrPoolNetwork,
				extremeWingCfgDhcpSvrPoolDomainName, extremeWingCfgDhcpSvrPoolNetbiosNodeType, extremeWingCfgDhcpSvrPoolBootfile, extremeWingCfgDhcpSvrPoolLeaseTime,
				extremeWingCfgDhcpSvrPoolBootpNextServer, extremeWingCfgDhcpSvrPoolUpdateDns, extremeWingCfgDhcpSvrPoolDdnsDomainName, extremeWingCfgDhcpSvrPoolDdnsTtl,
				extremeWingCfgDhcpSvrPoolDdnsMultiUserClass, extremeWingCfgProfIfEthSpeed, extremeWingCfgProfIfEthDuplex, extremeWingCfgProfIfEthSwitchportMode, extremeWingCfgProfIfEthSwitchportNativeVlan,
				extremeWingCfgProfIfEthSwitchportNativeVlanTagged, extremeWingCfgProfIfEthArpTrust, extremeWingCfgProfIfEthDhcpTrust, extremeWingCfgProfIfEthArpHeaderMismatchValidation,
				extremeWingCfgProfIfEthQosTrustDscp, extremeWingCfgProfIfEthQosTrust802dot1p, extremeWingCfgProfIfEthStaticChannelGroup, extremeWingCfgProfIfEthPoeSupported,
				extremeWingCfgProfIfEthPoePower, extremeWingCfgProfIfEthPoeLimit, extremeWingCfgProfIfEthPoePriority, extremeWingCfgProfIfEthDot1xSupported, extremeWingCfgProfIfEthDot1xEnable,
				extremeWingCfgProfIfEthDot1xUsername, extremeWingCfgProfIfEthDot1xPassword, extremeWingCfgProfIfEthCdpReceive, extremeWingCfgProfIfEthCdpTransmit, extremeWingCfgProfIfEthLldpReceive,
				extremeWingCfgProfIfEthLldpTransmit, extremeWingCfgProfIfEthPortChannelLoadBalance, extremeWingCfgProfIfVlanVlan, extremeWingCfgProfIfVlanDhcpcOptAll, extremeWingCfgProfIfVlanNatDirection,
				extremeWingCfgProfIfVlanCryptoMap, extremeWingCfgProfIfVlanDhcpRelayIncoming, extremeWingCfgProfIfVlanOspfAuth, extremeWingCfgProfIfVlanOspfAuthKey, extremeWingCfgProfIfVlanOspfNetworkType,
				extremeWingCfgProfIfSpanTreeLinkType, extremeWingCfgProfIfSpanTreePortfast, extremeWingCfgProfIfSpanTreeEdgeport, extremeWingCfgProfIfSpanTreeBpduguard,
				extremeWingCfgProfIfSpanTreeBpdufilter, extremeWingCfgProfIfSpanTreePortCiscoInterop, extremeWingCfgProfIfSpanTreeForceVersion, extremeWingCfgProfIfSpanTreeGuard,
				extremeWingCfgWipsName, extremeWingCfgWipsEnable, extremeWingCfgWipsHistoryThrottleDuration, extremeWingCfgWipsApDetection, extremeWingCfgWipsApDetectionAgeout,
				extremeWingCfgWipsApDetectionWaitTime, extremeWingCfgWipsDeviceCategorization, extremeWingCfgRfdWlanSsidOverrideWlan, extremeWingCfgRfdWlanSsidOverrideSsid,
				extremeWingCfgRfdWlanVlanOverrideWlan,	extremeWingCfgMgmtSnmpUsmUserName, extremeWingCfgMgmtSnmpUsmUserAuthentication, extremeWingCfgMgmtSnmpUsmUserEncryption,
				extremeWingCfgMgmtSnmpUsmUserPassword, extremeWingCfgProfRouteNetwork, extremeWingCfgProfRouteGateway, extremeWingCfgProfNtpSvrServerIp, extremeWingCfgProfNtpSvrAuthenkey,
				extremeWingCfgProfNtpSvrAutokey, extremeWingCfgProfNtpSvrKeyStr, extremeWingCfgProfNtpSvrPrefer, extremeWingCfgProfNtpSvrVersion, extremeWingCfgProfClstClstName,
				extremeWingCfgProfClstClstMemberVlan, extremeWingCfgProfClstClstMode,	extremeWingCfgProfClstClstMasterPriority, extremeWingCfgProfClstHandleStp, extremeWingCfgProfMintLevel1AreaId, extremeWingCfgProfMintSpfLatency,
				extremeWingCfgProfMintDisPriorityAdjustment, extremeWingCfgProfIfWwanApn, extremeWingCfgProfIfWwanAuth, 
				extremeWingCfgProfIfWwanUser, extremeWingCfgProfIfWwanPwd, extremeWingCfgProfIfWwanDefaultRoutePriority, extremeWingCfgProfCrlUpdateTrustpoint, 
				extremeWingCfgProfCrlUpdateUrl, extremeWingCfgProfCrlUpdateInterval, extremeWingCfgProfNatPoolName, extremeWingCfgProfControllerHostHost, extremeWingCfgProfControllerHostPool,
				extremeWingCfgProfControllerHostLevel, extremeWingCfgMacAclRulePrecedence, extremeWingCfgMacAclRuleAllow, extremeWingCfgMacAclRulePriorityField, extremeWingCfgMacAclRuleMarkDscp,
				extremeWingCfgMacAclRuleMark8021p, extremeWingCfgMacAclRuleDescription, extremeWingCfgMacAclRuleSmac, extremeWingCfgMacAclRuleSmacMask, extremeWingCfgMacAclRuleDmac, extremeWingCfgMacAclRuleDmacMask,
				extremeWingCfgMacAclRuleMatchVlan, extremeWingCfgMacAclRuleMatchDot1p, extremeWingCfgMacAclRuleMatchType, extremeWingCfgWlanVlanId, extremeWingCfgWlanVlanLimit, extremeWingCfgAaaAuthSrvrIdx, 
				extremeWingCfgAaaAuthSrvrType, extremeWingCfgAaaAuthSrvrHost, extremeWingCfgAaaAuthSrvrSecret, extremeWingCfgAaaAuthSrvrPort, extremeWingCfgAaaAuthSrvrTimeout, extremeWingCfgAaaAuthSrvrAttempts, 
				extremeWingCfgAaaAuthSrvrProxyMode, extremeWingCfgAaaAuthSrvrNaiRouting, extremeWingCfgAaaAuthSrvrRealmType, extremeWingCfgAaaAuthSrvrRealm, extremeWingCfgAaaAuthSrvrStripRealm, 
				extremeWingCfgAaaAuthSrvrRetryTimeoutFactor, extremeWingCfgAaaAuthSrvrNacEnable, extremeWingCfgAaaAuthSrvrDscp, extremeWingCfgAaaAcctSrvrIdx, extremeWingCfgAaaAcctSrvrType, 
				extremeWingCfgAaaAcctSrvrHost, extremeWingCfgAaaAcctSrvrSecret, extremeWingCfgAaaAcctSrvrPort, extremeWingCfgAaaAcctSrvrTimeout, extremeWingCfgAaaAcctSrvrAttempts, extremeWingCfgAaaAcctSrvrProxyMode, 
				extremeWingCfgAaaAcctSrvrNaiRouting, extremeWingCfgAaaAcctSrvrRealmType, extremeWingCfgAaaAcctSrvrRealm, extremeWingCfgAaaAcctSrvrStripRealm, extremeWingCfgAaaAcctSrvrRetryTimeoutFactor, 
				extremeWingCfgAaaAcctSrvrDscp, extremeWingCfgAssocAclRulePrecedence, extremeWingCfgAssocAclRulePermit, extremeWingCfgAssocAclRuleMac0, extremeWingCfgAssocAclRuleMac1, 
				extremeWingCfgIpAclRulePrecedence, extremeWingCfgIpAclRuleAllow, extremeWingCfgIpAclRulePriorityField, extremeWingCfgIpAclRuleMarkDscp, extremeWingCfgIpAclRuleMark8021p, 
				extremeWingCfgIpAclRuleDescription, extremeWingCfgIpAclRuleProtocol, extremeWingCfgIpAclRuleSip, extremeWingCfgIpAclRuleDip, extremeWingCfgRfdStatsWindowIdx, 
				extremeWingCfgRfdStatsWindowSampleInterval, extremeWingCfgRfdStatsWindowWindowSize, extremeWingCfgProfBridgeVlanId, extremeWingCfgProfBridgeVlanDesc, extremeWingCfgProfBridgeVlanEdgeVlan, 
				extremeWingCfgProfBridgeVlanBridgingMode, extremeWingCfgProfBridgeVlanIpArpTrust, extremeWingCfgProfBridgeVlanIpDhcpTrust, extremeWingCfgProfBridgeVlanTunnelMacOutAcl, 
				extremeWingCfgProfBridgeVlanTunnelIpOutAcl, extremeWingCfgRfdSensorSvrIdx, extremeWingCfgRfdSensorSvrIp, extremeWingCfgRfdSensorSvrPort, extremeWingCfgDevIfName, extremeWingCfgDevIfDescription,
				extremeWingCfgDevIfType, extremeWingCfgDevIfShutdown, extremeWingCfgDevIfIpInAcl, extremeWingCfgDevIfMacInAcl, extremeWingCfgDevIfRadioRfMode, extremeWingCfgDevIfRadioChannel,
				extremeWingCfgDevIfRadioPower, extremeWingCfgDevIfRadioPlacement, extremeWingCfgDevIfRadioBeaconInterval, extremeWingCfgDevIfRadioRtsThreshold, extremeWingCfgDevIfRadioOffChannelScan,
				extremeWingCfgDevIfRadioPreambleShort, extremeWingCfgDevIfRadioGuardInterval, extremeWingCfgDevIfRadioAmpduMode, extremeWingCfgDevIfRadioAmsduMode, extremeWingCfgDevIfRadioRifsMode,
				extremeWingCfgDevIfRadioAmpduMaxAggrSizeRx, extremeWingCfgDevIfRadioAmpduMaxAggrSizeTx, extremeWingCfgDevIfRadioAmpduMinSpacing, extremeWingCfgDevIfRadioAntennaMode,
				extremeWingCfgDevIfRadioNonUnicastForwarding, extremeWingCfgDevIfRadioDynamicChainSelection, extremeWingCfgDevIfRadioLockRfMode, extremeWingCfgDevIfRadioSnifferRedirHost,
				extremeWingCfgDevIfRadioSnifferRedirChannel, extremeWingCfgDevIfRadioMesh, extremeWingCfgDevIfRadioMeshLinks, extremeWingCfgDevIfRadioProbeResponseRetry,
				extremeWingCfgDevIfRadioProbeResponseRate, extremeWingCfgDevIfRadioMaxClients, extremeWingCfgDevIfRadioRadioTapMode, extremeWingCfgDevIfRadioWirelessClientPower,
				extremeWingCfgDevIfRadioLoadBalLfCount, extremeWingCfgDevIfRadioLoadBalLfThroughput, extremeWingCfgDevIfRadioLoadBalWmCount, extremeWingCfgDevIfRadioLoadBalWmTput,
				extremeWingCfgDevIfRadioAssocAcl, extremeWingCfgDevIfRadioQosPolicy, extremeWingCfgDevWlanSsidOverrideWlan, extremeWingCfgDevWlanSsidOverrideSsid, extremeWingCfgDevWlanVlanOverrideWlan,
				extremeWingCfgDevIfEthSpeed, extremeWingCfgDevIfEthDuplex, extremeWingCfgDevIfEthSwitchportMode, extremeWingCfgDevIfEthSwitchportNativeVlan, 
				extremeWingCfgDevIfEthSwitchportNativeVlanTagged, extremeWingCfgDevIfEthArpTrust, extremeWingCfgDevIfEthDhcpTrust, extremeWingCfgDevIfEthArpHeaderMismatchValidation, 
				extremeWingCfgDevIfEthQosTrustDscp, extremeWingCfgDevIfEthQosTrust802dot1p, extremeWingCfgDevIfEthStaticChannelGroup, extremeWingCfgDevIfEthPoeSupported, extremeWingCfgDevIfEthPoePower, 
				extremeWingCfgDevIfEthPoeLimit, extremeWingCfgDevIfEthPoePriority, extremeWingCfgDevIfEthDot1xSupported, extremeWingCfgDevIfEthDot1xEnable, extremeWingCfgDevIfEthDot1xUsername, 
				extremeWingCfgDevIfEthDot1xPassword, extremeWingCfgDevIfEthCdpReceive, extremeWingCfgDevIfEthCdpTransmit, extremeWingCfgDevIfEthLldpReceive, extremeWingCfgDevIfEthLldpTransmit, 
				extremeWingCfgDevIfEthPortChannelLoadBalance, extremeWingCfgDevIfVlanVlan, extremeWingCfgDevIfVlanDhcpcOptAll, extremeWingCfgDevIfVlanNatDirection, extremeWingCfgDevIfVlanCryptoMap, 
				extremeWingCfgDevIfVlanDhcpRelayIncoming, extremeWingCfgDevIfSpanTreeLinkType, extremeWingCfgDevIfSpanTreePortfast, extremeWingCfgDevIfSpanTreeEdgeport, 
				extremeWingCfgDevIfSpanTreeBpduguard, extremeWingCfgDevIfSpanTreeBpdufilter, extremeWingCfgDevIfSpanTreePortCiscoInterop, extremeWingCfgDevIfSpanTreeForceVersion, 
				extremeWingCfgDevIfSpanTreeGuard, extremeWingCfgProfVpnLifetimeSeconds, extremeWingCfgProfVpnLifetimeKb, extremeWingCfgProfVpnIkev1GlobalDpdKeepalive, 
				extremeWingCfgProfVpnIkev1GlobalDpdRetries, extremeWingCfgProfVpnIkev1GlobalNatKeepalive, extremeWingCfgProfVpnIkev2GlobalDpdKeepalive, extremeWingCfgProfVpnIkev2GlobalDpdRetries, 
				extremeWingCfgProfVpnIkev2GlobalNatKeepalive, extremeWingCfgProfVpnCookieChallengeThreshold, extremeWingCfgProfVpnMaxInNegotiationSa, extremeWingCfgProfVpnDfBit,
				extremeWingCfgProfVpnIkev1Name, extremeWingCfgProfVpnIkev1Mode, extremeWingCfgProfVpnIkev1IsakmpLifetime, extremeWingCfgProfVpnIkev1DpdKeepalive, extremeWingCfgProfVpnIkev1DpdRetries, 
				extremeWingCfgProfVpnIkev1IsakmpHash, extremeWingCfgProfVpnIkev2Name, 
				extremeWingCfgProfVpnIkev2IsakmpLifetime, extremeWingCfgProfVpnIkev2DpdKeepalive, 
				extremeWingCfgProfVpnIkev2IsakmpHash, extremeWingCfgProfVpnIkev1PeerName, 
				extremeWingCfgProfVpnIkev1PeerIpType, extremeWingCfgProfVpnIkev1PeerIpValue, 
				extremeWingCfgProfVpnIkev1PeerLocalidType, extremeWingCfgProfVpnIkev1PeerLocalidValue, extremeWingCfgProfVpnIkev1PeerRemoteidType, extremeWingCfgProfVpnIkev1PeerRemoteidValue, 
				extremeWingCfgProfVpnIkev1PeerIkev1Policy, extremeWingCfgProfVpnIkev2PeerName, extremeWingCfgProfVpnIkev2PeerIpType, extremeWingCfgProfVpnIkev2PeerIpValue, 
				extremeWingCfgProfVpnIkev2PeerLocalidType, extremeWingCfgProfVpnIkev2PeerLocalidValue, extremeWingCfgProfVpnIkev2PeerRemoteidType, extremeWingCfgProfVpnIkev2PeerRemoteidValue, 
				extremeWingCfgProfVpnIkev2PeerIkev2Policy, extremeWingCfgProfVpnTransformName, extremeWingCfgProfVpnTransformCipherAlgo,
				extremeWingCfgProfVpnTransformAuthAlgo, extremeWingCfgProfVpnTransformMode, extremeWingCfgProfVpnCryptoName, 
				extremeWingCfgProfNtpSvrServerIp, extremeWingCfgProfBridgeVlanIgsIpIgsQuerierMaxResponseTime, 
				extremeWingCfgProfVrrpVersion, extremeWingCfgProfVrrpGroupVirtualRouterId, extremeWingCfgProfVrrpGroupDescription, extremeWingCfgProfVrrpGroupPriority, 
				extremeWingCfgProfVrrpGroupAdvertisementIntervalV2, extremeWingCfgProfVrrpGroupAdvertisementIntervalV3, extremeWingCfgProfVrrpGroupPreempt, extremeWingCfgProfVrrpGroupPreemptDelay, 
				extremeWingCfgProfVrrpGroupCrmAction, extremeWingCfgProfVrrpGroupDeltaPriority, extremeWingCfgProfVrrpGroupInterface, extremeWingCfgProfVrrpGroupSyncGroup, extremeWingCfgDevVrrpVersion, 
				extremeWingCfgDevVrrpGroupVirtualRouterId, extremeWingCfgDevVrrpGroupDescription, extremeWingCfgDevVrrpGroupPriority, extremeWingCfgDevVrrpGroupAdvertisementIntervalV2, 
				extremeWingCfgDevVrrpGroupAdvertisementIntervalV3, extremeWingCfgDevVrrpGroupPreempt, extremeWingCfgDevVrrpGroupPreemptDelay, extremeWingCfgDevVrrpGroupCrmAction, 
				extremeWingCfgDevVrrpGroupDeltaPriority, extremeWingCfgDevVrrpGroupInterface, extremeWingCfgDevVrrpGroupSyncGroup, extremeWingCfgProfDynRouteOspfEnabled, 
				extremeWingCfgProfDynRouteOspfRouterId, extremeWingCfgProfDynRouteOspfAutoCost, extremeWingCfgProfDynRouteOspfPassiveAll, 
				extremeWingCfgProfIfVlanOspfOspfAuthentication, extremeWingCfgProfIfVlanOspfOspfAuthKey, extremeWingCfgProfIfVlanOspfOspfPriority, 
				extremeWingCfgProfIfVlanOspfOspfCost, extremeWingCfgDevIfVlanOspfOspfAuthentication, extremeWingCfgDevIfVlanOspfOspfAuthKey, extremeWingCfgDevIfVlanOspfOspfPriority, 
				extremeWingCfgDevIfVlanOspfOspfCost, extremeWingCfgDevIfPppoeAuthType, extremeWingCfgDevIfPppoeIdleTime, extremeWingCfgDevIfPppoeKeepalive, extremeWingCfgDevIfPppoeUsername, 
				extremeWingCfgDevIfPppoePassword, extremeWingCfgDevIfPppoeService, extremeWingCfgDevIfPppoeLocalnetVlan, extremeWingCfgDevIfPppoeMtu, extremeWingCfgProfIfPppoeAuthType, 
				extremeWingCfgProfIfPppoeIdleTime, extremeWingCfgProfIfPppoeKeepalive, extremeWingCfgProfIfPppoeUsername, extremeWingCfgProfIfPppoePassword, extremeWingCfgProfIfPppoeService, 
				extremeWingCfgProfIfPppoeLocalnetVlan, extremeWingCfgProfIfPppoeMtu, extremeWingCfgDevBridgeVlanId, extremeWingCfgDevBridgeVlanDescription, extremeWingCfgDevBridgeVlanEdgeVlan, 
				extremeWingCfgDevBridgeVlanBridgingMode, extremeWingCfgDevBridgeVlanIpArpTrust, extremeWingCfgDevBridgeVlanIpDhcpTrust, extremeWingCfgDevBridgeVlanTunnelMacOutAcl, 
				extremeWingCfgDevBridgeVlanTunnelIpOutAcl, extremeWingCfgDevBridgeVlanIgsIpIgs, extremeWingCfgDevBridgeVlanIgsIpIgsQuerier, 
				extremeWingCfgDevBridgeVlanIgsIpIgsQuerierMaxResponseTime, extremeWingCfgDevBridgeVlanIgsIpIgsQuerierVersion, extremeWingCfgDevBridgeVlanIgsIpIgsQuerierAddress, 
				extremeWingCfgDevBridgeVlanIgsIpIgsOtherQuerierTimerExpiry, extremeWingCfgDevBridgeVlanIgsIpIgsForwardUnknownMcast, extremeWingCfgDevBridgeVlanIgsIpIgsMrouterLearnPimDvmrp, 
				extremeWingCfgRouteName, extremeWingCfgRouteLogging, extremeWingCfgRouteLocalPbr, extremeWingCfgRouteMapPrecedence, extremeWingCfgRouteMapMatchClauseAcl, extremeWingCfgRouteMapMatchClauseDscp, 
				extremeWingCfgRouteMapMatchClauseWlan, extremeWingCfgRouteMapRolePolicy, extremeWingCfgRouteMapUserRole, extremeWingCfgRouteMapMatchClauseIncomingInterface, extremeWingCfgRouteMapNextHop1, 
				extremeWingCfgRouteMapNextHop2, extremeWingCfgRouteMapSetClauseDefaultNextHop, extremeWingCfgRouteUseCrm, 
				extremeWingCfgRouteMapSetClauseFallback, extremeWingCfgRouteMapSetClauseMarkDscp, extremeWingCfgProfBridgeVlanIgsIpIgs, extremeWingCfgProfBridgeVlanIgsIpIgsQuerier, 
				extremeWingCfgProfBridgeVlanIgsIpIgsQuerierMaxResponseTime, extremeWingCfgProfBridgeVlanIgsIpIgsQuerierVersion, extremeWingCfgProfBridgeVlanIgsIpIgsQuerierAddress, 
				extremeWingCfgProfBridgeVlanIgsIpIgsOtherQuerierTimerExpiry, extremeWingCfgProfBridgeVlanIgsIpIgsForwardUnknownMcast, extremeWingCfgProfBridgeVlanIgsIpIgsMrouterLearnPimDvmrp, 
				extremeWingCfgProfIgsIpIgmpSnooping, extremeWingCfgProfIgsIpIgmpSnoopingForwardUnknownMulticast, extremeWingCfgProfIgsIpIgmpSnoopingQuerier, 
				extremeWingCfgProfIgsIpIgmpSnoopingQuerierAddress, extremeWingCfgProfIgsIpIgmpSnoopingQuerierMaxResponseTime, extremeWingCfgProfIgsIpIgmpSnoopingQuerierOtherQuerierTimerExpiry, 
				extremeWingCfgProfIgsIpIgmpSnoopingQuerierVersion, extremeWingCfgProfIgsIpIgmpSnoopingQuerierQueryInterval, extremeWingCfgProfIgsIpIgmpSnoopingQuerierRobustnessVariable, 
				extremeWingCfgDevIgsIpIgmpSnooping, extremeWingCfgDevIgsIpIgmpSnoopingForwardUnknownMulticast, extremeWingCfgDevIgsIpIgmpSnoopingQuerier, 
				extremeWingCfgDevIgsIpIgmpSnoopingQuerierAddress, extremeWingCfgDevIgsIpIgmpSnoopingQuerierMaxResponseTime, extremeWingCfgDevIgsIpIgmpSnoopingQuerierOtherQuerierTimerExpiry, 
				extremeWingCfgDevIgsIpIgmpSnoopingQuerierVersion, extremeWingCfgDevIgsIpIgmpSnoopingQuerierQueryInterval, extremeWingCfgDevIgsIpIgmpSnoopingQuerierRobustnessVariable, 
				extremeWingCfgDevVpnLifetimeSeconds, extremeWingCfgDevVpnLifetimeKb, extremeWingCfgDevVpnIkev1GlobalDpdKeepalive, extremeWingCfgDevVpnIkev1GlobalDpdRetries, 
				extremeWingCfgDevVpnIkev1GlobalNatKeepalive, extremeWingCfgDevVpnIkev2GlobalDpdKeepalive, extremeWingCfgDevVpnIkev2GlobalDpdRetries, extremeWingCfgDevVpnIkev2GlobalNatKeepalive, 
				extremeWingCfgDevVpnCookieChallengeThreshold, extremeWingCfgDevVpnMaxInNegotiationSa, extremeWingCfgDevVpnIkev1Name, extremeWingCfgDevVpnIkev1Mode, extremeWingCfgDevVpnIkev1IsakmpLifetime, 
				extremeWingCfgDevVpnIkev1DpdKeepalive, extremeWingCfgDevVpnIkev1DpdRetries, extremeWingCfgDevVpnIkev2Name, extremeWingCfgDevVpnIkev2IkeLifetime, extremeWingCfgDevVpnIkev2DpdKeepalive, 
				extremeWingCfgProfVpnIkev1PeerName, extremeWingCfgProfVpnIkev1PeerIpType, extremeWingCfgProfVpnIkev1PeerIpValue, extremeWingCfgProfVpnIkev1PeerAuthType, 
				extremeWingCfgProfVpnIkev1PeerAuthKey, extremeWingCfgProfVpnIkev1PeerLocalidType, extremeWingCfgProfVpnIkev1PeerLocalidValue, extremeWingCfgProfVpnIkev1PeerRemoteidType, 
				extremeWingCfgProfVpnIkev1PeerRemoteidValue, extremeWingCfgProfVpnIkev1PeerIkev1Policy, extremeWingCfgProfVpnIkev2PeerName, extremeWingCfgProfVpnIkev2PeerIpType, 
				extremeWingCfgProfVpnIkev2PeerIpValue, extremeWingCfgProfVpnIkev2PeerLocalAuthType, extremeWingCfgProfVpnIkev2PeerLocalAuthKey, extremeWingCfgProfVpnIkev2PeerRemoteAuthType, 
				extremeWingCfgProfVpnIkev2PeerRemoteAuthKey, extremeWingCfgProfVpnIkev2PeerLocalidType, extremeWingCfgProfVpnIkev2PeerLocalidValue, extremeWingCfgProfVpnIkev2PeerRemoteidType, 
				extremeWingCfgProfVpnIkev2PeerRemoteidValue, extremeWingCfgProfVpnIkev2PeerIkev2Policy, extremeWingCfgDevVpnIkev1PeerName, extremeWingCfgDevVpnIkev1PeerIpType, 
				extremeWingCfgDevVpnIkev1PeerIpValue, extremeWingCfgDevVpnIkev1PeerAuthType, extremeWingCfgDevVpnIkev1PeerAuthKey, extremeWingCfgDevVpnIkev1PeerLocalidType, 
				extremeWingCfgDevVpnIkev1PeerLocalidValue, extremeWingCfgDevVpnIkev1PeerRemoteidType, extremeWingCfgDevVpnIkev1PeerRemoteidValue, extremeWingCfgDevVpnIkev1PeerIkev1Policy, 
				extremeWingCfgDevVpnIkev2PeerName, extremeWingCfgDevVpnIkev2PeerIpType, extremeWingCfgDevVpnIkev2PeerIpValue, extremeWingCfgDevVpnIkev2PeerLocalAuthType, 
				extremeWingCfgDevVpnIkev2PeerLocalAuthKey, extremeWingCfgDevVpnIkev2PeerRemoteAuthType, extremeWingCfgDevVpnIkev2PeerRemoteAuthKey, extremeWingCfgDevVpnIkev2PeerLocalidType, 
				extremeWingCfgDevVpnIkev2PeerLocalidValue, extremeWingCfgDevVpnIkev2PeerRemoteidType, extremeWingCfgDevVpnIkev2PeerRemoteidValue, extremeWingCfgDevVpnIkev2PeerIkev2Policy,
				extremeWingCfgVersionVal, extremeWingCfgPasswordEncVal, extremeWingCfgPasswordEncSetOldPassphrase, extremeWingCfgPasswordEncSetNewPassphrase, extremeWingCfgDevDynRouteOspfEnabled, 
				extremeWingCfgDevDynRouteOspfRouterId, extremeWingCfgDevDynRouteOspfAutoCost, extremeWingCfgDevDynRouteOspfPassiveAll, 
				extremeWingCfgDevVpnTransformName, extremeWingCfgDevVpnTransformCipherAlgo, extremeWingCfgDevVpnTransformAuthAlgo, 
				extremeWingCfgDevVpnTransformMode, extremeWingCfgDevVpnCryptoName, extremeWingCfgProfVpnIkev1RemoteAuthMethod, extremeWingCfgProfVpnIkev1RemoteAaaPolicy, 
				extremeWingCfgProfVpnIkev1RemoteIpLocalPool, extremeWingCfgProfVpnIkev1RemoteWinsServerType, extremeWingCfgProfVpnIkev1RemoteWinsServerIp, 
				extremeWingCfgProfVpnIkev1RemoteNameServerType, extremeWingCfgProfVpnIkev1RemoteNameServerIp, extremeWingCfgProfVpnIkev2RemoteAuthMethod, 
				extremeWingCfgProfVpnIkev2RemoteAaaPolicy, extremeWingCfgProfVpnIkev2RemoteIpLocalPool, extremeWingCfgProfVpnIkev2RemoteDhcpServerType, 
				extremeWingCfgProfVpnIkev2RemoteDhcpServer, extremeWingCfgProfVpnIkev2RemoteDhcpServerGiaddr, extremeWingCfgProfVpnIkev2RemoteNetmask, extremeWingCfgProfVpnIkev2RemoteWinsServerType, 
				extremeWingCfgProfVpnIkev2RemoteWinsServerIp, extremeWingCfgProfVpnIkev2RemoteNameServerType, extremeWingCfgProfVpnIkev2RemoteNameServerIp, 
				extremeWingCfgDevVpnIkev1RemoteAuthMethod, extremeWingCfgDevVpnIkev1RemoteAaaPolicy, extremeWingCfgDevVpnIkev1RemoteIpLocalPool, extremeWingCfgDevVpnIkev1RemoteWinsServerType, 
				extremeWingCfgDevVpnIkev1RemoteWinsServerIp, extremeWingCfgDevVpnIkev1RemoteNameServerType, extremeWingCfgDevVpnIkev1RemoteNameServerIp, extremeWingCfgDevVpnIkev2RemoteAuthMethod, 
				extremeWingCfgDevVpnIkev2RemoteAaaPolicy, extremeWingCfgDevVpnIkev2RemoteIpLocalPool, extremeWingCfgDevVpnIkev2RemoteDhcpServerType, extremeWingCfgDevVpnIkev2RemoteDhcpServer, 
				extremeWingCfgDevVpnIkev2RemoteDhcpServerGiaddr, extremeWingCfgDevVpnIkev2RemoteNetmask, extremeWingCfgDevVpnIkev2RemoteWinsServerType, extremeWingCfgDevVpnIkev2RemoteWinsServerIp, 
				extremeWingCfgDevVpnIkev2RemoteNameServerType, extremeWingCfgDevVpnIkev2RemoteNameServerIp, extremeWingStatsRfdWlRadioStatDetailTxBytes, extremeWingStatsRfdWlRadioStatDetailRxBytes,
				extremeWingStatsDevSysInfoFreeMem, extremeWingStatsDevSysInfoTotalMem, extremeWingStatsDevSysInfoFreeRamCurrent, extremeWingStatsDevSysInfoFreeRamLimit, extremeWingStatsDevSysInfoFdMax,
				extremeWingStatsDevSysInfoFdCurrent, extremeWingStatsDevSysInfoFdLimit, extremeWingStatsDevSysInfoLoadLimitS0, extremeWingStatsDevSysInfoLoadLimitS1, extremeWingStatsDevSysInfoLoadLimitS2,
				extremeWingStatsDevSysInfoBufferCurrent0, extremeWingStatsDevSysInfoBufferCurrent1, extremeWingStatsDevSysInfoBufferCurrent2, extremeWingStatsDevSysInfoBufferCurrent3,
				extremeWingStatsDevSysInfoBufferCurrent4, extremeWingStatsDevSysInfoBufferCurrent5, extremeWingStatsDevSysInfoBufferCurrent6, extremeWingStatsDevSysInfoBufferCurrent7,
				extremeWingStatsDevSysInfoBufferCurrent8, extremeWingStatsDevSysInfoBufferCurrent9, extremeWingStatsDevSysInfoBufferCurrent10, extremeWingStatsDevSysInfoBufferCurrent11,
				extremeWingStatsDevSysInfoBufferCurrent12, extremeWingStatsDevSysInfoBufferTotal0, extremeWingStatsDevSysInfoBufferTotal1, extremeWingStatsDevSysInfoBufferTotal2,
				extremeWingStatsDevSysInfoBufferTotal3, extremeWingStatsDevSysInfoBufferTotal4, extremeWingStatsDevSysInfoBufferTotal5, extremeWingStatsDevSysInfoBufferTotal6,
				extremeWingStatsDevSysInfoBufferTotal7, extremeWingStatsDevSysInfoBufferTotal8, extremeWingStatsDevSysInfoBufferTotal9, extremeWingStatsDevSysInfoBufferTotal10,
				extremeWingStatsDevSysInfoBufferTotal11, extremeWingStatsDevSysInfoBufferTotal12, extremeWingStatsDevSysProductName, extremeWingStatsDevSysSerialNo, extremeWingStatsDevSysVersion,
				extremeWingStatsDevSysPrimaryVersion, extremeWingStatsDevSysSecondaryVersion, extremeWingStatsDevSysPrimaryBuildDate, extremeWingStatsDevSysSecondaryBuildDate,
				extremeWingStatsDevSysPrimaryInstallDate, extremeWingStatsDevSysSecondaryInstallDate, extremeWingStatsDevSysBootPartition, extremeWingStatsDevSysNextBoot, extremeWingStatsDevSysIsFallback,
				extremeWingStatsDevSysImgFallback, extremeWingStatsDevSysUptime, extremeWingStatsDevSysCpu, extremeWingStatsDevSysRam, extremeWingStatsDevSysClock, extremeWingStatsDevSysUpgradeStatus,
				extremeWingStatsDevSysUpgradeTime, extremeWingStatsDevSysPoeFwVersion, extremeWingStatsDevSysFpgaVersion, extremeWingStatsDevSysModelNumber, extremeWingStatsDevIfName, extremeWingStatsDevIfIndex,
				extremeWingStatsDevIfHwType, extremeWingStatsDevIfMode, extremeWingStatsDevIfMac, extremeWingStatsDevIfStatusAdmin, extremeWingStatsDevIfMtu, extremeWingStatsDevIfGoodOctetsRcv, extremeWingStatsDevIfGoodPktsRcv,
				extremeWingStatsDevIfDropEvents, extremeWingStatsDevIfUcPktsRcv, extremeWingStatsDevIfBrdcPktsRcv, extremeWingStatsDevIfMcPktsRcv, extremeWingStatsDevIfBadPktsRcv, extremeWingStatsDevIfUndersizePkts,
				extremeWingStatsDevIfOversizePkts, extremeWingStatsDevIfBadCrc, extremeWingStatsDevIfMacRcvError, extremeWingStatsDevIfFragmentsPkts, extremeWingStatsDevIfJabberPkts, extremeWingStatsDevIfGoodOctetsSent,
				extremeWingStatsDevIfGoodPktsSent, extremeWingStatsDevIfMacTransmitErr, extremeWingStatsDevIfUcPktsSent, extremeWingStatsDevIfBrdcPktsSent, extremeWingStatsDevIfMcPktsSent,
				extremeWingStatsDevIfLateCollisions, extremeWingStatsDevIfExcessiveCollisions, extremeWingStatsDevIfCollisions, extremeWingStatsDevIfMetric, extremeWingStatsDevIfRxFifoErrors,
				extremeWingStatsDevIfRxOverErrors, extremeWingStatsDevIfTxWindowErrors, extremeWingStatsDevIfTxFifoErrors, extremeWingStatsDevIfTxAbortedErrors, extremeWingStatsDevIfTxCarrierErrors,
				extremeWingStatsDevIfTxDropped, extremeWingStatsDevIfRxLengthErrors, extremeWingStatsDevIfRxMissedErrors, extremeWingStatsDevIfRxFrameErrors, extremeWingStatsDevIfTxErrors,
				extremeWingStatsDevIfTxHeartbeatErrors, extremeWingStatsRfdWlClientStatTxBytes, extremeWingStatsRfdWlClientStatRxBytes, extremeWingStatsRfdWlClientStatDetailTxBytes,
				extremeWingStatsRfdWlClientStatDetailRxBytes, extremeWingStatsRfdWlClientStatDetailRawTxBytes, extremeWingStatsRfdWlClientStatDetailRawRxBytes,
				extremeWingStatsRfdWlClientStatDetailRawTotalBytes, extremeWingStatsRfdWlClientStatDetailTxBcmcPkts, extremeWingStatsRfdWlClientStatDetailRxBcmcPkts,
				extremeWingStatsRfdWlClientStatDetailTotalBcmcPkts, extremeWingStatsRfdWlClientStatDetailTxMgmtPkts, extremeWingStatsRfdWlClientStatDetailRxMgmtPkts,
				extremeWingStatsRfdWlClientStatDetailTotalMgmtPkts, extremeWingStatsRfdWlClientStatDetailTxRetries, extremeWingStatsRfdWlClientStatDetailTotalBytes,
				extremeWingStatsRfdWlRadioStatTxBytes, extremeWingStatsRfdWlRadioStatRxBytes, extremeWingStatsRfdWlRadioStatDetailRawTxBytes, extremeWingStatsRfdWlRadioStatDetailRawRxBytes,
				extremeWingStatsRfdWlRadioStatDetailRawTotalBytes, extremeWingStatsRfdWlRadioStatDetailTxBcmcPkts, extremeWingStatsRfdWlRadioStatDetailRxBcmcPkts,
				extremeWingStatsRfdWlRadioStatDetailTotalBcmcPkts, extremeWingStatsRfdWlRadioStatDetailTxMgmtPkts, extremeWingStatsRfdWlRadioStatDetailRxMgmtPkts,
				extremeWingStatsRfdWlRadioStatDetailTotalMgmtPkts, extremeWingStatsRfdWlRadioStatDetailTxRetries, extremeWingStatsRfdWlRadioStatDetailTotalBytes,
				extremeWingStatsRfdWlRadioStatDetailRxRetries, extremeWingCfgProfIfRadioBssmapWlan, extremeWingCfgProfIfRadioBssmapBss, extremeWingCfgProfIfRadioBssmapPrimary,
				extremeWingCfgRfdWlanVlanOverrideInstVlan, extremeWingCfgRfdWlanVlanOverrideInstLimit, extremeWingCfgDevIfRadioBssmapWlan, extremeWingCfgDevIfRadioBssmapBss,
				extremeWingCfgDevIfRadioBssmapPrimary, extremeWingCfgDevWlanVlanOverrideInstVlan, extremeWingCfgDevWlanVlanOverrideInstLimit,
				extremeWingCfgDevStatsWindowIdx, extremeWingCfgDevStatsWindowSampleInterval, extremeWingCfgDevStatsWindowWindowSize, extremeWingActionFileCopyInMac, extremeWingActionFileCopyInFrom,
				extremeWingActionFileCopyInTo, extremeWingActionFileCopyOutStatus, extremeWingActionFileCopyOutMessage, extremeWingActionFileCopyRun,
				extremeWingStatsNocDevMac, extremeWingStatsNocDevHostname, extremeWingStatsNocDevType, extremeWingStatsNocDevClusterName, extremeWingStatsNocDevRfDomainName,
				extremeWingStatsNocDevAdoptedBy, extremeWingStatsNocDevOnline, extremeWingStatsNocDevReporter, extremeWingStatsNocDevLastUpdate, extremeWingStatsNocDevHasRadio, extremeWingStatsNocDevIsController,
				extremeWingStatsNocDevProfileName, extremeWingStatsRfdWlClientStatDetailTxRetriedBytes, extremeWingStatsRfdWlRadioStatDetailTxRetriedBytes, extremeWingStatsRfdWlApInfoIp,
				extremeWingActionFileMD5sumInMac, extremeWingActionFileMD5sumInPath, extremeWingActionFileMD5sumOutStatus, extremeWingActionFileMD5sumOutMessage, extremeWingActionFileMD5sumRun,
				extremeWingActionDisassociateClientInRfDomainName, extremeWingActionDisassociateClientInMac, extremeWingActionDisassociateClientInWlanName, extremeWingActionDisassociateClientOutStatus,
				extremeWingActionDisassociateClientOutMessage, extremeWingActionDisassociateClientRun, extremeWingStatsDevAdoptDevBy, extremeWingStatsDevAdoptDevLastAdoption,
				extremeWingStatsDevAdoptDevModelNumber, extremeWingStatsDevAdoptDevStartup, extremeWingStatsDevAdoptDevCfgStatus, extremeWingStatsDevCdpNeighborIndex, extremeWingStatsDevCdpNeighborDevId,
				extremeWingStatsDevCdpNeighborPlatform, extremeWingStatsDevCdpNeighborIpList, extremeWingStatsDevCdpNeighborPortId, extremeWingStatsDevCdpNeighborTtl, extremeWingStatsDevCdpNeighborLocalPort,
				extremeWingStatsDevCdpNeighborDuplex, extremeWingCfgSysCommitLastError, extremeWingStatsDevWlApDetectMac, extremeWingStatsDevWlApDetectVendor, extremeWingStatsDevWlApDetectChannel,
				extremeWingStatsDevWlApDetectRadioType, extremeWingStatsDevWlApDetectApMode, extremeWingStatsDevWlApDetectSsid, extremeWingStatsDevWlApDetectRssi, extremeWingStatsDevWlApDetectLastSeen,
				extremeWingStatsDevWlApDetectFirstSeen, extremeWingStatsDevWlApDetectEncryption, extremeWingStatsDevWlApDetectReportingApMac, extremeWingStatsDevWlApDetectReportingApRadioNum,
				extremeWingCfgSysRunningConfigChecksum, extremeWingStatsRfdWlRadioDetailWlanMapWlanName, extremeWingStatsRfdWlRadioDetailWlanMapBssIndex, extremeWingStatsRfdWlRadioDetailWlanMapIsPrimary,
				extremeWingStatsRfdWlRadioDetailBssMapBssIndex, extremeWingStatsRfdWlRadioDetailBssMapBasicRates, extremeWingStatsRfdWlRadioDetailBssMapSupportedRates,
				extremeWingCfgDevVpnCryptoInstPeerListPriority, extremeWingCfgDevVpnCryptoInstPeerListType, extremeWingCfgDevVpnCryptoInstPeerListIkev1Peer, 
				extremeWingCfgDevVpnCryptoInstPeerListIkev2Peer, extremeWingCfgProfVpnCryptoInstAhSessionDirection, extremeWingCfgProfVpnCryptoInstAhSessionSpi,
				extremeWingCfgProfVpnCryptoInstAhSessionAuth, extremeWingCfgProfVpnCryptoInstAhSessionKey, 
                                extremeWingCfgDevDynRouteOspfNetworkAreaId, extremeWingCfgDevDynRouteOspfAreaId, extremeWingCfgDevDynRouteOspfAreaAuthentication, 
				extremeWingCfgDevDynRouteOspfAreaRange, extremeWingCfgDevDynRouteOspfAreaType, extremeWingCfgDevDynRouteOspfAreaDefaultCost, 
				extremeWingCfgDevDynRouteOspfAreaTranslateType, extremeWingCfgDevDynRouteDefaultInfoOriginate, extremeWingCfgDevDynRouteDefaultInfoAlways,
                                extremeWingCfgDevDynRouteDefaultInfoRtMetric, extremeWingCfgDevDynRouteDefaultInfoRtMetricType, extremeWingCfgDevDynRouteRedistributeRouteType, 
				extremeWingCfgDevDynRouteRedistributeMetric, extremeWingCfgDevDynRouteRedistributeMetricType, extremeWingCfgDevDynRouteOspfNetwork, 
				extremeWingCfgDevDynRouteOspfVrrpStateCheck, extremeWingCfgDevDynRouteOspfPassiveRemoved,
                                extremeWingCfgDevDynRouteOspfPassive, extremeWingCfgProfDynRouteDefaultInfoRtMetricType, extremeWingCfgProfDynRouteDefaultInfoRtMetric, 
				extremeWingCfgProfDynRouteDefaultInfoAlways, extremeWingCfgProfDynRouteOspfPassive, extremeWingCfgProfDynRouteOspfPassiveRemoved, extremeWingCfgProfDynRouteOspfVrrpStateCheck, 
				extremeWingCfgProfDynRouteDefaultInfoOriginate, extremeWingStatsDevDynRouteIpOspfShutdownFlag, extremeWingStatsDevDynRouteIpOspfShutdownDueTime, extremeWingStatsDevDynRouteIpOspfTos,
                                extremeWingStatsDevDynRouteIpOspfRFC2328ConformanceFlag, extremeWingStatsDevDynRouteIpOspfRFC1583CompatFlag, extremeWingStatsDevDynRouteIpOspfOpaquelsaFlag, extremeWingStatsDevDynRouteIpOspfOpaquelsaOriginationBlockedFlag, extremeWingStatsDevDynRouteIpOspfStubRouterAdvFlag,
                                extremeWingStatsDevDynRouteIpOspfStubRouterStartupTime, extremeWingStatsDevDynRouteIpOspfStubRouterShutdownTime, extremeWingStatsDevDynRouteIpOspfDelay, extremeWingStatsDevDynRouteIpOspfHoldTime, extremeWingStatsDevDynRouteIpOspfMaxHoldTime,
                                extremeWingStatsDevDynRouteIpOspfHoldMultiplier, extremeWingStatsDevDynRouteIpOspfExecutedFlag, extremeWingStatsDevDynRouteIpOspfExecutedWhen, extremeWingStatsDevDynRouteIpOspfTimerDueFlag, extremeWingStatsDevDynRouteIpOspfDueIn,
                                extremeWingStatsDevDynRouteIpOspflsaRefreshTimer, extremeWingStatsDevDynRouteIpOspfAbrFlag, extremeWingStatsDevDynRouteIpOspfAbrType, extremeWingStatsDevDynRouteIpOspfAsbrFlag, extremeWingStatsDevDynRouteIpOspfExtLsdbCount,
                                extremeWingStatsDevDynRouteIpOspfExtLsdbCsum, extremeWingStatsDevDynRouteIpOspfOpaqueLsdbCount, extremeWingStatsDevDynRouteIpOspfOpaqueExtLsdbCsum, extremeWingStatsDevDynRouteIpOspfNumAreasAttached, extremeWingStatsDevDynRouteOspfAreaId,
                                extremeWingStatsDevDynRouteOspfAreaType, extremeWingStatsDevDynRouteOspfAreaBackboneFlag, extremeWingStatsDevDynRouteOspfAreaNoSummaryFlag, extremeWingStatsDevDynRouteOspfAreaShortcutType, extremeWingStatsDevDynRouteOspfAreaShortcutCapability,
                                extremeWingStatsDevDynRouteOspfAreaInterfaceNum, extremeWingStatsDevDynRouteOspfAreaActiveInterfaces, extremeWingStatsDevDynRouteOspfAreaNssaFlag, extremeWingStatsDevDynRouteOspfAreaNssaTransType, extremeWingStatsDevDynRouteOspfAreaStubRouterStateFlag,
                                extremeWingStatsDevDynRouteOspfAreaAdminStubRoutedFlag, extremeWingStatsDevDynRouteOspfAreaStartupTimeDue, extremeWingStatsDevDynRouteOspfAreaNumFullyAdjNbrs, extremeWingStatsDevDynRouteOspfAreaAuthType,
                                extremeWingStatsDevDynRouteOspfAreaNumFullVirtualAdj, extremeWingStatsDevDynRouteOspfAreaNumSpfExecuted, extremeWingStatsDevDynRouteOspfAreaNumTotalLsa, extremeWingStatsDevDynRouteOspfAreaNumRouterLsa, extremeWingStatsDevDynRouteOspfAreaRouterLsaCsum,
                                extremeWingStatsDevDynRouteOspfAreaNumNetworkLsa, extremeWingStatsDevDynRouteOspfAreaNetworkLsaCsum, extremeWingStatsDevDynRouteOspfAreaNumSummaryLsa, extremeWingStatsDevDynRouteOspfAreaSummaryLsaCsum, extremeWingStatsDevDynRouteOspfAreaNumAsbrSummaryLsa,
                                extremeWingStatsDevDynRouteOspfAreaAsbrSummaryLsaCsum, extremeWingStatsDevDynRouteOspfAreaNumNssaLsa, extremeWingStatsDevDynRouteOspfAreaNssaLsaCsum, extremeWingStatsDevDynRouteOspfAreaNumOpaqueLinkLsa, extremeWingStatsDevDynRouteOspfAreaOpaqueLinkLsaCsum,
                                extremeWingStatsDevDynRouteOspfAreaNumOpaqueAreaLsa, extremeWingStatsDevDynRouteOspfAreaOpaqueAreaLsaCsum, extremeWingStatsDevDynRouteIpOspfNetworkRoute, extremeWingStatsDevDynRouteIpOspfNetworkRoutesPathType, extremeWingStatsDevDynRouteIpOspfNetworkRoutesDestType,
                                extremeWingStatsDevDynRouteIpOspfNetworkRoutesCost, extremeWingStatsDevDynRouteIpOspfNetworkRoutesArea, extremeWingStatsDevDynRouteIpOspfNetworkRoutesMPathsIndex, extremeWingStatsDevDynRouteIpOspfNetworkRoutesAttachedFlags, extremeWingStatsDevDynRouteIpOspfNetworkRoutesIfName,
                                extremeWingStatsDevDynRouteIpOspfNetworkRoutesNextHop, extremeWingStatsDevDynRouteIpOspfRouterRoute, extremeWingStatsDevDynRouteIpOspfRouterRoutesInfoIndex, extremeWingStatsDevDynRouteIpOspfRouterRoutePathType, extremeWingStatsDevDynRouteIpOspfRouterRouteArea,
                                extremeWingStatsDevDynRouteIpOspfRouterRouteCost, extremeWingStatsDevDynRouteIpOspfRouterRouteFlags, extremeWingStatsDevDynRouteIpOspfRouterRouteAttachedFlag, extremeWingStatsDevDynRouteIpOspfRouterRouteIfName, extremeWingStatsDevDynRouteIpOspfRouterRouteNextHop,
                                extremeWingstatsDevDynRouteIpOspfExtRoute, extremeWingstatsDevDynRouteIpOspfExtRoutePathType, extremeWingstatsDevDynRouteIpOspfExtRouteArea, extremeWingstatsDevDynRouteIpOspfExtRouteCost, extremeWingstatsDevDynRouteIpOspfExtRouteType2Cost,
                                extremeWingstatsDevDynRouteIpOspfExtRouteTag, extremeWingstatsDevDynRouteIpOspfExtRoutesMPathsIndex, extremeWingstatsDevDynRouteIpOspfExtRouteAttachedFlag, extremeWingstatsDevDynRouteIpOspfExtRouteIfName, extremeWingstatsDevDynRouteIpOspfExtRouteNextHop,
                                extremeWingStatsDevDynRouteBorderRouter, extremeWingStatsDevDynRouteBorderRoutersInfoIndex, extremeWingStatsDevDynRouteBorderRouterPathType, extremeWingStatsDevDynRouteBorderRouterArea, extremeWingStatsDevDynRouteBorderRouterCost,
                                extremeWingStatsDevDynRouteBorderRouterFlags, extremeWingStatsDevDynRouteBorderRouterAttachedFlag, extremeWingStatsDevDynRouteBorderRouterIfName, extremeWingStatsDevDynRouteBorderRouterNextHop, extremeWingStatsDevDynRouteOspfIfName,
                                extremeWingStatsDevDynRouteOspfIfStatusFlag, extremeWingStatsDevDynRouteOspfIfIndex, extremeWingStatsDevDynRouteOspfIfMtu, extremeWingStatsDevDynRouteOspfIfBandwidth, extremeWingStatsDevDynRouteOspfIfFlags,
                                extremeWingStatsDevDynRouteOspfIfEnabled, extremeWingStatsDevDynRouteOspfIfInfoIndex, extremeWingStatsDevDynRouteOspfIfIpAddr, extremeWingStatsDevDynRouteOspfIfMask, extremeWingStatsDevDynRouteOspfIfBroadcastOrP2P,
                                extremeWingStatsDevDynRouteOspfIfBroadcastOrP2PIpAddr, extremeWingStatsDevDynRouteOspfIfAreaId, extremeWingStatsDevDynRouteOspfIfMtuMismatchDetectFlag, extremeWingStatsDevDynRouteOspfIfRouterId, extremeWingStatsDevDynRouteOspfIfNetworkType,
                                extremeWingStatsDevDynRouteOspfIfCost, extremeWingStatsDevDynRouteOspfIfTransmitDelay, extremeWingStatsDevDynRouteOspfIfIsmState, extremeWingStatsDevDynRouteOspfIfPriority, extremeWingStatsDevDynRouteOspfIfDesgRouterId,
                                extremeWingStatsDevDynRouteOspfIfDesgRouterAddr, extremeWingStatsDevDynRouteOspfIfBackupDesgRouterId, extremeWingStatsDevDynRouteOspfIfBackupDesgRouterAddr, extremeWingStatsDevDynRouteOspfIfMcastMembership, extremeWingStatsDevDynRouteOspfIfSubSecHelloFlag,
                                extremeWingStatsDevDynRouteOspfIfHelloInterval, extremeWingStatsDevDynRouteOspfIfDeadInterval, extremeWingStatsDevDynRouteOspfIfWaitInterval, extremeWingStatsDevDynRouteOspfIfRetransmitInterval, extremeWingStatsDevDynRouteOspfIfPassiveFlag,
                                extremeWingStatsDevDynRouteOspfIfHelloDueIn, extremeWingStatsDevDynRouteOspfIfNeighborCount, extremeWingStatsDevDynRouteOspfIfAdjNeighborCount, extremeWingStatsDevDynRouteNeighborIndex, extremeWingStatsDevDynRouteNeighborRouterId,
                                extremeWingStatsDevDynRouteNeighborPriority, extremeWingStatsDevDynRouteNeighborSelfState, extremeWingStatsDevDynRouteNeighborDeadTime, extremeWingStatsDevDynRouteNeighborAddr, extremeWingStatsDevDynRouteNeighborIfName,
                                extremeWingStatsDevDynRouteNeighborSrcAddr, extremeWingStatsDevDynRouteNeighborRetansmitCount, extremeWingStatsDevDynRouteNeighborRequestCount, extremeWingStatsDevDynRouteNeighborSummaryCount, extremeWingStatsDevDynRouteIpOspfRouterId,
                                extremeWingCfgProfDynRouteDefaultInfoAlways, extremeWingCfgProfDynRouteOspfPassive, extremeWingCfgProfDynRouteOspfPassiveRemoved, extremeWingCfgProfDynRouteOspfVrrpStateCheck,
                                extremeWingCfgProfDynRouteDefaultInfoOriginate, extremeWingStatsDevPbrRuleString, extremeWingCfgDevVpnAutoIPSecSecureGroupId, extremeWingCfgDevVpnAutoIPSecSecureGroupIdAuthType, 
				extremeWingCfgDevVpnAutoIPSecSecureGroupIdAuthKey, extremeWingCfgDevVpnAutoIPSecSecureRemoteGWIkeVersion, extremeWingCfgProfVpnAutoIPSecSecureGroupId, extremeWingCfgProfVpnAutoIPSecSecureGroupIdAuthType, 
				extremeWingCfgProfVpnAutoIPSecSecureGroupIdAuthKey, extremeWingCfgProfVpnAutoIPSecSecureRemoteGWIkeVersion, extremeWingCfgl2tpv3PolicyName, extremeWingCfgl2tpv3PolicyHelloInterval, 
				extremeWingCfgl2tpv3PolicyRetryAttempts, extremeWingCfgl2tpv3PolicyRetryInterval, extremeWingCfgl2tpv3PolicyHideAVPs, extremeWingCfgl2tpv3PolicyCookieSize, 
				extremeWingCfgl2tpv3PolicyRxWindowSize, extremeWingCfgl2tpv3PolicyTxWindowSize, extremeWingCfgl2tpv3PolicySequencingRequired, extremeWingCfgl2tpv3PolicyReconnectInterval, 
				extremeWingCfgl2tpv3PolicyReconnectAttempts, extremeWingStatsDevPbrRuleString, extremeWingCfgDevIfPppoeDefaultRoutePriority,
				extremeWingCfgProfVpnIkev1IsakmpName, extremeWingCfgProfVpnIkev1IsakmpEncryption, extremeWingCfgProfVpnIkev1IsakmpGroup, 
				extremeWingCfgProfVpnIkev1IsakmpHash, extremeWingCfgProfVpnIkev2IsakmpName, extremeWingCfgProfVpnIkev2IsakmpEncryption, extremeWingCfgProfVpnIkev2IsakmpGroup, 
				extremeWingCfgProfVpnIkev2IsakmpHash, extremeWingCfgDevVpnIkev1IsakmpName, extremeWingCfgDevVpnIkev1IsakmpEncryption, extremeWingCfgDevVpnIkev1IsakmpGroup, 
				extremeWingCfgDevVpnIkev1IsakmpHash, extremeWingCfgDevVpnIkev2IsakmpName, extremeWingCfgDevVpnIkev2IsakmpEncryption, extremeWingCfgDevVpnIkev2IsakmpGroup, 
				extremeWingCfgDevVpnIkev2IsakmpHash, extremeWingCfgProfVpnCryptoInstSequence, extremeWingCfgProfVpnCryptoInstType, extremeWingCfgProfVpnCryptoInstIpAcl, 
				extremeWingCfgProfVpnCryptoInstTransformSet, extremeWingCfgProfVpnCryptoInstLocalip, extremeWingCfgProfVpnCryptoInstPfs, extremeWingCfgProfVpnCryptoInstLifetimeSeconds,
				extremeWingCfgProfVpnCryptoInstLifetimeKb, extremeWingCfgProfVpnCryptoInstRemoteType, extremeWingCfgProfVpnCryptoInstModeconfig, extremeWingCfgProfVpnCryptoInstPeer,
				extremeWingCfgProfVpnCryptoInstProtocol, extremeWingCfgProfVpnCryptoInstMode, 
                                extremeWingCfgDevDynRouteOspfNetworkAreaId, extremeWingCfgDevDynRouteOspfAreaId, extremeWingCfgDevDynRouteOspfAreaAuthentication, extremeWingCfgDevDynRouteOspfAreaRange,
                                extremeWingCfgDevDynRouteOspfAreaType, extremeWingCfgDevDynRouteOspfAreaDefaultCost, extremeWingCfgDevDynRouteOspfAreaTranslateType, extremeWingCfgDevDynRouteDefaultInfoOriginate, extremeWingCfgDevDynRouteDefaultInfoAlways,
                                extremeWingCfgDevDynRouteDefaultInfoRtMetric, extremeWingCfgDevDynRouteDefaultInfoRtMetricType, extremeWingCfgDevDynRouteRedistributeRouteType, extremeWingCfgDevDynRouteRedistributeMetric,
                                extremeWingCfgDevDynRouteRedistributeMetricType, extremeWingCfgDevDynRouteOspfNetwork, extremeWingCfgDevDynRouteOspfVrrpStateCheck, extremeWingCfgDevDynRouteOspfPassiveRemoved,
                                extremeWingCfgDevDynRouteOspfPassive, extremeWingCfgProfDynRouteDefaultInfoRtMetricType, extremeWingCfgProfDynRouteDefaultInfoRtMetric, extremeWingCfgProfDynRouteDefaultInfoAlways, extremeWingCfgProfDynRouteOspfPassive,
                                extremeWingCfgProfDynRouteOspfPassiveRemoved, extremeWingCfgProfDynRouteOspfVrrpStateCheck, extremeWingCfgProfDynRouteDefaultInfoOriginate,
				extremeWingCfgProfVrrpGroupAdvertisementUnit, extremeWingCfgProfVrrpGroupAdvertisementIntervalV2Msec, extremeWingCfgDevVrrpGroupAdvertisementUnit,
				extremeWingCfgDevVrrpGroupAdvertisementIntervalV2Msec, extremeWingCfgProfCriticalResMonitorInt, extremeWingCfgProfCriticalResPolicyVia, 
				extremeWingCfgProfCriticalResPolicyAnyAll, extremeWingCfgProfCriticalResourcesAddr, extremeWingCfgProfCriticalResourcesMonitorType, 
				extremeWingCfgProfCriticalResourcesVlan, extremeWingCfgDevCriticalResMonitorInt, extremeWingCfgDevCriticalResPolicyVia, extremeWingCfgDevCriticalResPolicyAnyAll, 
				extremeWingCfgDevCriticalResourcesAddr, extremeWingCfgDevCriticalResourcesMonitorType, extremeWingCfgDevCriticalResourcesVlan, extremeWingStatsDevVrrpGlobalErrIpTtlErrs, 
				extremeWingStatsDevVrrpGlobalErrVersionMismatch, extremeWingStatsDevVrrpGlobalErrPacketLenErr, extremeWingStatsDevVrrpGlobalErrChecksumErr, 
				extremeWingStatsDevVrrpGlobalErrInvalidVirtualRouterId, extremeWingStatsDevVrrpGlobalErrAuthMismatch, extremeWingStatsDevVrrpGlobalErrInvalidTypePackets, 
				extremeWingStatsDevVrrpGlobalErrLastProtocolErrReason, extremeWingStatsDevVrrpOperationVirtualRouterId, extremeWingStatsDevVrrpOperationIfName, 
				extremeWingStatsDevVrrpOperationVersion, extremeWingStatsDevVrrpOperationState, extremeWingStatsDevVrrpOperationPriority, extremeWingStatsDevVrrpOperationVirtualAddr, 
				extremeWingStatsDevVrrpOperationMasterAddr, extremeWingStatsDevVrrpOperationExpiryTimer, extremeWingStatsDevVrrpOperationMasterDeadTimer, 
				extremeWingStatsDevVrrpDetailVirtualRouterId, extremeWingStatsDevVrrpDetailIfName, extremeWingStatsDevVrrpDetailVersion, extremeWingStatsDevVrrpDetailConfiguredPriority, 
				extremeWingStatsDevVrrpDetailAdvertisementInterval, extremeWingStatsDevVrrpDetailLocalIpAddress, extremeWingStatsDevVrrpDetailIfStatusAdmin, 
				extremeWingStatsDevVrrpDetailVirtualAddressCount, extremeWingStatsDevVrrpDetailPreempt, extremeWingStatsDevVrrpDetailPreemptDelay, extremeWingStatsDevVrrpDetailCrmDownAction, 
				extremeWingStatsDevVrrpDetailCrmStatus, extremeWingStatsDevVrrpDetailCfgedDeltaPriority, extremeWingStatsDevVrrpDetailVirtualMacAddr, extremeWingStatsDevVrrpDetailSyncGroup, 
				extremeWingStatsDevVrrpDetailFailoverSyncGroup, extremeWingStatsDevVrrpDetailMonitorIf, extremeWingStatsDevVrrpDetailMonitorIfStatusAdmin, 
				extremeWingStatsDevVrrpRouterStatsVirtualRouterId, extremeWingStatsDevVrrpRouterStatsMasterTransitions, extremeWingStatsDevVrrpRouterStatsNewMasterReason, 
				extremeWingStatsDevVrrpRouterStatsNumReceivedAdvertisement, extremeWingStatsDevVrrpRouterStatsAdvertisementIntervalErrs, 
				extremeWingStatsDevVrrpRouterStatsNumSendAdvertisement, extremeWingStatsDevVrrpRouterStatsReceivedAdvtInitState, 
				extremeWingStatsDevVrrpRouterStatsReceivedPriorityZeroPackets, extremeWingStatsDevVrrpRouterStatsSendPriorityZeroPackets, 
				extremeWingStatsDevPbrRouteMapPrecedence, extremeWingStatsDevPbrPrimaryNextHopIfName, extremeWingStatsDevPbrPrimaryNextHopIpAddr, 
				extremeWingStatsDevPbrPrimaryNextHopState, extremeWingStatsDevPbrPrimaryNextHopMonitorMode, extremeWingStatsDevPbrSecondaryNextHopIfName, 
				extremeWingStatsDevPbrSecondaryNextHopIpAddr, extremeWingStatsDevPbrSecondaryNextHopState, extremeWingStatsDevPbrSecondaryNextHopMonitorMode, 
				extremeWingStatsDevPbrDefaultNextHopIfName, extremeWingStatsDevPbrDefaultNextHopIpAddr, extremeWingStatsDevPbrDefaultNextHopState, 
				extremeWingStatsDevPbrDefaultNextHopMonitorMode, extremeWingStatsDevPbrWlan, extremeWingStatsDevPbrWirelessClientRole, extremeWingStatsDevPbrInInterface, 
				extremeWingStatsDevPbrIpDscp, extremeWingStatsDevPbrRuleString, extremeWingStatsDevPbrRulesHitcount, extremeWingStatsDevDynRouteIpOspfShutdownFlag, extremeWingStatsDevDynRouteIpOspfShutdownDueTime, extremeWingStatsDevDynRouteIpOspfTos,
                                extremeWingStatsDevDynRouteIpOspfRFC2328ConformanceFlag, extremeWingStatsDevDynRouteIpOspfRFC1583CompatFlag, extremeWingStatsDevDynRouteIpOspfOpaquelsaFlag, extremeWingStatsDevDynRouteIpOspfOpaquelsaOriginationBlockedFlag, extremeWingStatsDevDynRouteIpOspfStubRouterAdvFlag,
                                extremeWingStatsDevDynRouteIpOspfStubRouterStartupTime, extremeWingStatsDevDynRouteIpOspfStubRouterShutdownTime, extremeWingStatsDevDynRouteIpOspfDelay, extremeWingStatsDevDynRouteIpOspfHoldTime, extremeWingStatsDevDynRouteIpOspfMaxHoldTime,
                                extremeWingStatsDevDynRouteIpOspfHoldMultiplier, extremeWingStatsDevDynRouteIpOspfExecutedFlag, extremeWingStatsDevDynRouteIpOspfExecutedWhen, extremeWingStatsDevDynRouteIpOspfTimerDueFlag, extremeWingStatsDevDynRouteIpOspfDueIn,
                                extremeWingStatsDevDynRouteIpOspflsaRefreshTimer, extremeWingStatsDevDynRouteIpOspfAbrFlag, extremeWingStatsDevDynRouteIpOspfAbrType, extremeWingStatsDevDynRouteIpOspfAsbrFlag, extremeWingStatsDevDynRouteIpOspfExtLsdbCount,
                                extremeWingStatsDevDynRouteIpOspfExtLsdbCsum, extremeWingStatsDevDynRouteIpOspfOpaqueLsdbCount, extremeWingStatsDevDynRouteIpOspfOpaqueExtLsdbCsum, extremeWingStatsDevDynRouteIpOspfNumAreasAttached, extremeWingStatsDevDynRouteOspfAreaId,
                                extremeWingStatsDevDynRouteOspfAreaType, extremeWingStatsDevDynRouteOspfAreaBackboneFlag, extremeWingStatsDevDynRouteOspfAreaNoSummaryFlag, extremeWingStatsDevDynRouteOspfAreaShortcutType, extremeWingStatsDevDynRouteOspfAreaShortcutCapability,
                                extremeWingStatsDevDynRouteOspfAreaInterfaceNum, extremeWingStatsDevDynRouteOspfAreaActiveInterfaces, extremeWingStatsDevDynRouteOspfAreaNssaFlag, extremeWingStatsDevDynRouteOspfAreaNssaTransType, extremeWingStatsDevDynRouteOspfAreaStubRouterStateFlag,
                                extremeWingStatsDevDynRouteOspfAreaAdminStubRoutedFlag, extremeWingStatsDevDynRouteOspfAreaStartupTimeDue, extremeWingStatsDevDynRouteOspfAreaNumFullyAdjNbrs, extremeWingStatsDevDynRouteOspfAreaAuthType, 
                                extremeWingStatsDevDynRouteOspfAreaNumFullVirtualAdj, extremeWingStatsDevDynRouteOspfAreaNumSpfExecuted, extremeWingStatsDevDynRouteOspfAreaNumTotalLsa, extremeWingStatsDevDynRouteOspfAreaNumRouterLsa, extremeWingStatsDevDynRouteOspfAreaRouterLsaCsum,
                                extremeWingStatsDevDynRouteOspfAreaNumNetworkLsa, extremeWingStatsDevDynRouteOspfAreaNetworkLsaCsum, extremeWingStatsDevDynRouteOspfAreaNumSummaryLsa, extremeWingStatsDevDynRouteOspfAreaSummaryLsaCsum, extremeWingStatsDevDynRouteOspfAreaNumAsbrSummaryLsa,
                                extremeWingStatsDevDynRouteOspfAreaAsbrSummaryLsaCsum, extremeWingStatsDevDynRouteOspfAreaNumNssaLsa, extremeWingStatsDevDynRouteOspfAreaNssaLsaCsum, extremeWingStatsDevDynRouteOspfAreaNumOpaqueLinkLsa, extremeWingStatsDevDynRouteOspfAreaOpaqueLinkLsaCsum,
                                extremeWingStatsDevDynRouteOspfAreaNumOpaqueAreaLsa, extremeWingStatsDevDynRouteOspfAreaOpaqueAreaLsaCsum, extremeWingStatsDevDynRouteIpOspfNetworkRoute, extremeWingStatsDevDynRouteIpOspfNetworkRoutesPathType, extremeWingStatsDevDynRouteIpOspfNetworkRoutesDestType,
                                extremeWingStatsDevDynRouteIpOspfNetworkRoutesCost, extremeWingStatsDevDynRouteIpOspfNetworkRoutesArea, extremeWingStatsDevDynRouteIpOspfNetworkRoutesMPathsIndex, extremeWingStatsDevDynRouteIpOspfNetworkRoutesAttachedFlags, extremeWingStatsDevDynRouteIpOspfNetworkRoutesIfName,
                                extremeWingStatsDevDynRouteIpOspfNetworkRoutesNextHop, extremeWingStatsDevDynRouteIpOspfRouterRoute, extremeWingStatsDevDynRouteIpOspfRouterRoutesInfoIndex, extremeWingStatsDevDynRouteIpOspfRouterRoutePathType, extremeWingStatsDevDynRouteIpOspfRouterRouteArea,
                                extremeWingStatsDevDynRouteIpOspfRouterRouteCost, extremeWingStatsDevDynRouteIpOspfRouterRouteFlags, extremeWingStatsDevDynRouteIpOspfRouterRouteAttachedFlag, extremeWingStatsDevDynRouteIpOspfRouterRouteIfName, extremeWingStatsDevDynRouteIpOspfRouterRouteNextHop,
                                extremeWingstatsDevDynRouteIpOspfExtRoute, extremeWingstatsDevDynRouteIpOspfExtRoutePathType, extremeWingstatsDevDynRouteIpOspfExtRouteArea, extremeWingstatsDevDynRouteIpOspfExtRouteCost, extremeWingstatsDevDynRouteIpOspfExtRouteType2Cost,
                                extremeWingstatsDevDynRouteIpOspfExtRouteTag, extremeWingstatsDevDynRouteIpOspfExtRoutesMPathsIndex, extremeWingstatsDevDynRouteIpOspfExtRouteAttachedFlag, extremeWingstatsDevDynRouteIpOspfExtRouteIfName, extremeWingstatsDevDynRouteIpOspfExtRouteNextHop,
                                extremeWingStatsDevDynRouteBorderRouter, extremeWingStatsDevDynRouteBorderRoutersInfoIndex, extremeWingStatsDevDynRouteBorderRouterPathType, extremeWingStatsDevDynRouteBorderRouterArea, extremeWingStatsDevDynRouteBorderRouterCost,
                                extremeWingStatsDevDynRouteBorderRouterFlags, extremeWingStatsDevDynRouteBorderRouterAttachedFlag, extremeWingStatsDevDynRouteBorderRouterIfName, extremeWingStatsDevDynRouteBorderRouterNextHop, extremeWingStatsDevDynRouteOspfIfName,
                                extremeWingStatsDevDynRouteOspfIfStatusFlag, extremeWingStatsDevDynRouteOspfIfIndex, extremeWingStatsDevDynRouteOspfIfMtu, extremeWingStatsDevDynRouteOspfIfBandwidth, extremeWingStatsDevDynRouteOspfIfFlags,
                                extremeWingStatsDevDynRouteOspfIfEnabled, extremeWingStatsDevDynRouteOspfIfInfoIndex, extremeWingStatsDevDynRouteOspfIfIpAddr, extremeWingStatsDevDynRouteOspfIfMask, extremeWingStatsDevDynRouteOspfIfBroadcastOrP2P,
                                extremeWingStatsDevDynRouteOspfIfBroadcastOrP2PIpAddr, extremeWingStatsDevDynRouteOspfIfAreaId, extremeWingStatsDevDynRouteOspfIfMtuMismatchDetectFlag, extremeWingStatsDevDynRouteOspfIfRouterId, extremeWingStatsDevDynRouteOspfIfNetworkType,
                                extremeWingStatsDevDynRouteOspfIfCost, extremeWingStatsDevDynRouteOspfIfTransmitDelay, extremeWingStatsDevDynRouteOspfIfIsmState, extremeWingStatsDevDynRouteOspfIfPriority, extremeWingStatsDevDynRouteOspfIfDesgRouterId,
                                extremeWingStatsDevDynRouteOspfIfDesgRouterAddr, extremeWingStatsDevDynRouteOspfIfBackupDesgRouterId, extremeWingStatsDevDynRouteOspfIfBackupDesgRouterAddr, extremeWingStatsDevDynRouteOspfIfMcastMembership, extremeWingStatsDevDynRouteOspfIfSubSecHelloFlag,
                                extremeWingStatsDevDynRouteOspfIfHelloInterval, extremeWingStatsDevDynRouteOspfIfDeadInterval, extremeWingStatsDevDynRouteOspfIfWaitInterval, extremeWingStatsDevDynRouteOspfIfRetransmitInterval, extremeWingStatsDevDynRouteOspfIfPassiveFlag,
                                extremeWingStatsDevDynRouteOspfIfHelloDueIn, extremeWingStatsDevDynRouteOspfIfNeighborCount, extremeWingStatsDevDynRouteOspfIfAdjNeighborCount, extremeWingStatsDevDynRouteNeighborIndex, extremeWingStatsDevDynRouteNeighborRouterId,
                                extremeWingStatsDevDynRouteNeighborPriority, extremeWingStatsDevDynRouteNeighborSelfState, extremeWingStatsDevDynRouteNeighborDeadTime, extremeWingStatsDevDynRouteNeighborAddr, extremeWingStatsDevDynRouteNeighborIfName,
                                extremeWingStatsDevDynRouteNeighborSrcAddr, extremeWingStatsDevDynRouteNeighborRetansmitCount, extremeWingStatsDevDynRouteNeighborRequestCount, extremeWingStatsDevDynRouteNeighborSummaryCount, extremeWingStatsDevDynRouteIpOspfRouterId,
                                extremeWingCfgProfDynRouteDefaultInfoAlways, extremeWingCfgProfDynRouteOspfPassive, extremeWingCfgProfDynRouteOspfPassiveRemoved, extremeWingCfgProfDynRouteOspfVrrpStateCheck, 
                                extremeWingCfgProfDynRouteDefaultInfoOriginate, extremeWingStatsDevPbrRuleString,
				extremeWingCfgProfVpnIkev1RemoteLocalUsersName, extremeWingCfgProfVpnIkev1RemoteLocalUsersPassword, extremeWingCfgDevVpnIkev1RemoteLocalUsersName, 
				extremeWingCfgDevVpnIkev1RemoteLocalUsersPassword, extremeWingCfgProfVpnIkev2RemoteLocalUsersName, extremeWingCfgProfVpnIkev2RemoteLocalUsersPassword, 
				extremeWingCfgDevVpnIkev2RemoteLocalUsersName, extremeWingCfgDevVpnIkev2RemoteLocalUsersPassword, extremeWingCfgDevVpnCryptoInstSequence, 
				extremeWingCfgDevVpnCryptoInstType, extremeWingCfgDevVpnCryptoInstIpAcl, extremeWingCfgDevVpnCryptoInstTransformSet, extremeWingCfgDevVpnCryptoInstLocalip, 
				extremeWingCfgDevVpnCryptoInstPfs, extremeWingCfgDevVpnCryptoInstLifetimeSeconds, extremeWingCfgDevVpnCryptoInstLifetimeKb, 
				extremeWingCfgDevVpnCryptoInstRemoteType, extremeWingCfgDevVpnCryptoInstModeconfig, extremeWingCfgDevVpnCryptoInstPeer, extremeWingCfgDevVpnCryptoInstProtocol, 
				extremeWingCfgDevVpnCryptoInstMode, extremeWingCfgDevVpnIkev2RemoteLocalUsersName, extremeWingCfgDevVpnIkev2RemoteLocalUsersPassword, 
				extremeWingCfgDevVpnAutoIPSecSecureGroupId, extremeWingCfgDevVpnAutoIPSecSecureGroupIdAuthType, 
				extremeWingCfgDevVpnAutoIPSecSecureGroupIdAuthKey, extremeWingCfgDevVpnAutoIPSecSecureRemoteGWIkeVersion, 
				extremeWingCfgProfVpnAutoIPSecSecureGroupId, extremeWingCfgProfVpnAutoIPSecSecureGroupIdAuthType, 
				extremeWingCfgProfVpnAutoIPSecSecureGroupIdAuthKey, extremeWingCfgProfVpnAutoIPSecSecureRemoteGWIkeVersion, extremeWingCfgProfVpnCryptoInstPeerListPriority,
				extremeWingCfgProfVpnCryptoInstPeerListType, extremeWingCfgProfVpnCryptoInstPeerListIkev1Peer, extremeWingCfgProfVpnCryptoInstPeerListIkev2Peer,
				extremeWingStatsRfdWlRadioDetailWlanMapWlanName, extremeWingStatsRfdWlRadioDetailWlanMapBssIndex, extremeWingStatsRfdWlRadioDetailWlanMapIsPrimary,
				extremeWingStatsRfdWlRadioDetailBssMapBssIndex, extremeWingStatsRfdWlRadioDetailBssMapBasicRates, extremeWingStatsRfdWlRadioDetailBssMapSupportedRates,
				extremeWingCfgDevVpnCryptoInstPeerListPriority, extremeWingCfgDevVpnCryptoInstPeerListType, extremeWingCfgDevVpnCryptoInstPeerListIkev1Peer, 
				extremeWingCfgDevVpnCryptoInstPeerListIkev2Peer, extremeWingCfgProfVpnCryptoInstAhSessionDirection, extremeWingCfgProfVpnCryptoInstAhSessionSpi,
				extremeWingCfgProfVpnCryptoInstAhSessionAuth, extremeWingCfgProfVpnCryptoInstAhSessionKey, extremeWingCfgDevVpnCryptoInstAhSessionDirection, 
				extremeWingCfgDevVpnCryptoInstAhSessionSpi, extremeWingCfgDevVpnCryptoInstAhSessionAuthAlgo, extremeWingCfgDevVpnCryptoInstAhSessionKey, 
				extremeWingCfgProfVpnCryptoInstEspSessionDirection, extremeWingCfgProfVpnCryptoInstEspSessionSpi, extremeWingCfgProfVpnCryptoInstEspSessionCipherAlgo, 
				extremeWingCfgProfVpnCryptoInstEspSessionCipherKey, extremeWingCfgProfVpnCryptoInstEspSessionAuthAlgo, extremeWingCfgProfVpnCryptoInstEspSessionAuthKey, 
				extremeWingCfgDevVpnCryptoInstEspSessionDirection, extremeWingCfgDevVpnCryptoInstEspSessionSpi, extremeWingCfgDevVpnCryptoInstEspSessionCipherAlgo, 
				extremeWingCfgDevVpnCryptoInstEspSessionCipherKey, extremeWingCfgDevVpnCryptoInstEspSessionAuthAlgo, extremeWingCfgDevVpnCryptoInstEspSessionAuthKey,
				extremeWingCfgProfIfPppoeDefaultRoutePriority, extremeWingCfgProfIfPppoeIp, extremeWingCfgDevIfPppoeDefaultRoutePriority, extremeWingCfgDevIfPppoeIp, 
				extremeWingStatsDevPppoeStatusPeer, extremeWingStatsDevPppoeStatusSid, extremeWingStatsDevPppoeStatusService, extremeWingStatsDevPppoeStatusStatus, 
				extremeWingStatsDevPppoeStatusMtu, extremeWingStatsDevPppoeStatusDns1, extremeWingStatsDevPppoeStatusDns2, extremeWingStatsDevPppoeCfgAuthtype, 
				extremeWingStatsDevPppoeCfgIdleTime, extremeWingStatsDevPppoeCfgKalive, extremeWingStatsDevPppoeCfgMtu, extremeWingStatsDevPppoeCfgNet, 
				extremeWingStatsDevPppoeCfgService, extremeWingStatsDevPppoeCfgUsername, extremeWingStatsDevPppoeCfgPasswd, extremeWingStatsDevPppoeCfgShutdown,
				extremeWingCfgProfControllerHostRowStatus, extremeWingCfgDevControllerHostRowStatus,
				extremeWingCfgDevControllerHostHost, extremeWingCfgDevControllerHostPool, extremeWingCfgDevControllerHostLevel, extremeWingActionReloadInMac,
				extremeWingActionReloadInForce, extremeWingActionReloadInTimeout, extremeWingActionReloadInReason, extremeWingActionReloadOutStatus, extremeWingActionReloadOutMessage,
				extremeWingActionReloadRun,
extremeWingCfgLegacyApIndex, extremeWingCfgLegacyApCountryCode, extremeWingCfgLegacyApLed, extremeWingCfgLegacyApLocation, extremeWingCfgLegacyApIpAddr, extremeWingCfgLegacyApGateway, extremeWingCfgLegacyApPreferredControllerGroup,
				extremeWingCfgLegacyApIfName, extremeWingCfgLegacyApIfDescr, extremeWingCfgLegacyApIfShutdown, extremeWingCfgLegacyApIfRfMode, extremeWingCfgLegacyApIfAntennaDiversity, extremeWingCfgLegacyApIfBeaconInterval, extremeWingCfgLegacyApIfChannel, extremeWingCfgLegacyApIfMaxClients, extremeWingCfgLegacyApIfPlacement, extremeWingCfgLegacyApIfPower, extremeWingCfgLegacyApIfPreambleShort, extremeWingCfgLegacyApIfOnChannelScan, extremeWingCfgLegacyApIfRtsThreshold, extremeWingCfgLegacyApIfQosPolicy, extremeWingCfgLegacyApIfWirelessClientPower,	
				extremeWingCfgLegacyApIfWlanBssMapWlan, extremeWingCfgLegacyApIfWlanBssMapBss, extremeWingCfgLegacyApIfWlanBssMapPrimary, extremeWingStatsRfdWlRadioStatTxRetries, extremeWingStatsRfdWlRadioStatTxRetriedBytes,
				extremeWingStatsNocAdoptDevMac, extremeWingStatsNocAdoptDevType, extremeWingStatsNocAdoptDevHostname, extremeWingStatsNocAdoptDevVersion, extremeWingStatsNocAdoptDevSerialNo, extremeWingStatsNocAdoptDevRfDomainName,
				extremeWingStatsNocAdoptDevOnline, extremeWingStatsNocAdoptDevBy, extremeWingStatsNocAdoptDevLastAdoption, extremeWingStatsNocAdoptDevModelNumber, extremeWingStatsNocAdoptDevStartup,
				extremeWingStatsNocAdoptDevCfgStatus, extremeWingStatsNocAdoptPendingDevMac, extremeWingStatsNocAdoptPendingDevType, extremeWingStatsNocAdoptPendingDevTarget, extremeWingStatsNocAdoptPendingDevDisOption,
				extremeWingStatsNocAdoptPendingDevVersion, extremeWingStatsNocAdoptPendingDevSerialNumber, extremeWingStatsNocAdoptPendingDevReason, extremeWingStatsNocAdoptPendingDevNumRadios,
				extremeWingStatsNocAdoptPendingDevIp, extremeWingStatsNocAdoptPendingDevVlan, extremeWingCfgAltDevMac, extremeWingCfgAltDevHostname, extremeWingCfgAltDevBuilding, extremeWingCfgAltDevFloor, extremeWingCfgAltDevNumRadios,
				extremeWingCfgAltDevProfileName, extremeWingCfgAltDevRfDomainName, extremeWingCfgAltDevHttpsTrustpoint, extremeWingCfgAltDevRadiusCaTrustpoint, extremeWingCfgAltDevRadiusServerTrustpoint,
				extremeWingCfgAltDevSshRsaKey, extremeWingCfgAltDevHasOverrides, extremeWingCfgAltDevIfName, extremeWingCfgAltDevIfDescription, extremeWingCfgAltDevIfType, extremeWingCfgAltDevIfShutdown, extremeWingCfgAltDevIfIpInAcl,
				extremeWingCfgAltDevIfMacInAcl, extremeWingCfgAltDevIfRadioBssmapWlan, extremeWingCfgAltDevIfRadioBssmapBss, extremeWingCfgAltDevIfRadioBssmapPrimary, extremeWingCfgProfNatPoolAddrStartIp,
				extremeWingCfgProfNatPoolAddrEndIp, extremeWingCfgProfNatBridgeSrcDynamicAcl, extremeWingCfgProfNatBridgeSrcDynamicIfName, extremeWingCfgProfNatBridgeSrcDynamicIfOverloadType,
				extremeWingCfgProfNatBridgeSrcDynamicIfOverloadIp, extremeWingCfgProfNatBridgeSrcDynamicIfNatPool, extremeWingCfgDevNatPoolAddrStartIp, extremeWingCfgDevNatPoolAddrEndIp,
				extremeWingCfgDevNatBridgeSrcDynamicAcl, extremeWingCfgDevNatBridgeSrcDynamicIfName, extremeWingCfgDevNatBridgeSrcDynamicIfOverloadType, extremeWingCfgDevNatBridgeSrcDynamicIfOverloadIp,
				extremeWingCfgDevNatBridgeSrcDynamicIfNatPool, extremeWingCfgDevNatPoolName, extremeWingStatsDevl2tpv3TunnelName, extremeWingStatsDevl2tpv3TunnelCtrlConnId, extremeWingStatsDevl2tpv3TunnelUpTime,
				extremeWingStatsDevl2tpv3TunnelPeerAddr, extremeWingStatsDevl2tpv3TunnelLocalAddr, extremeWingStatsDevl2tpv3TunnelMtu, extremeWingStatsDevl2tpv3TunnelNativeVlanId,
				extremeWingStatsDevl2tpv3TunnelTrunkSession, extremeWingStatsDevl2tpv3TunnelNativeVlanTagged, extremeWingStatsDevl2tpv3TunnelPeerHostName, extremeWingStatsDevl2tpv3TunnelPeerCtrlConnId,
				extremeWingStatsDevl2tpv3TunnelPeerVendorName, extremeWingStatsDevl2tpv3TunnelState, extremeWingStatsDevl2tpv3TunnelNextTxSeqNum, extremeWingStatsDevl2tpv3TunnelNextRxSeqNum,
				extremeWingStatsDevl2tpv3TunnelRxAckSeqNum, extremeWingStatsDevl2tpv3TunnelRetransmitCount, extremeWingStatsDevl2tpv3TunnelReconnectCount, extremeWingStatsDevl2tpv3SessionsVlanId,
				extremeWingStatsDevl2tpv3SessionsName, extremeWingStatsDevl2tpv3SessionsPseudoWireType, extremeWingStatsDevl2tpv3SessionsCallSerialNumber, extremeWingStatsDevl2tpv3SessionsLocalSessionId,
				extremeWingStatsDevl2tpv3SessionsRemoteSessionId, extremeWingStatsDevl2tpv3SessionsLocalCookieSize, extremeWingStatsDevl2tpv3SessionsLocalcookieWord1,
				extremeWingStatsDevl2tpv3SessionsLocalCookieWord2, extremeWingStatsDevl2tpv3SessionsRemoteCookieSize, extremeWingStatsDevl2tpv3SessionsRemoteCookieWord1,
				extremeWingStatsDevl2tpv3SessionsRemoteCookieWord2, extremeWingStatsDevl2tpv3SessionsState, extremeWingStatsDevl2tpv3SessionsRemoteEndId, extremeWingCfgProfTunnelController,
				extremeWingCfgProfPreferredTunnelController, extremeWingCfgProfMintMlcpVlan, extremeWingCfgProfMintMlcpIp, extremeWingCfgProfMintTunnelControllerLoadBalancingLevel1, extremeWingCfgProfl2tpv3lUdpListenPort,
				extremeWingCfgProfl2tpv3RouterId, extremeWingCfgProfl2tpv3HostName, extremeWingCfgProfl2tpv3InterTunnelBridging, extremeWingCfgProfl2tpv3TunnelName, extremeWingCfgProfl2tpv3TunnelLocalIpAddrss,
				extremeWingCfgProfl2tpv3TunnelMtu, extremeWingCfgProfl2tpv3TunnelUseTunnelPolicy, extremeWingCfgProfl2tpv3TunnelHostname, extremeWingCfgProfl2tpv3TunnelRouterId, extremeWingCfgProfl2tpv3TunnelPeerId,
				extremeWingCfgProfl2tpv3TunnelPeerIp, extremeWingCfgProfl2tpv3TunnelPeerHostName, extremeWingCfgProfl2tpv3TunnelPeerRouterId, extremeWingCfgProfl2tpv3TunnelPeerEncapsulation,
				extremeWingCfgProfl2tpv3TunnelPeerUDPPort, extremeWingCfgProfl2tpv3TunnelSessionName, extremeWingCfgProfl2tpv3TunnelSessionPseudoWireId, extremeWingCfgProfl2tpv3TunnelSessionTrafficSourceType,
				extremeWingCfgProfl2tpv3TunnelSessionTrafficSourceValue, extremeWingCfgProfl2tpv3TunnelSessionNativeVlan, extremeWingCfgProfl2tpv3ManualSessionName, extremeWingCfgProfl2tpv3ManualSessionLocalIpAddr,
				extremeWingCfgProfl2tpv3ManualSessionPeerIp, extremeWingCfgProfl2tpv3ManualSessionPeerEncapsulation, extremeWingCfgProfl2tpv3ManualSessionPeerUDPPort, extremeWingCfgProfl2tpv3ManualSessionMtu,
				extremeWingCfgProfl2tpv3ManualSessionTrafficSource, extremeWingCfgProfl2tpv3ManualSessionTrafficSourceValue, extremeWingCfgProfl2tpv3ManualSessionNativeVlan,
				extremeWingCfgProfl2tpv3ManualSessionLocalSessionId, extremeWingCfgProfl2tpv3ManualSessionRemoteSessionId, extremeWingCfgProfl2tpv3ManualSessionCookieEndpoint,
				extremeWingCfgProfl2tpv3ManualSessionCookieSize, extremeWingCfgProfl2tpv3ManualSessionCookieVal1, extremeWingCfgProfl2tpv3ManualSessionCookieVal2, extremeWingCfgDevTunnelController,
				extremeWingCfgDevPreferredTunnelController, extremeWingCfgDevMintLevel1AreaId, extremeWingCfgDevMintSpfLatency, extremeWingCfgDevMintDisPriorityAdjustment, extremeWingCfgDevMintMlcpVlan,
				extremeWingCfgDevMintMlcpIp, extremeWingCfgDevMintTunnelControllerLoadBalancingLevel1, extremeWingCfgDevl2tpv3lUdpListenPort, extremeWingCfgDevl2tpv3RouterId, extremeWingCfgDevl2tpv3HostName,
				extremeWingCfgDevl2tpv3InterTunnelBridging, extremeWingCfgDevl2tpv3TunnelName, extremeWingCfgDevl2tpv3TunnelLocalIpAddrss, extremeWingCfgDevl2tpv3TunnelMtu, extremeWingCfgDevl2tpv3TunnelUseTunnelPolicy,
				extremeWingCfgDevl2tpv3TunnelHostname, extremeWingCfgDevl2tpv3TunnelRouterId, extremeWingCfgDevl2tpv3TunnelPeerId, extremeWingCfgDevl2tpv3TunnelPeerIp, extremeWingCfgDev2tpv3TunnelPeerHostName,
				extremeWingCfgDevl2tpv3TunnelPeerRouterId, extremeWingCfgDevl2tpv3TunnelPeerEncapsulation, extremeWingCfgDevl2tpv3TunnelPeerUDPPort, extremeWingCfgDevl2tpv3TunnelSessionName,
				extremeWingCfgDevl2tpv3TunnelSessionPseudoWireId, extremeWingCfgDevl2tpv3TunnelSessionTrafficSourceType, extremeWingCfgDevl2tpv3TunnelSessionTrafficSourceValue,
				extremeWingCfgDevl2tpv3TunnelSessionNativeVlan, extremeWingCfgDevl2tpv3ManualSessionName, extremeWingCfgDevl2tpv3ManualSessionLocalIpAddr, extremeWingCfgDevl2tpv3ManualSessionPeerIp,
				extremeWingCfgDevl2tpv3ManualSessionPeerEncapsulation, extremeWingCfgDevl2tpv3ManualSessionPeerUDPPort, extremeWingCfgDevl2tpv3ManualSessionMtu, extremeWingCfgDevl2tpv3ManualSessionTrafficSource,
				extremeWingCfgDevl2tpv3ManualSessionTrafficSourceValue, extremeWingCfgDevl2tpv3ManualSessionNativeVlan, extremeWingCfgDevl2tpv3ManualSessionLocalSessionId,
				extremeWingCfgDevl2tpv3ManualSessionRemoteSessionId, extremeWingCfgDevl2tpv3ManualSessionCookieEndpoint, extremeWingCfgDevl2tpv3ManualSessionCookieSize, extremeWingCfgDevl2tpv3ManualSessionCookieVal1,
				extremeWingCfgDevl2tpv3ManualSessionCookieVal2, extremeWingStatsDevDynRouteIpOspfMaxRoutes, extremeWingStatsDevDynRouteIpOspfRoutesReceived, extremeWingStatsDevDynRouteIpOspfMaxIgnoreStateCount,
				extremeWingStatsDevDynRouteIpOspfIgnoreStateCount, extremeWingStatsDevDynRouteIpOspfIgnoreStateTimeout, extremeWingStatsDevDynRouteIpOspfIgnoreStateMonitorTimeout,
				extremeWingStatsDevDynRouteIpOspfState, extremeWingCfgProfDynRouteOspfDefaultRoutePriority, extremeWingCfgProfDynRouteOspfNumRoutes, extremeWingCfgProfDynRouteOspfRetryCount,
				extremeWingCfgProfDynRouteOspfRetryTimeout, extremeWingCfgProfDynRouteOspfResetTime, extremeWingCfgDevDynRouteOspfDefaultRoutePriority, extremeWingCfgDevDynRouteOspfNumRoutes,
				extremeWingCfgDevDynRouteOspfRetryCount, extremeWingCfgDevDynRouteOspfRetryTimeout, extremeWingCfgDevDynRouteOspfResetTime, extremeWingCfgProfIfVlanOspfOspfBandWidth,
				extremeWingCfgProfIfVlanOspfMsgDigestKeyId, extremeWingCfgProfIfVlanOspfMsgDigestMessageDigest, extremeWingCfgDevIfVlanOspfOspfBandWidth, extremeWingCfgDevIfVlanOspfMsgDigestKeyId,
				extremeWingCfgDevIfVlanOspfMsgDigestMessageDigest, extremeWingStatsDevl2tpv3TunnelEncapsulationProtocol, extremeWingStatsDevl2tpv3SessionsRxPktCounter,
				extremeWingStatsDevl2tpv3SessionsRxBytesCounter, extremeWingStatsDevl2tpv3SessionsTxPktCounter, extremeWingStatsDevl2tpv3SessionsTxBytesCounter,
				extremeWingStatsDevl2tpv3SessionsNumDroppedPkts, extremeWingCfgProfIfRadioAntennaDowntilt, extremeWingCfgProfIfRadioExtendedRange, extremeWingCfgDevIfRadioAntennaDowntilt, extremeWingCfgDevIfRadioExtendedRange,
				extremeWingCfgProfIfT1E1Media, extremeWingCfgProfIfT1E1ClockMode, extremeWingCfgProfIfT1E1HighImpedance, extremeWingCfgProfIfT1E1LineBuildOut, extremeWingCfgProfIfT1E1LineEncoding,
				extremeWingCfgProfIfT1E1RxSensitivityLevel, extremeWingCfgProfIfSerialAuthentication, extremeWingCfgProfIfSerialEncapsulation, extremeWingCfgProfIfSerialLocalIpAddress, extremeWingCfgProfIfSerialUsername,
				extremeWingCfgProfIfSerialPassword, extremeWingCfgProfIfSerialRemoteIpSubnet, extremeWingCfgDevIfT1E1Media, extremeWingCfgDevIfT1E1ClockMode, extremeWingCfgDevIfT1E1HighImpedance,
				extremeWingCfgDevIfT1E1LineBuildOut, extremeWingCfgDevIfT1E1LineEncoding, extremeWingCfgDevIfT1E1RxSensitivityLevel, extremeWingCfgDevIfSerialAuthentication, extremeWingCfgDevIfSerialEncapsulation,
				extremeWingCfgDevIfSerialLocalIpAddress, extremeWingCfgDevIfSerialUsername, extremeWingCfgDevIfSerialPassword, extremeWingCfgDevIfSerialRemoteIpSubnet, 
				extremeWingCfgProfIfDot1xAuthHostMode, extremeWingCfgProfIfDot1xAuthGuestVlan, extremeWingCfgProfIfDot1xAuthPortControl, 
				extremeWingCfgProfIfDot1xAuthReauthenticate, extremeWingCfgProfIfDot1xAuthMaxReauthCount, extremeWingCfgProfIfDot1xAuthMaxReq, 
				extremeWingCfgProfIfDot1xAuthQuietPeriod, extremeWingCfgProfIfDot1xAuthReauthPeriod, extremeWingCfgDevIfDot1xAuthHostMode, 
				extremeWingCfgDevIfDot1xAuthGuestVlan, extremeWingCfgDevIfDot1xAuthPortControl, extremeWingCfgDevIfDot1xAuthReauthenticate, 
				extremeWingCfgDevIfDot1xAuthMaxReauthCount, extremeWingCfgDevIfDot1xAuthMaxReq, extremeWingCfgDevIfDot1xAuthQuietPeriod, 
				extremeWingCfgDevIfDot1xAuthReauthPeriod, extremeWingCfgProfDot1xSysAuthCtrl, extremeWingCfgProfDot1xGuestVlanCtrl, 
				extremeWingCfgProfDot1xAaaPolicy, extremeWingCfgDevDot1xSysAuthCtrl, extremeWingCfgDevDot1xGuestVlanCtrl, 
				extremeWingCfgDevDot1xAaaPolicy, extremeWingCfgProfCriticalResourcesPort, extremeWingCfgDevCriticalResourcesPort, 
				extremeWingStatsDevCrmMonitorInterval, extremeWingStatsDevCrmCriticalResVia, 	extremeWingStatsDevCrmCriticalResStatus, 
				extremeWingStatsDevCrmCriticalResErrorReason, 	extremeWingStatsDevCrmCriticalResMode, extremeWingStatsDevCrmCriticalResResAddr, 
				extremeWingStatsDevCrmCriticalResResMonitorMode, extremeWingStatsDevCrmCriticalResResArpVlan, extremeWingStatsDevCrmCriticalResResStatus, 
				extremeWingStatsDevCrmCriticalResResArpPort, extremeWingCfgProfMeshpointDevName, extremeWingCfgProfMeshpointDevIsRootDev, 
				extremeWingCfgProfMeshpointDevPreferredRoot, extremeWingCfgProfMeshpointDevPreferredNeighbor, extremeWingCfgProfMeshpointDevPreferredIf, extremeWingCfgProfMeshpointDevPathMethod,
				extremeWingCfgProfMeshpointDevMonitorCriticalResources, extremeWingCfgProfMeshpointDevMonitorPriPortLink, extremeWingCfgProfMeshpointDevHysteresisPeriod,
				extremeWingCfgProfMeshpointDevHysteresisSnrDelta, extremeWingCfgProfMeshpointDevHysteresisSnrMin, extremeWingCfgProfMeshpointDevExcludeWiredPeer, 
				extremeWingCfgDevMeshpointDevName, extremeWingCfgDevMeshpointDevIsRootDev, extremeWingCfgDevMeshpointDevPreferredRoot, 
				extremeWingCfgDevMeshpointDevPreferredNeighbor, extremeWingCfgDevMeshpointDevPreferredIf, extremeWingCfgSmartRfOcsMeshpointA,extremeWingCfgDevMeshpointDevMonitorCriticalResources, extremeWingCfgDevMeshpointDevMonitorPriPortLink,  
				extremeWingCfgSmartRfOcsMeshpointBg, extremeWingCfgMcxMeshpointName, extremeWingCfgMcxMeshpointShutdown, extremeWingCfgMcxMeshpointMeshid, 
				extremeWingCfgMcxMeshpointDescription, extremeWingCfgMcxMeshpointBeaconFormat, extremeWingCfgMcxMeshpointControlVlan, 
				extremeWingCfgMcxMeshpointNeighborInactivityTimeout, extremeWingCfgMcxMeshpointQosPolicy, extremeWingCfgMcxMeshpointSecurityMode, 
				extremeWingCfgMcxMeshpointWpa2Psk, extremeWingCfgMcxMeshpointWpa2KeyRotationUnicast, extremeWingCfgMcxMeshpointWpa2KeyRotationBroadcast, extremeWingCfgMcxMeshpointIsRoot,  
				extremeWingCfgMcxMeshpointQosName, extremeWingCfgMcxMeshpointQosMeshpointRlDownEnable, extremeWingCfgMcxMeshpointQosMeshpointRlDownRate, 
				extremeWingCfgMcxMeshpointQosMeshpointRlDownBurstSize, extremeWingCfgMcxMeshpointQosMeshpointRlDownThreshBackground, 
				extremeWingCfgMcxMeshpointQosMeshpointRlDownThreshBestEffort, extremeWingCfgMcxMeshpointQosMeshpointRlDownThreshVoice, 
				extremeWingCfgMcxMeshpointQosMeshpointRlDownThreshVideo, extremeWingCfgMcxMeshpointQosMeshpointRlUpEnable, extremeWingCfgMcxMeshpointQosMeshpointRlUpRate, 
				extremeWingCfgMcxMeshpointQosMeshpointRlUpBurstSize, extremeWingCfgMcxMeshpointQosMeshpointRlUpThreshBackground, 
				extremeWingCfgMcxMeshpointQosMeshpointRlUpThreshBestEffort, extremeWingCfgMcxMeshpointQosMeshpointRlUpThreshVoice, 
				extremeWingCfgMcxMeshpointQosMeshpointRlUpThreshVideo, extremeWingCfgMcxMeshpointQosNeighborRlDownEnable, 
				extremeWingCfgMcxMeshpointQosNeighborRlDownRate, extremeWingCfgMcxMeshpointQosNeighborRlDownBurstSize, 
				extremeWingCfgMcxMeshpointQosNeighborRlDownThreshBackground, extremeWingCfgMcxMeshpointQosNeighborRlDownThreshBestEffort, 
				extremeWingCfgMcxMeshpointQosNeighborRlDownThreshVoice, extremeWingCfgMcxMeshpointQosNeighborRlDownThreshVideo, 
				extremeWingCfgMcxMeshpointQosNeighborRlUpEnable, extremeWingCfgMcxMeshpointQosNeighborRlUpRate, extremeWingCfgMcxMeshpointQosNeighborRlUpBurstSize, 
				extremeWingCfgMcxMeshpointQosNeighborRlUpThreshBackground, extremeWingCfgMcxMeshpointQosNeighborRlUpThreshBestEffort, 
				extremeWingCfgMcxMeshpointQosNeighborRlUpThreshVoice, extremeWingCfgMcxMeshpointQosNeighborRlUpThreshVideo, extremeWingCfgMcxMeshpointQosAddr, 
				extremeWingCfgMcxMeshpointQosPriority, extremeWingCfgProfIfMeshpointBssmapMeshpoint, extremeWingCfgProfIfMeshpointBssmapBss, 
				extremeWingCfgDevIfMeshpointBssmapMeshpoint, extremeWingCfgDevIfMeshpointBssmapBss, extremeWingStatsDevWlMcxMeshpointMpid, extremeWingStatsDevWlMcxMeshpointName, 
				extremeWingStatsDevWlMcxMeshpointHostname, extremeWingStatsDevWlMcxMeshpointDeviceMac, extremeWingStatsDevWlMcxMeshpointIsRoot, 
				extremeWingStatsDevWlMcxMeshpointIsCfgRoot, extremeWingStatsDevWlMcxMeshpointRootMpid, extremeWingStatsDevWlMcxMeshpointNextHop, 
				extremeWingStatsDevWlMcxMeshpointRootHops, extremeWingStatsDevWlMcxMeshpointIfidCnt, extremeWingStatsDevWlMcxMeshpointIfid, 
				extremeWingStatsDevWlMcxMeshpointIfidDataDesc, extremeWingStatsDevWlMcxMeshpointStatsName, extremeWingStatsDevWlMcxMeshpointStatsMeshid, 
				extremeWingStatsDevWlMcxMeshpointStatsNumRadios, extremeWingStatsDevWlMcxMeshpointStatsNumNeighbors, 
				extremeWingStatsDevWlMcxMeshpointStatsTxBytes, extremeWingStatsDevWlMcxMeshpointStatsRxBytes, extremeWingStatsDevWlMcxMeshpointStatsTxPkts, 
				extremeWingStatsDevWlMcxMeshpointStatsRxPkts, extremeWingStatsDevWlMcxMeshpointStatsTxDropped, extremeWingStatsDevWlMcxMeshpointStatsRxErrors, 
				extremeWingStatsDevWlMcxMeshpointStatsTIndex, extremeWingStatsDevWlMcxMeshpointStatsTotalBytes, extremeWingStatsDevWlMcxMeshpointStatsTotalPkts, 
				extremeWingStatsDevWlMcxMeshpointStatsTxBps, extremeWingStatsDevWlMcxMeshpointStatsRxBps, extremeWingStatsDevWlMcxMeshpointStatsTotalBps, 
				extremeWingStatsDevWlMcxMeshpointStatsTxPps, extremeWingStatsDevWlMcxMeshpointStatsRxPps, extremeWingStatsDevWlMcxMeshpointStatsTotalPps, 
				extremeWingStatsDevWlMcxMeshpointStatsTxBcmcPkts, extremeWingStatsDevWlMcxMeshpointStatsRxBcmcPkts, extremeWingStatsDevWlMcxMeshpointStatsTotalBcmcPkts, 
				extremeWingStatsDevWlMcxMeshpointStatsTxMgmtPkts, extremeWingStatsDevWlMcxMeshpointStatsRxMgmtPkts, extremeWingStatsDevWlMcxMeshpointStatsTotalMgmtPkts, 
				extremeWingStatsDevWlMcxMeshpointStatsMaxUserRate, extremeWingStatsDevWlMcxMeshpointNeighborsMpid, 
				extremeWingStatsDevWlMcxMeshpointNeighborsName, extremeWingStatsDevWlMcxMeshpointNeighborsHostname, extremeWingStatsDevWlMcxMeshpointNeighborsDeviceMac, 
				extremeWingStatsDevWlMcxMeshpointNeighborsNumEntries, extremeWingStatsDevWlMcxMeshpointNeighborsEntriesNeighborIfid, 
				extremeWingStatsDevWlMcxMeshpointNeighborsEntriesNeighborMpid, extremeWingStatsDevWlMcxMeshpointNeighborsEntriesBoundRoot, 
				extremeWingStatsDevWlMcxMeshpointNeighborsEntriesRootMetric, extremeWingStatsDevWlMcxMeshpointNeighborsEntriesRootHops, 
				extremeWingStatsDevWlMcxMeshpointNeighborsEntriesValid, extremeWingStatsDevWlMcxMeshpointNeighborsEntriesRoot, 
				extremeWingStatsDevWlMcxMeshpointNeighborsEntriesProxy, extremeWingStatsDevWlMcxMeshpointNeighborsEntriesGeoReference, 
				extremeWingStatsDevWlMcxMeshpointNeighborsEntriesMobile, extremeWingStatsDevWlMcxMeshpointNeighborsEntriesInterfaceId, 
				extremeWingStatsDevWlMcxMeshpointNeighborsEntriesAuthState, extremeWingStatsDevWlMcxMeshpointNeighborsEntriesRank, 
				extremeWingStatsDevWlMcxMeshpointNeighborsEntriesResourced, extremeWingStatsDevWlMcxMeshpointNeighborsEntriesLinkQuality, 
				extremeWingStatsDevWlMcxMeshpointNeighborsEntriesLinkMetric, extremeWingStatsDevWlMcxMeshpointNeighborsEntriesAge, 
				extremeWingStatsDevWlMcxMeshpointPathsMpid, extremeWingStatsDevWlMcxMeshpointPathsName, extremeWingStatsDevWlMcxMeshpointPathsHostname, 
				extremeWingStatsDevWlMcxMeshpointPathsDeviceMac, extremeWingStatsDevWlMcxMeshpointPathsNumEntries, 
				extremeWingStatsDevWlMcxMeshpointPathsEntriesDestMpid, extremeWingStatsDevWlMcxMeshpointPathsEntriesNextHopIfid, 
				extremeWingStatsDevWlMcxMeshpointPathsEntriesPathMetric, extremeWingStatsDevWlMcxMeshpointPathsEntriesHops, 
				extremeWingStatsDevWlMcxMeshpointPathsEntriesPathState, extremeWingStatsDevWlMcxMeshpointPathsEntriesBindState, 
				extremeWingStatsDevWlMcxMeshpointPathsEntriesValid, extremeWingStatsDevWlMcxMeshpointPathsEntriesRoot, extremeWingStatsDevWlMcxMeshpointPathsEntriesProxy, 
				extremeWingStatsDevWlMcxMeshpointPathsEntriesGeoReference, extremeWingStatsDevWlMcxMeshpointPathsEntriesMobile, 
				extremeWingStatsDevWlMcxMeshpointPathsEntriesDestinationSequence, extremeWingStatsDevWlMcxMeshpointPathsEntriesPathTimeout, 
				extremeWingStatsDevWlMcxMeshpointPathsEntriesNewRouteTimeout, extremeWingStatsDevWlMcxMeshpointPathsEntriesDestMintId, 
				extremeWingStatsDevWlMcxMeshpointRootsMpid, extremeWingStatsDevWlMcxMeshpointRootsName, extremeWingStatsDevWlMcxMeshpointRootsHostname, 
				extremeWingStatsDevWlMcxMeshpointRootsDeviceMac, extremeWingStatsDevWlMcxMeshpointRootsNumEntries, extremeWingStatsDevWlMcxMeshpointRootsEntriesRootMpid, 
				extremeWingStatsDevWlMcxMeshpointRootsEntriesNextHopIfid, extremeWingStatsDevWlMcxMeshpointRootsEntriesInterfaceId, 
				extremeWingStatsDevWlMcxMeshpointRootsEntriesRecommended, extremeWingStatsDevWlMcxMeshpointRootsEntriesBindFailed, 
				extremeWingStatsDevWlMcxMeshpointRootsEntriesPathFailed, extremeWingStatsDevWlMcxMeshpointRootsEntriesPathMetric, 
				extremeWingStatsDevWlMcxMeshpointRootsEntriesIfBias, extremeWingStatsDevWlMcxMeshpointRootsEntriesNeighborBias, 
				extremeWingStatsDevWlMcxMeshpointRootsEntriesRootBias, extremeWingStatsDevWlMcxMeshpointProxiesMpid, 
				extremeWingStatsDevWlMcxMeshpointProxiesName, extremeWingStatsDevWlMcxMeshpointProxiesHostname, extremeWingStatsDevWlMcxMeshpointProxiesDeviceMac, 
				extremeWingStatsDevWlMcxMeshpointProxiesNumEntries, extremeWingStatsDevWlMcxMeshpointProxiesEntriesProxyAddr, 
				extremeWingStatsDevWlMcxMeshpointProxiesEntriesProxyOwner, extremeWingStatsDevWlMcxMeshpointProxiesEntriesPersistence, 
				extremeWingStatsDevWlMcxMeshpointProxiesEntriesAge, extremeWingStatsDevWlMcxMeshpointProxiesEntriesVlan, extremeWingStatsDevWlMcxMeshpointLsaMpid, 
				extremeWingStatsDevWlMcxMeshpointLsaName, extremeWingStatsDevWlMcxMeshpointLsaHostname, extremeWingStatsDevWlMcxMeshpointLsaDeviceMac, 
				extremeWingStatsDevWlMcxMeshpointLsaNumEntries, extremeWingStatsDevWlMcxMeshpointLsaMeshid, extremeWingStatsDevWlMcxMeshpointLsaR0Valid, 
				extremeWingStatsDevWlMcxMeshpointLsaR0mdid, extremeWingStatsDevWlMcxMeshpointLsaR0khid, extremeWingStatsDevWlMcxMeshpointLsaEntriesLinkAddr, 
				extremeWingStatsDevWlMcxMeshpointLsaEntriesInterfaceId, extremeWingStatsDevWlMcxMeshpointLsaEntriesKeepAlive, 
				extremeWingStatsDevWlMcxMeshpointLsaEntriesLinkState, extremeWingStatsDevWlMcxMeshpointLsaEntriesLinkTimeout, 
				extremeWingStatsDevWlMcxMeshpointMcastPathsMpid, extremeWingStatsDevWlMcxMeshpointMcastPathsName, extremeWingStatsDevWlMcxMeshpointMcastPathsHostname, 
				extremeWingStatsDevWlMcxMeshpointMcastPathsDeviceMac, extremeWingStatsDevWlMcxMeshpointMcastPathsNumEntries, 
				extremeWingStatsDevWlMcxMeshpointMcastPathsEntriesGroupAddr, extremeWingStatsDevWlMcxMeshpointMcastPathsEntriesMemberAddr, 
				extremeWingStatsDevWlMcxMeshpointMcastPathsEntriesPathTimeout, 
				extremeWingStatsRfdSmartRfRadioInfoMac, extremeWingStatsRfdSmartRfRadioInfoApMac, extremeWingStatsRfdSmartRfRadioInfoHostname, 
				extremeWingStatsRfdSmartRfRadioInfoChannel, extremeWingStatsRfdSmartRfRadioInfoPower, extremeWingStatsRfdSmartRfRadioInfoRadioIdx, 
				extremeWingStatsRfdSmartRfRadioInfoState, extremeWingStatsRfdSmartRfRadioInfoType, extremeWingStatsRfdSmartRfRadioActMac, 
				extremeWingStatsRfdSmartRfRadioActApMac, extremeWingStatsRfdSmartRfRadioActType, extremeWingStatsRfdSmartRfRadioActPowerChanges, 
				extremeWingStatsRfdSmartRfRadioActChannelChanges, extremeWingStatsRfdSmartRfRadioActCoverageChanges, extremeWingStatsRfdSmartRfRadioNeighborsMac, 
				extremeWingStatsRfdSmartRfRadioNeighborsApMac, extremeWingStatsRfdSmartRfRadioNeighborsHostname, extremeWingStatsRfdSmartRfRadioNeighborsChannel, 
				extremeWingStatsRfdSmartRfRadioNeighborsRadioIdx, extremeWingStatsRfdSmartRfRadioNeighborsType, extremeWingStatsRfdSmartRfRadioNeighborsNeighborsMac, 
				extremeWingStatsRfdSmartRfRadioNeighborsNeighborsApMac, extremeWingStatsRfdSmartRfRadioNeighborsNeighborsChannel, 
				extremeWingStatsRfdSmartRfRadioNeighborsNeighborsPower, extremeWingStatsRfdSmartRfRadioNeighborsNeighborsAttenuation, 
				extremeWingStatsRfdSmartRfRadioNeighborsNeighborsRadioIdx, extremeWingStatsRfdSmartRfRadioEnergyMac, 
				extremeWingStatsRfdSmartRfRadioEnergyApMac, extremeWingStatsRfdSmartRfRadioEnergyHostname, extremeWingStatsRfdSmartRfRadioEnergyChannel, 
				extremeWingStatsRfdSmartRfRadioEnergyRadioIdx, extremeWingStatsRfdSmartRfRadioEnergyType, extremeWingStatsRfdSmartRfRadioEnergyEnergyChannel, 
				extremeWingStatsRfdSmartRfRadioEnergyEnergyExternal, extremeWingStatsRfdSmartRfRadioEnergyEnergyNeighbor, extremeWingStatsRfdSmartRfRadioEnergyEnergyNoise, 
				extremeWingStatsRfdSmartRfRadioEnergyEnergyTotal, extremeWingStatsRfdSmartRfRadioNonSsmMac, extremeWingStatsRfdSmartRfRadioNonSsmInfoApMac, 
				extremeWingStatsRfdSmartRfRadioNonSsmHostname, extremeWingStatsRfdSmartRfRadioNonSsmChannel, extremeWingStatsRfdSmartRfRadioNonSsmPower, 
				extremeWingStatsRfdSmartRfRadioNonSsmRadioIdx, extremeWingStatsRfdSmartRfRadioNonSsmState, extremeWingStatsRfdSmartRfRadioNonSsmInfoType, 
				extremeWingStatsRfdSmartRfRadioNonSsmActApMac, extremeWingStatsRfdSmartRfRadioNonSsmActType, extremeWingStatsRfdSmartRfRadioNonSsmPowerChanges, 
				extremeWingStatsRfdSmartRfRadioNonSsmChannelChanges, extremeWingStatsRfdSmartRfRadioNonSsmCoverageChanges, extremeWingStatsRfdSmartRfRadioNonSsmNeighborsMac, 
				extremeWingStatsRfdSmartRfRadioNonSsmNeighborsApMac, extremeWingStatsRfdSmartRfRadioNonSsmNeighborsChannel, extremeWingStatsRfdSmartRfRadioNonSsmNeighborsPower, 
				extremeWingStatsRfdSmartRfRadioNonSsmNeighborsAttenuation, extremeWingStatsRfdSmartRfRadioNonSsmNeighborsRadioIdx, 
				extremeWingStatsRfdSmartRfRadioNonSsmEnergyChannel, extremeWingStatsRfdSmartRfRadioNonSsmEnergyExternal, extremeWingStatsRfdSmartRfRadioNonSsmEnergyNeighbor, 
				extremeWingStatsRfdSmartRfRadioNonSsmEnergyNoise, extremeWingStatsRfdSmartRfRadioNonSsmEnergyTotal, 
				extremeWingStatsRfdSmartRfApMac, extremeWingStatsRfdSmartRfApNeighborsMac, extremeWingStatsRfdSmartRfApNeighborsApMac, 
				extremeWingStatsRfdSmartRfApNeighborsHostname, extremeWingStatsRfdSmartRfApNeighborsChannel, extremeWingStatsRfdSmartRfApNeighborsPower, 
				extremeWingStatsRfdSmartRfApNeighborsAttenuation, extremeWingStatsRfdSmartRfApNeighborsInterference, extremeWingStatsRfdSmartRfApNeighborsRadioIdx, 
				extremeWingStatsRfdSmartRfApNeighborsListenerIdx, extremeWingStatsRfdSmartRfApNeighborsListenerMac, extremeWingStatsRfdSmartRfApNeighborsType, 
				extremeWingStatsRfdSmartRfHighActRadiosMac, extremeWingStatsRfdSmartRfHighActRadiosApMac, extremeWingStatsRfdSmartRfHighActRadiosHostname, 
				extremeWingStatsRfdSmartRfHighActRadiosType, extremeWingStatsRfdSmartRfHighActRadiosPowerChanges, extremeWingStatsRfdSmartRfHighActRadiosChannelChanges, 
				extremeWingStatsRfdSmartRfHighActRadiosCoverageChanges, extremeWingStatsRfdSmartRfHistoryTime, extremeWingStatsRfdSmartRfHistoryApMac, 
				extremeWingStatsRfdSmartRfHistoryHostname, extremeWingStatsRfdSmartRfHistoryRadioMac, extremeWingStatsRfdSmartRfHistoryRadioIdx, extremeWingStatsRfdSmartRfHistoryOldValue, 
				extremeWingStatsRfdSmartRfHistoryNewValue, extremeWingStatsRfdSmartRfHistoryDaysTime, extremeWingStatsRfdSmartRfHistoryDaysPowerChanges, 
				extremeWingStatsRfdSmartRfHistoryDaysChannelChanges, extremeWingStatsRfdSmartRfHistoryDaysCoverageChanges, extremeWingStatsRfdSmartRfHistoryHoursTime, 
				extremeWingStatsRfdSmartRfHistoryHoursPowerChanges, extremeWingStatsRfdSmartRfHistoryHoursChannelChanges, extremeWingStatsRfdSmartRfHistoryHoursCoverageChanges, 
				extremeWingStatsRfdSmartRfDashboardHistoryDetails, extremeWingStatsRfdSmartRfDashboardHistoryPowerChanges, extremeWingStatsRfdSmartRfDashboardHistoryChannelChanges, 
				extremeWingStatsRfdSmartRfDashboardHistoryCoverageChanges, extremeWingStatsRfdSmartRfCalibrateResultMac, extremeWingStatsRfdSmartRfCalibrateResultResultMac, 
				extremeWingStatsRfdSmartRfCalibrateResultApMac, extremeWingStatsRfdSmartRfCalibrateResultChannel, extremeWingStatsRfdSmartRfCalibrateResultOldChannel, 
				extremeWingStatsRfdSmartRfCalibrateResultPower, extremeWingStatsRfdSmartRfCalibrateResultOldPower, extremeWingStatsRfdSmartRfCalibrateResultRadioIdx, 
				extremeWingStatsRfdSmartRfCalibrateResultState, extremeWingStatsRfdSmartRfCalibrateResultType, extremeWingStatsRfdSmartRfCalibrateResultSmartSensor, extremeWingStatsDevIfStatusOper,
				extremeWingStatsNocAdoptDevProductName, extremeWingStatsDevAdoptDevProductName, extremeWingStatsRfdWlRadioProtocol, extremeWingEventSourceHostname,
				extremeWingStatsDevWlApInfoMac, extremeWingStatsDevWlApInfoFaultDetected,
				extremeWingStatsDevWlApInfoNumRadios, extremeWingStatsDevWlApInfoNumClients, extremeWingStatsDevWlApInfoLastCalTime, extremeWingStatsDevWlApInfoType, extremeWingStatsDevWlApInfoStatsMode,
				extremeWingStatsDevWlApInfoStatsInterval, extremeWingStatsDevWlApInfoHostname, extremeWingStatsDevWlApInfoRfDomainName, extremeWingStatsDevWlApInfoLocation, extremeWingStatsDevWlApInfoAdoptedTo,
				extremeWingStatsDevWlApInfoIp, extremeWingStatsDevWlClientStatMac, extremeWingStatsDevWlClientStatMacName, extremeWingStatsDevWlClientStatVendor, extremeWingStatsDevWlClientStatAp,
				extremeWingStatsDevWlClientStatTxBytes, extremeWingStatsDevWlClientStatRxBytes, extremeWingStatsDevWlClientStatTxPkts, extremeWingStatsDevWlClientStatRxPkts, extremeWingStatsDevWlClientStatTxDropped,
				extremeWingStatsDevWlClientStatRxErrors, extremeWingStatsDevWlClientStatTIndex, extremeWingStatsDevWlClientStatTxBps, extremeWingStatsDevWlClientStatRxBps, extremeWingStatsDevWlClientStatSignal,
				extremeWingStatsDevWlClientStatNoise, extremeWingStatsDevWlClientStatSnr, extremeWingStatsDevWlClientStatTxRate, extremeWingStatsDevWlClientStatRxRate, extremeWingStatsDevWlClientStatErrorRate,
				extremeWingStatsDevWlClientStatQIndex, extremeWingStatsDevWlRadioId, extremeWingStatsDevWlRadioDeviceMac, extremeWingStatsDevWlRadioAlias, extremeWingStatsDevWlRadioMac, extremeWingStatsDevWlRadioType,
				extremeWingStatsDevWlRadioHostname, extremeWingStatsDevWlRadioRfdName, extremeWingStatsDevWlRadioLocation, extremeWingStatsDevWlRadioState, extremeWingStatsDevWlRadioCurChannel,
				extremeWingStatsDevWlRadioConfigChannel, extremeWingStatsDevWlRadioCurPower, extremeWingStatsDevWlRadioConfigPower, extremeWingStatsDevWlRadioMaxUserRate, extremeWingStatsDevWlRadioNumClient,
				extremeWingStatsDevWlRadioProtocol, extremeWingStatsDevWlRadioStatId, extremeWingStatsDevWlRadioStatDeviceMac, extremeWingStatsDevWlRadioStatAlias, extremeWingStatsDevWlRadioStatMac,
				extremeWingStatsDevWlRadioStatType, extremeWingStatsDevWlRadioStatTxBytes, extremeWingStatsDevWlRadioStatRxBytes, extremeWingStatsDevWlRadioStatTxPkts, extremeWingStatsDevWlRadioStatRxPkts,
				extremeWingStatsDevWlRadioStatTxDropped, extremeWingStatsDevWlRadioStatRxErrors, extremeWingStatsDevWlRadioStatTIndex, extremeWingStatsDevWlRadioStatTxBps, extremeWingStatsDevWlRadioStatRxBps,
				extremeWingStatsDevWlRadioStatSignal, extremeWingStatsDevWlRadioStatNoise, extremeWingStatsDevWlRadioStatSnr, extremeWingStatsDevWlRadioStatTxRate, extremeWingStatsDevWlRadioStatRxRate,
				extremeWingStatsDevWlRadioStatErrorRate, extremeWingStatsDevWlRadioStatQIndex, extremeWingStatsDevWlRadioStatNumClients, extremeWingStatsDevWlRadioStatNumBClients,
				extremeWingStatsDevWlRadioStatNumBgClients, extremeWingStatsDevWlRadioStatNumBgnClients, extremeWingStatsDevWlRadioStatNumAClients, extremeWingStatsDevWlRadioStatNumAnClients,
				extremeWingStatsDevWlRadioStatMediumErrorRate, extremeWingStatsDevWlRadioStatTxRetries, extremeWingStatsDevWlRadioStatTxRetriedBytes,
				extremeWingStatsDevCdpNeighborAdvertisedVersion, extremeWingStatsDevCdpNeighborVtpDomain, extremeWingStatsDevCdpNeighborNativeVlan, extremeWingStatsDevCdpNeighborUntrustedPortCos, 
				extremeWingStatsDevCdpNeighborMgmtAddrList, extremeWingStatsDevCdpNeighborVersion, extremeWingStatsNocAdoptDevProductName, extremeWingStatsDevAdoptDevProductName, 
				extremeWingStatsRfdWlRadioProtocol, extremeWingActionLocatorOnInDuration, extremeWingActionLocatorOnInMac, extremeWingActionLocatorOnOutStatus, extremeWingActionLocatorOnOutMessage,
				extremeWingActionLocatorOnRun, extremeWingActionLocatorOffInMac, extremeWingActionLocatorOffOutStatus, extremeWingActionLocatorOffOutMessage, extremeWingActionLocatorOffRun,
				extremeWingCfgAltDevIfMacInAcl, extremeWingCfgAltDevIfRadioBssmapWlan, extremeWingCfgAltDevIfRadioBssmapBss, extremeWingCfgAltDevIfRadioBssmapPrimary, extremeWingStatsDevIfStatusOper,
				extremeWingCfgCaptPrtlExternalLoginUrl, extremeWingCfgCaptPrtlExternalWelcomeUrl, extremeWingCfgCaptPrtlExternalFailUrl, extremeWingCfgCaptPrtlExternalAgreementUrl, extremeWingCfgDevIfRadioOperMode,
				extremeWingActionLoadApUpgradeImageFileInProductName, extremeWingActionLoadApUpgradeImageFileInFileUrl, extremeWingActionLoadApUpgradeImageFileOutStatus, extremeWingActionLoadApUpgradeImageFileOutMessage, extremeWingActionLoadApUpgradeImageFileRun,
				extremeWingActionClearApUpgradeHistoryInScope, extremeWingActionClearApUpgradeHistoryInRfDomainName, extremeWingActionClearApUpgradeHistoryRun,
				extremeWingActionApUpgradeInApList, extremeWingActionApUpgradeInApProduct, extremeWingActionApUpgradeInNoViaRfDomain, extremeWingActionApUpgradeInRfDomainName,
				extremeWingActionApUpgradeInUpgradeTime, extremeWingActionApUpgradeInRebootTime, extremeWingActionApUpgradeInNoReboot, extremeWingActionApUpgradeInStaggeredReboot, extremeWingActionApUpgradeInScope,
				extremeWingActionApUpgradeRun, extremeWingActionApUpgradeCancelInApList, extremeWingActionApUpgradeCancelInApProduct,
				extremeWingActionApUpgradeCancelInRfDomainName, extremeWingActionApUpgradeCancelInScope, extremeWingActionApUpgradeCancelOutStatus, extremeWingActionApUpgradeCancelOutMessage, extremeWingActionApUpgradeCancelRun, extremeWingActionExportMacUserDBInFileURL, extremeWingActionExportMacUserDBOutStatus, extremeWingActionExportMacUserDBOutMessage,
                                extremeWingActionExportMacUserDBRun, extremeWingActionImportMacUserDBInFileURL, extremeWingActionImportMacUserDBOutStatus, extremeWingActionImportMacUserDBOutMessage, extremeWingActionImportMacUserDBRun,
                                extremeWingActionDeleteUserFromMacUserDBInUser, extremeWingActionDeleteUserFromMacUserDBOutStatus, extremeWingActionDeleteUserFromMacUserDBOutMessage, extremeWingActionDeleteUserFromMacUserDBRun, extremeWingCfgWlanMacRegistrationEnable,
                                extremeWingCfgWlanMacRegistrationGroupName, extremeWingCfgWlanMacRegistrationExpiryTime, extremeWingCfgWlanMacRegistrationExternalEnable, extremeWingCfgWlanMacRegistrationExternalHost, extremeWingCfgWlanMacRegistrationExternalProxyMode,
				extremeWingStatsDevWlMcxMeshpointNeighborsEntriesIndex, extremeWingStatsDevWlMcxMeshpointPathsEntriesIndex, extremeWingStatsDevWlMcxMeshpointRootsEntriesIndex, extremeWingStatsDevWlMcxMeshpointProxiesEntriesIndex, extremeWingStatsDevWlMcxMeshpointLsaEntriesIndex, extremeWingStatsDevWlMcxMeshpointMcastPathsEntriesIndex,
				extremeWingStatsNocLoadApImageStatus, extremeWingStatsNocLoadApImageStatusMsg, extremeWingStatsNocSysImgUpgradeStatus, extremeWingStatsNocSysImgUpgradeTime, extremeWingStatsNocSysImgUpgradeMsg,
				extremeWingActionDeviceStartUpgradeInMac, extremeWingActionDeviceStartUpgradeInUrlPath, extremeWingActionDeviceStartUpgradeOutStatus, extremeWingActionDeviceStartUpgradeOutMessage, extremeWingActionDeviceStartUpgradeRun, 
				extremeWingActionDeviceAbortUpgradeInMac, extremeWingActionDeviceAbortUpgradeOutStatus, extremeWingActionDeviceAbortUpgradeOutMessage, extremeWingActionDeviceAbortUpgradeRun,
				extremeWingCfgWlanServiceMonitorAaaServer, extremeWingCfgWlanServiceMonitorCaptPrtlExtServer, extremeWingCfgWlanServiceMonitorAdoptionName, extremeWingCfgWlanServiceMonitorAdoptionEnable, extremeWingCfgWlanServiceMonitorAdoptionVlan,
				extremeWingCfgWlanServiceMonitorDhcpName, extremeWingCfgWlanServiceMonitorDhcpEnable, extremeWingCfgWlanServiceMonitorDhcpVlan, extremeWingCfgWlanServiceMonitorDhcpCrmName,
				extremeWingCfgCaptPrtlInternalPageNoServDescription, extremeWingCfgCaptPrtlInternalPageNoServFooter, extremeWingCfgCaptPrtlInternalPageNoServHeader, extremeWingCfgCaptPrtlInternalPageNoServMainLogoUrl, extremeWingCfgCaptPrtlInternalPageNoServSmallLogoUrl, extremeWingCfgCaptPrtlInternalPageNoServTitle, 
				extremeWingCfgDevMeshpointDevPathMethod, extremeWingCfgDevMeshpointDevHysteresisPeriod, extremeWingCfgDevMeshpointDevHysteresisSnrDelta, extremeWingCfgDevMeshpointDevHysteresisSnrMin, extremeWingCfgDevMeshpointDevExcludeWiredPeer,
				extremeWingCfgDevBridgeVlanTunnelOverLevel2, extremeWingCfgProfBridgeVlanTunnelOverLevel2, extremeWingCfgWlanControllerAssistedMobility, extremeWingCfgProfRaidAlarmEnable, extremeWingCfgDevRaidAlarmEnable, 
				extremeWingStatsDevRaidStatusSize, extremeWingStatsDevRaidStatusState, extremeWingStatsDevRaidStatusAlarmEnable, extremeWingStatsDevRaidStatusDate, 
				extremeWingStatsDevRaidStatusResult, extremeWingStatsDevRaidStatusPhyDriveSlot, extremeWingStatsDevRaidStatusPhyDriveState, 
				extremeWingActionRaidManageArrayCommand, extremeWingActionRaidManageArrayStatus, extremeWingActionRaidManageArrayMessage, extremeWingActionRaidManageArrayRun, 
				extremeWingActionRaidManageDriveSelect, extremeWingActionRaidManageDriveCommand, extremeWingActionRaidManageDriveStatus, extremeWingActionRaidManageDriveMessage, extremeWingActionRaidManageDriveRun,
				extremeWingCfgWlanVlanRowStatus, extremeWingCfgWlanRowStatus, extremeWingCfgDevIfVlanRowStatus, extremeWingCfgWlanTimeBasedAccessDays, extremeWingCfgWlanTimeBasedAccessStartTime, extremeWingCfgWlanTimeBasedAccessEndTime, extremeWingCfgWlanTimeBasedAccessRowStatus,  
				extremeWingActionLocatorOnRun, extremeWingActionLocatorOffInMac, extremeWingActionLocatorOffOutStatus, extremeWingActionLocatorOffOutMessage, extremeWingActionLocatorOffRun, extremeWingCfgDevGreFailoverRetries, extremeWingCfgDevGreFailoverPingIntv,extremeWingCfgDevGreDscpInPkt, extremeWingCfgDevGreDscpOutPkt, 
				extremeWingCfgDevGreNativeVlan, extremeWingCfgDevGreNativeTag, extremeWingCfgGreTunnelVlan,  
				extremeWingCfgDevGreTunnelName, extremeWingCfgDevGreTunnelPeerIp, extremeWingCfgDevGreTunnelPeerId, extremeWingCfgWlanDhcpOption82,
				extremeWingActionLocatorOnRun, extremeWingActionLocatorOffInMac, extremeWingActionLocatorOffOutStatus, extremeWingActionLocatorOffOutMessage, extremeWingActionLocatorOffRun,extremeWingStatsDevWlMcxMeshpointNeighborsEntriesIndex, 
				extremeWingStatsDevWlMcxMeshpointPathsEntriesIndex, extremeWingStatsDevWlMcxMeshpointRootsEntriesIndex, extremeWingStatsDevWlMcxMeshpointProxiesEntriesIndex, 
				extremeWingStatsDevWlMcxMeshpointLsaEntriesIndex, extremeWingStatsDevWlMcxMeshpointMcastPathsEntriesIndex, extremeWingCfgProfLed,
				extremeWingStatsNocAAPLicApCount, extremeWingStatsNocAAPLicApUsage, extremeWingtStatsNocDeviceType, extremeWingtStatsNocDevAdoptedCount, extremeWingStatsRfdTotalAdoptedDevices, extremeWingStatsDevApUpgradeResultStatus, extremeWingStatsDevApUpgradeResultMessage,
				extremeWingStatsDevGreInfoTunnelId, extremeWingStatsDevGreInfoTunnelCreated, extremeWingStatsDevGreInfoPeerIp, extremeWingStatsDevGreInfoRxPkt, extremeWingStatsDevGreInfoTxPkt, extremeWingStatsDevGreInfoPktDropped, extremeWingCfgWlanBridgingMode,
				extremeWingStatsDevWlGlobalRadioInfoNoOfAdopRadios, extremeWingStatsDevWlGlobalRadioInfoNoOfOnlineRadios, extremeWingStatsRfdCaptivePortalClientCp, extremeWingStatsRfdCaptivePortalClientIPv4, extremeWingStatsRfdCaptivePortalClientMac,
				extremeWingStatsRfdCaptivePortalClientSessTime, extremeWingStatsRfdCaptivePortalClientState, extremeWingStatsRfdCaptivePortalClientVlan, extremeWingStatsRfdCaptivePortalClientWlan, extremeWingStatsRfdCaptivePortalClientRxBytes,
				extremeWingStatsRfdCaptivePortalClientRxPkts, extremeWingStatsRfdCaptivePortalClientTxBytes, extremeWingStatsRfdCaptivePortalClientTxPkts, extremeWingStatsNocDevProductName, extremeWingStatsNocDevVersion, extremeWingStatsNocDevSerialNumber, extremeWingCfgProfEnvSensorHumidity, extremeWingCfgProfEnvSensorMotion,
                                extremeWingCfgProfEnvSensorTemperature, extremeWingCfgProfLightSensor, extremeWingCfgProfLightSensorThresholdRadioShutdown, extremeWingCfgProfLightSensorLowLimitThreshold, extremeWingCfgProfLightSensorHighLimitThreshold,
                                extremeWingCfgProfSharedSensorPollingInterval, extremeWingCfgDevEnvSensorHumidity, extremeWingCfgDevEnvSensorMotion, extremeWingCfgDevEnvSensorTemperature, extremeWingCfgDevLightSensor,
                                extremeWingCfgDevLightSensorThresholdRadioShutdown, extremeWingCfgDevLightSensorLowLimitThreshold, extremeWingCfgDevLightSensorHighLimitThreshold, extremeWingCfgDevSharedSensorPollingInterval, extremeWingCfgProfLightSensorHoldTime,
                                extremeWingCfgDevLightSensorHoldTime, extremeWingStatsDevClrApUpRfdHistResultMac, extremeWingStatsDevClrApUpRfdHistResultStatus, extremeWingStatsDevClrApUpRfdHistResultMessage,
				extremeWingStatsDevClrApUpNocHistResultMac, extremeWingStatsDevClrApUpNocHistResultStatus, extremeWingStatsDevClrApUpNocHistResultMessage, extremeWingCfgRadiusUserPolicyName, 
				extremeWingCfgRadiusUserPolicyRowStatus, extremeWingCfgRadiusUserName, extremeWingCfgRadiusUserRowStatus, extremeWingCfgRadiusUserPassword, extremeWingCfgRadiusUserIsGuest, extremeWingCfgRadiusUserGroupList,
				extremeWingCfgRadiusUserGroup, extremeWingCfgRadiusUserStartDate, extremeWingCfgRadiusUserStartTime, extremeWingCfgRadiusUserExpiryDate, extremeWingCfgRadiusUserExpiryTime, extremeWingCfgRadiusUserEmailId, extremeWingCfgRadiusUserTelephone,
				extremeWingCfgProfControllerHostForce, extremeWingCfgProfControllerHostRemoteVpnClient, extremeWingCfgDevControllerHostForce, extremeWingCfgDevControllerHostRremoteVpnClient,
                                extremeWingCfgDevControllerHostIPSecSecure, extremeWingCfgDevControllerHostIPSecGw, extremeWingCfgProfControllerHostIPSecSecure, extremeWingCfgProfControllerHostIPSecGw,
				extremeWingStatsDevVpnIkesaIndex, extremeWingStatsDevVpnIkesaVersion, extremeWingStatsDevVpnIkesapeer, extremeWingStatsDevVpnIkesaLocalIP, extremeWingStatsDevVpnIkesaMeBehindNat,
				extremeWingStatsDevVpnIkesaPeerBehindNat, extremeWingStatsDevVpnIkesaEncr, extremeWingStatsDevVpnIkesaHash, extremeWingStatsDevVpnIkesaDhGroup, extremeWingStatsDevVpnIkesaPolicyDes,
				extremeWingStatsDevVpnIkesaIkeSaLifetime, extremeWingStatsDevVpnIkesaIkeState, extremeWingStatsDevVpnIpsecSaPeer, extremeWingStatsDevVpnIpsecSaSpiIn, extremeWingStatsDevVpnIpsecSaSpiOut,
				extremeWingStatsDevVpnIpsecSaProtocol, extremeWingStatsDevVpnIpsecSaLocalIp, extremeWingStatsDevVpnIpsecSaState, extremeWingStatsDevVpnIpsecSaEncrAlgo, extremeWingStatsDevVpnIpsecSaAuthAlgo,
				extremeWingStatsDevVpnIpsecSaMode, extremeWingStatsDevVpnIpsecSaReplayEnabled, extremeWingStatsDevVpnIpsecSaReplayWindowSize, extremeWingStatsDevVpnIpsecSaReplaySequenceNumber,
				extremeWingStatsDevVpnIpsecSaNatPresent, extremeWingStatsDevVpnIpsecSaNatSport, extremeWingStatsDevVpnIpsecSaNatDport, extremeWingStatsDevVpnIpsecSaConfigAgeKb, extremeWingStatsDevVpnIpsecSaConfigAgeSeconds,
				extremeWingStatsDevVpnIpsecSaRemAgeKb, extremeWingStatsDevVpnIpsecSaRemAgeSeconds, extremeWingStatsDevVpnIpsecSaTrafficSelectorSourceSubnet, extremeWingStatsDevVpnIpsecSaTrafficSelectorDestinationSubnet,
				extremeWingStatsDevVpnIpsecSaTrafficSelectorSourcePort, extremeWingStatsDevVpnIpsecSaTrafficSelectorDestinationPort, extremeWingStatsDevVpnIpsecSaTrafficSelectorProtocol, extremeWingStatsDevVpnIpsecSaIpsIndex,
				extremeWingCfgProfMeshpointDevHysteresisRootSelSnrDelta, extremeWingCfgDevMeshpointDevHysteresisRootSelSnrDelta, extremeWingCfgAutoProvisionPolicyName, extremeWingCfgAutoProvisionPolicyDefaultAdoption,
				extremeWingCfgAutoProvisionPolicyRulePrecedence, extremeWingCfgAutoProvisionPolicyRuleOperation, extremeWingCfgAutoProvisionPolicyRuleDevice, extremeWingCfgAutoProvisionPolicyRuleProfileName,
				extremeWingCfgAutoProvisionPolicyRuleRfDomainName, extremeWingCfgAutoProvisionPolicyRuleControllerName, extremeWingCfgAutoProvisionPolicyRuleArea, extremeWingCfgAutoProvisionPolicyRuleFloor, extremeWingCfgAutoProvisionPolicyRuleType,
				extremeWingStatsDevAclIpAclStatsName, extremeWingStatsDevAclIpAclStatsRulePrecedence, extremeWingStatsDevAclIpAclStatsRuleFriendlyString, extremeWingStatsDevAclIpAclStatsRuleHitcount, extremeWingStatsDevAclIpAclStatsRuleHwHitcount, 
				extremeWingStatsDevAclIpAclStatsDetailName, extremeWingStatsDevAclIpAclStatsDetailRulePrecedence,extremeWingStatsDevAclIpAclStatsDetailRuleFriendlyString, extremeWingStatsDevAclIpAclStatsDetailRuleHitcount, extremeWingStatsDevAclMacAclStatsName, 
				extremeWingStatsDevAclMacAclStatsRulePrecedence, extremeWingStatsDevAclMacAclStatsRuleFriendlyString, extremeWingStatsDevAclMacAclStatsRuleHitcount, extremeWingStatsDevAclMacAclStatsRuleHwHitcount,
				extremeWingCfgDevMeshpointDevRootSelectMethod, extremeWingCfgProfMeshpointDevRootSelectMethod, extremeWingCfgProfMeshpointDevRootSelectCostRoot, extremeWingCfgDevMeshpointDevRootSelectCostRoot,
				extremeWingCfgDhcpSvrActCriteriaCriteria 
				}
			STATUS current
			DESCRIPTION 
				"This group is mandatory for all WiNG devices."
			::= { extremeWingGroups 1 }

		
		-- 1.3.6.1.4.1.1916.2.131.50.2.2.2
		extremeWingNotificationGroup NOTIFICATION-GROUP
				NOTIFICATIONS { extremeWingTrapGeneric, extremeWingTrapAaaRadiusDisconMsg, extremeWingTrapAaaRadiusVlanUpdate
				, extremeWingTrapAaaRadiusSessionNotStarted, extremeWingTrapAaaRadiusSessionExpired, extremeWingTrapAdvWipsAdvWipsEvent1
				, extremeWingTrapAdvWipsAdvWipsEvent2, extremeWingTrapAdvWipsAdvWipsEvent3, extremeWingTrapAdvWipsAdvWipsEvent10
				, extremeWingTrapAdvWipsAdvWipsEvent11, extremeWingTrapAdvWipsAdvWipsEvent12, extremeWingTrapAdvWipsAdvWipsEvent13
				, extremeWingTrapAdvWipsAdvWipsEvent14, extremeWingTrapAdvWipsAdvWipsEvent16, extremeWingTrapAdvWipsAdvWipsEvent19
				, extremeWingTrapAdvWipsAdvWipsEvent21, extremeWingTrapAdvWipsAdvWipsEvent25, extremeWingTrapAdvWipsAdvWipsEvent29
				, extremeWingTrapAdvWipsAdvWipsEvent47, extremeWingTrapAdvWipsAdvWipsEvent87, extremeWingTrapAdvWipsAdvWipsEvent105
				, extremeWingTrapAdvWipsAdvWipsEvent109, extremeWingTrapAdvWipsAdvWipsEvent110, extremeWingTrapAdvWipsAdvWipsEvent111
				, extremeWingTrapAdvWipsAdvWipsEvent112, extremeWingTrapAdvWipsAdvWipsEvent113, extremeWingTrapAdvWipsAdvWipsEvent114
				, extremeWingTrapAdvWipsAdvWipsEvent115, extremeWingTrapAdvWipsAdvWipsEvent116, extremeWingTrapAdvWipsAdvWipsEvent117
				, extremeWingTrapAdvWipsAdvWipsEvent118, extremeWingTrapAdvWipsAdvWipsEvent119, extremeWingTrapAdvWipsAdvWipsEvent120
				, extremeWingTrapAdvWipsAdvWipsEvent121, extremeWingTrapAdvWipsAdvWipsEvent142, extremeWingTrapAdvWipsAdvWipsEvent221
				, extremeWingTrapAdvWipsAdvWipsEvent222, extremeWingTrapAdvWipsAdvWipsEvent63, extremeWingTrapAdvWipsAdvWipsEvent26
				, extremeWingTrapAdvWipsAdvWipsEvent220, extremeWingTrapApAdopted, extremeWingTrapApUnadopted
				, extremeWingTrapApAdoptedToController, extremeWingTrapApOnline, extremeWingTrapApOffline
				, extremeWingTrapApReset, extremeWingTrapApAdoptionRedirected, extremeWingTrapApSwConnLost
				, extremeWingTrapApApAutoupTimeout, extremeWingTrapApApAutoupReboot, extremeWingTrapApApAutoupNoNeed
				, extremeWingTrapApApAutoupNeeded, extremeWingTrapApApAutoupDone, extremeWingTrapApApAutoupFail
				, extremeWingTrapApApAutoupVer, extremeWingTrapApNoImageFile, extremeWingTrapApImageParseFailure
				, extremeWingTrapApLegacyAutoUpdate, extremeWingTrapApApAdopted, extremeWingTrapApApUnadopted
				, extremeWingTrapApApResetDetected, extremeWingTrapApApResetRequest, extremeWingTrapApApTimeout
				, extremeWingTrapCaptivePortalAuthSuccess, extremeWingTrapCaptivePortalAuthFailed, extremeWingTrapCaptivePortalSessionTimeout
				, extremeWingTrapCaptivePortalClientDisconnect, extremeWingTrapCaptivePortalPurgeClient, extremeWingTrapCaptivePortalFlexLogAccess
				, extremeWingTrapCaptivePortalInactivityTimeout, extremeWingTrapCaptivePortalAllowAccess, extremeWingTrapCaptivePortalClientRemoved
				, extremeWingTrapCaptivePortalPageCreFailed, extremeWingTrapCaptivePortalDataLimitExceed, extremeWingTrapCaptivePortalVlanSwitch
				, extremeWingTrapCaptivePortalServerMonitorStateChange, extremeWingTrapCaptivePortalNoServicePageSent, extremeWingTrapCertmgrRsaKeyActionsSuccess
				, extremeWingTrapCertmgrRsaKeyActionsFailure, extremeWingTrapCertmgrCaCertActionsSuccess, extremeWingTrapCertmgrCaCertActionsFailure
				, extremeWingTrapCertmgrSrvCertActionsSuccess, extremeWingTrapCertmgrSvrCertActionsFailure, extremeWingTrapCertmgrCsrExportSuccess
				, extremeWingTrapCertmgrCsrExportFailure, extremeWingTrapCertmgrCrlActionsSuccess, extremeWingTrapCertmgrCrlActionsFailure
				, extremeWingTrapCertmgrDeleteTrustpointAction, extremeWingTrapCertmgrImportTrustpoint, extremeWingTrapCertmgrExportTrustpoint
				, extremeWingTrapCertmgrCertExpiry, extremeWingTrapCertmgrCaKeyActionsSuccess, extremeWingTrapCertmgrCaKeyActionsFailure
				, extremeWingTrapCertmgrTrustpointInvalidKeyLength, extremeWingTrapCfgdAclRuleAltered, extremeWingTrapCfgdAclAttachedAltered
				, extremeWingTrapClusterCmasterCfgUpdateFail, extremeWingTrapClusterMaxExceeded, extremeWingTrapClusterStateChange
				, extremeWingTrapDhcpsvrRelayNoIface, extremeWingTrapDhcpsvrRelayIfaceNoIp, extremeWingTrapDhcpsvrRelayStart
				, extremeWingTrapDhcpsvrRelayStop, extremeWingTrapDhcpsvrDhcpsvrStart, extremeWingTrapDhcpsvrDhcpsvrStop
				, extremeWingTrapDiagFanUnderspeed, extremeWingTrapDiagUnderVoltage, extremeWingTrapDiagOverVoltage
				, extremeWingTrapDiagLowTemp, extremeWingTrapDiagHighTemp, extremeWingTrapDiagOverTemp
				, extremeWingTrapDiagWdStateChange, extremeWingTrapDiagElapsedTime, extremeWingTrapDiagAutogenTechSprt
				, extremeWingTrapDiagPoeInitFail, extremeWingTrapDiagPoePowerLevel, extremeWingTrapDiagPoeReadFail
				, extremeWingTrapDiagPoeStateChange, extremeWingTrapDiagRaidDegraded, extremeWingTrapDiagRaidError
				, extremeWingTrapDiagPwrsplyFail, extremeWingTrapDiagHddFailing, extremeWingTrapDiagWdResetSys
				, extremeWingTrapDiagCpuUsageTooHigh, extremeWingTrapDiagCpuUsageTooHighRecover, extremeWingTrapDiagCpuLoad
				, extremeWingTrapDiagRamUsage, extremeWingTrapDiagMemUsageTooHigh, extremeWingTrapDiagMemUsageTooHighRecover
				, extremeWingTrapDiagBufUsage, extremeWingTrapDiagHeadCacheUsage, extremeWingTrapDiagIpDestUsage
				, extremeWingTrapDiagFreeRam, extremeWingTrapDiagFreeFlashDisk, extremeWingTrapDiagFreeFlashInodes
				, extremeWingTrapDiagFreeNvramDisk, extremeWingTrapDiagFreeNvramInodes, extremeWingTrapDiagFreeRamDisk
				, extremeWingTrapDiagFreeRamInodes, extremeWingTrapDiagFdCount, extremeWingTrapDiagDiskUsage
				, extremeWingTrapDiagNewLedState, extremeWingTrapDiagLedIdentify, extremeWingTrapDot11CountryCode
				, extremeWingTrapDot11CountryCodeError, extremeWingTrapDot11ClientAssociated, extremeWingTrapDot11ClientDisassociated
				, extremeWingTrapDot11ClientDeniedAssoc, extremeWingTrapDot11ClientAssocIgnored, extremeWingTrapDot11WpaWpa2Success
				, extremeWingTrapDot11WpaWpa2Failed, extremeWingTrapDot11WpaWpa2KeyRotn, extremeWingTrapDot11TkipMicFailReport
				, extremeWingTrapDot11TkipMicFailure, extremeWingTrapDot11TkipCntrmeasStart, extremeWingTrapDot11TkipCntrmeasEnd
				, extremeWingTrapDot11EapSuccess, extremeWingTrapDot11EapFailed, extremeWingTrapDot11EapClientTimeout
				, extremeWingTrapDot11EapServerTimeout, extremeWingTrapDot11EapCachedKeys, extremeWingTrapDot11EapOppCachedKeys
				, extremeWingTrapDot11EapPreauthSuccess, extremeWingTrapDot11EapPreauthFailed, extremeWingTrapDot11EapPreauthClientTimeout
				, extremeWingTrapDot11EapPreauthServerTimeout, extremeWingTrapDot11KerberosWlanSuccess, extremeWingTrapDot11KerberosWlanTimeout
				, extremeWingTrapDot11KerberosWlanFailed, extremeWingTrapDot11KerberosClientSuccess, extremeWingTrapDot11KerberosClientFailed
				, extremeWingTrapDot11VoiceCallFailed, extremeWingTrapDot11VoiceCallEstablished, extremeWingTrapDot11VoiceCallCompleted
				, extremeWingTrapDot11UnsanctionedApActive, extremeWingTrapDot11UnsanctionedApInactive, extremeWingTrapDot11UnsanctionedApStatusChange
				, extremeWingTrapDot11NeighborDeniedAssoc, extremeWingTrapDot11WlanTimeAccessDisable, extremeWingTrapDot11WlanTimeAccessEnable
				, extremeWingTrapDot11MoveOperationSuccess, extremeWingTrapDot11FtRoamSuccess, extremeWingTrapDot11GalRxRequest
				, extremeWingTrapDot11GalTxResponse, extremeWingTrapDot11GalValidateReq, extremeWingTrapDot11GalValidateFailed
				, extremeWingTrapDot11GalValidateSuccess, extremeWingTrapFwuFwudone, extremeWingTrapFwuFwuaborted
				, extremeWingTrapFwuFwunoneed, extremeWingTrapFwuFwusyserr, extremeWingTrapFwuFwubadconfig
				, extremeWingTrapFwuFwuserverundef, extremeWingTrapFwuFwufileundef, extremeWingTrapFwuFwuserverunreachable
				, extremeWingTrapFwuFwucouldntgetfile, extremeWingTrapFwuFwuvermismatch, extremeWingTrapFwuFwuprodmismatch
				, extremeWingTrapFwuFwucorruptedfile, extremeWingTrapFwuFwusignmismatch, extremeWingTrapFwuFwuunsupportedhw
				, extremeWingTrapFwuFwuunsupportedmodelnum, extremeWingTrapLicmgrLicInstalled, extremeWingTrapLicmgrLicInstallDefault
				, extremeWingTrapLicmgrLicInstallCount, extremeWingTrapLicmgrLicRemoved, extremeWingTrapLicmgrLicInvalid
				, extremeWingTrapMeshMeshLinkUp, extremeWingTrapMeshMeshLinkDown, extremeWingTrapMeshMeshpointUp
				, extremeWingTrapMeshMeshpointDown, extremeWingTrapMeshMeshpointLoopPreventOn, extremeWingTrapMeshMeshpointLoopPreventOff
				, extremeWingTrapMeshMeshpointRootChange, extremeWingTrapMeshMeshpointPathChange, extremeWingTrapNsmIfup
				, extremeWingTrapNsmIfdown, extremeWingTrapNsmDhcpip, extremeWingTrapNsmDhcpdefrt
				, extremeWingTrapNsmDhcpipchg, extremeWingTrapNsmDhcpnodefrt, extremeWingTrapNsmIfipcfg
				, extremeWingTrapNsmDhcpcErr, extremeWingTrapNsmDhcpipnoadd, extremeWingTrapNsmDhcplsexp
				, extremeWingTrapNsmDhcpnak, extremeWingTrapNsmNsmNtp, extremeWingTrapNsmIfFailover
				, extremeWingTrapNsmIfFailback, extremeWingTrapPmProcstart, extremeWingTrapPmProcrstrt
				, extremeWingTrapPmProcmaxrstrt, extremeWingTrapPmProcsysrstrt, extremeWingTrapPmProcstop
				, extremeWingTrapPmProcid, extremeWingTrapPmStartupcomplete, extremeWingTrapPmProcnoresp
				, extremeWingTrapRadconfRadiusdstart, extremeWingTrapRadconfRadiusdstop, extremeWingTrapRadconfCouldNotStopRadiusd
				, extremeWingTrapRadioChannelCountryMismatch, extremeWingTrapRadioRadioStateChange, extremeWingTrapRadioRadarScanStarted
				, extremeWingTrapRadioRadarScanCompleted, extremeWingTrapRadioRadarDetected, extremeWingTrapRadioRadarDetInfo
				, extremeWingTrapRadioResumeHomeChannel, extremeWingTrapRadioAcsScanStarted, extremeWingTrapRadioAcsScanComplete
				, extremeWingTrapRadioRadioAntennaError, extremeWingTrapRadioRadioAntennaSetting, extremeWingTrapSmrtCalibrationStarted
				, extremeWingTrapSmrtCalibrationDone, extremeWingTrapSmrtNeighborRecovery, extremeWingTrapSmrtPowerAdjustment
				, extremeWingTrapSmrtInterferenceRecovery, extremeWingTrapSmrtRootRecovery, extremeWingTrapSmrtCovHoleRecovery
				, extremeWingTrapSmrtCovHoleRecoveryDone, extremeWingTrapSmrtConfigCleared, extremeWingTrapSmrtChannelChange
				, extremeWingTrapSmtpnotSmtpauth, extremeWingTrapSmtpnotNet, extremeWingTrapSmtpnotSmtpinfo
				, extremeWingTrapSmtpnotCfg, extremeWingTrapSmtpnotCfginc, extremeWingTrapSmtpnotSmtperr
				, extremeWingTrapSmtpnotProto, extremeWingTrapSystemPanic, extremeWingTrapSystemHttpErr
				, extremeWingTrapSystemProcStop, extremeWingTrapSystemClockReset, extremeWingTrapSystemUiUserAuthFail
				, extremeWingTrapSystemUiUserAuthSuccess, extremeWingTrapSystemLogin, extremeWingTrapSystemLoginFail
				, extremeWingTrapSystemLoginFailAccess, extremeWingTrapSystemLoginFailBadRole, extremeWingTrapSystemLogout
				, extremeWingTrapSystemWarmStart, extremeWingTrapSystemWarmStartRecover, extremeWingTrapSystemColdStart
				, extremeWingTrapSystemServerUnreachable, extremeWingTrapSystemPeriodicHeartBeat, extremeWingTrapSystemConfigCommit
				, extremeWingTrapSystemSystemAutoupEnable, extremeWingTrapSystemSystemAutoupDisable, extremeWingTrapSystemMaatLight
				, extremeWingTrapSystemDevupRfdFail, extremeWingTrapSystemGuestUserExp, extremeWingTrapWipsWipsEvent
				, extremeWingTrapWipsWipsClientBlacklisted, extremeWingTrapWipsWipsClientRemBlacklist, extremeWingTrapDot1xDot1xSuccess
				, extremeWingTrapDot1xDot1xFailed, extremeWingTrapCrmCriticalResourceUp, extremeWingTrapCrmCriticalResourceDown
				, extremeWingTrapVrrpVrrpStateChange, extremeWingTrapVrrpVrrpVipSubnetMismatch, extremeWingTrapVrrpVrrpMonitorChange
				, extremeWingTrapL2tpv3L2tpv3TunnelUp, extremeWingTrapL2tpv3L2tpv3TunnelDown, extremeWingTrapIsdnIsdnEmerg
				, extremeWingTrapIsdnIsdnAlert, extremeWingTrapIsdnIsdnCrit, extremeWingTrapIsdnIsdnErr
				, extremeWingTrapIsdnIsdnWarning, extremeWingTrapIsdnIsdnNotice, extremeWingTrapIsdnIsdnInfo
				, extremeWingTrapIsdnIsdnDebug, extremeWingTrapMgmtLogKeyDeleted, extremeWingTrapMgmtLogKeyRestored
				, extremeWingTrapMgmtLogTrustpointDeleted, extremeWingTrapMgmtLogHttpStart, extremeWingTrapMgmtLogHttpLocalStart
				, extremeWingTrapMgmtLogHttpsStart, extremeWingTrapMgmtLogHttpsWait, extremeWingTrapMgmtLogHttpInit
				 }

			STATUS current
			DESCRIPTION 
				"This group must be supported for all WiNG devices
				if notifications are supported."
			::= { extremeWingGroups 2 }

		
	
	END

--
-- EXTREME-WING-MIB.my
--
