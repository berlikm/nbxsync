FORTINET-FORTIMANAGER-FORTIANALYZER-MIB DEFINITIONS ::= BEGIN

IMPORTS
    fnSysSerial, fortinet, FnIndex, FnBoolState, fnGenTrapMsg
        FROM FORTINET-CORE-MIB
    sysName
        FROM SNMPv2-MIB
    InetPortNumber, InetAddress
        FROM INET-ADDRESS-MIB
    MODULE-COMPLIANCE, NOTIFICATION-GROUP, OBJECT-GROUP
        FROM SNMPv2-CONF
    MODULE-IDENTITY, NOTIFICATION-TYPE, OBJECT-TYPE,
    Integer32, Gauge32, Counter32, Counter64, IpAddress
        FROM SNMPv2-SMI
    DisplayString, TEXTUAL-CONVENTION
        FROM SNMPv2-TC;


fnFortiManagerMib MODULE-IDENTITY
    LAST-UPDATED "202204230000Z"
    ORGANIZATION
        "Fortinet Technologies, Inc."
    CONTACT-INFO
        "Technical Support
         email: support@fortinet.com
         http://www.fortinet.com"
    DESCRIPTION
        "A MIB module containing definitions of managed objects implemented by FortiManager/FortiAnalyzer products."
    REVISION      "202204230000Z"
    DESCRIPTION
        "Add the following objects.
         fmDeviceEntLogRateHour,         fmDeviceEntLogRateDay,
         fmDeviceEntLogRateWeek,         fmDeviceEntArchiveLogUsedSpace,
         fmAdomEntLogRateMinute,         fmAdomEntArchiveLogRetention,
         fmAdomEntArchiveLogQuota,       fmAdomEntArchiveLogUsedSpacePercent,
         fmAdomEntArchiveLogUsedSpace,   fmAdomEntAnalyticsLogRetention,
         fmAdomEntAnalyticsLogQuota,     fmAdomEntAnalyticsLogUsedSpacePercent,
         fmAdomEntAnalyticsLogUsedSpace, fmAdomEntLicGbDayToday,
         fmAdomEntLicGbDayYesterday,     fmAdomEntLicGbDayWeekAvg,
         fmSysLogRateHr,                 fmSysLogIndexingRate,
         fmSysLogLagTime,                fmSysLicGbDayToday,
         fmSysLicGbDayYesterday,         fmSysLicGbDayWeekAvg,
         fmSysDiskInfo,                  fmSysDiskTable,
         fmSysLogForwardInfo,            fmSysLogForwardTable."
    REVISION    "202202040000Z"
    DESCRIPTION
        "Add support for UM (FDS/FGD service)."
    REVISION    "202105130000Z"
    DESCRIPTION
        "Change fmDeviceEntPolicyPackageState syntax."
    REVISION    "202002120000Z"
    DESCRIPTION
        "Add fmVdomNumber."
    REVISION    "201908210000Z"
    DESCRIPTION
        "HW sensors."
    REVISION    "201808070000Z"
    DESCRIPTION
        "NPI faz800F, fmg300F."
    REVISION    "201710130000Z"
    DESCRIPTION
        "NPI faz200F, faz300F, fmg200F."
    REVISION    "201707270000Z"
    DESCRIPTION
        "Added model names faz1000E, fmg400E,
         faz400E, fmg300E,
         faz3500F,
         faz3000F, fmg3000F,
         faz2000E, fmg2000E,
         faz3700F."
    REVISION    "201706280000Z"
    DESCRIPTION
        "Add fmSysVersion,fmSysUpTime,fmLogRate,fmAdom,fmDevice,fmRaid,fmPower,fmHa"
    REVISION    "201508150000Z"
    DESCRIPTION
        "NPI faz200E, fmg200E."
    REVISION    "201506120000Z"
    DESCRIPTION
        "Add model names faz3000E, fmg4000E, faz1000D, fmg1000D."
    REVISION    "201404220000Z"
    DESCRIPTION
        "Added fmSysCpuUsageExcludedNice.
         Added fmTrapCpuThresholdExcludeNice."
    REVISION    "201306100000Z"
    DESCRIPTION
        "Add support for FortiAnalyzer."
    REVISION    "201303270000Z"
    DESCRIPTION
        "Added license gb/day and device quota trap. fmTrapLicGbDayThreshold
         and fmTrapLicDevQuotaThreshold"
    REVISION    "201211260000Z"
    DESCRIPTION
        "Added commas between notifications in NOTIFICATION-GROUP.
         Added imports from SNMPv2-SMI and SNMPv2-TC.
         imported `OBJECT-GROUP' from module SNMPv2-CONF"
    REVISION    "201204200000Z"
    DESCRIPTION
        "Added RAID trap fmTrapRAIDStatusChange."
    REVISION    "201103250000Z"
    DESCRIPTION
        "Added fmSysMemUsed,fmSysMemCapacity,fmSysCpuUsage.
         Added new FortiManager models."
    REVISION    "201101190000Z"
    DESCRIPTION
        "MIB module for Fortinet FortiManager devices."
    REVISION    "200807180000Z"
    DESCRIPTION
        "Add sysName to fmTrapHASwitch."
    REVISION    "200806260000Z"
    DESCRIPTION
        "OID correction for fnFortiManagerMib."
    REVISION    "200806160000Z"
    DESCRIPTION
        "Spelling corrections."
    REVISION    "200806100000Z"
    DESCRIPTION
        "Initial version of FORTINET-FORTIMANAGER-MIB."
    ::= { fortinet 103 }

--
-- Type definition
--
FmTenths ::= TEXTUAL-CONVENTION
    DISPLAY-HINT "d-1"
    STATUS       current
    DESCRIPTION
        "An integer to be displayed with one decimal place,
        e.g. 12345 displayed as 1234.5."
    SYNTAX      Gauge32

FmHundredths ::= TEXTUAL-CONVENTION
    DISPLAY-HINT "d-2"
    STATUS       current
    DESCRIPTION
        "An integer to be displayed with two decimal places,
        e.g. 12345 displayed as 123.45."
    SYNTAX      Gauge32
---

--
-- fortinet.fnFortiManagerMib.fmTraps
--

FmRAIDStatusCode ::= TEXTUAL-CONVENTION
    STATUS      current
    DESCRIPTION
        "Enumerated list of RAID status codes."
    SYNTAX      INTEGER { arrayOK(1), arrayDegraded(2), arrayFailed(3),
		    arrayRebuilding(4), arrayRebuildingStarted(5),
		    arrayRebuildingFinished(6), arrayInitializing(7),
                    arrayInitializingStarted(8), arrayInitializingFinished(9),
                    diskOk(10), diskDegraded(11), diskFailEvent(12),
        diskUnavailable(100), diskUnused(101), diskOK(102), diskRebuilding(103), diskFailed(104), diskSpare(105),
        raidUnavailable(200), raidOK(201), raidDegraded(202), raidFailed(203), raidBackground-Initializing(204), raidBackground-Verifying(205), raidBackground-Rebuilding(206)}

FmSessProto ::= TEXTUAL-CONVENTION
    STATUS      current
    DESCRIPTION
        "data type for session protocols"
    SYNTAX      INTEGER { ip(0), icmp(1), igmp(2), ipip(4), tcp(6),
                          egp(8), pup(12), udp(17), idp(22), ipv6(41),
                          rsvp(46), gre(47), esp(50), ah(51), ospf(89),
                          pim(103), comp(108), raw(255) }


fmTraps OBJECT IDENTIFIER
    ::= { fnFortiManagerMib 0 }

fmTrapPrefix OBJECT IDENTIFIER
    ::= { fmTraps 0 }

fmTrapObject OBJECT IDENTIFIER
    ::= { fmTraps 1 }

fmRAIDStatus OBJECT-TYPE
    SYNTAX      FmRAIDStatusCode
    MAX-ACCESS  accessible-for-notify
    STATUS      current
    DESCRIPTION
        "New RAID state associated with a RAID status change event."
    ::= { fmTrapObject 1 }

fmRAIDDevIndex OBJECT-TYPE
    SYNTAX      DisplayString (SIZE(0..32))
    MAX-ACCESS  accessible-for-notify
    STATUS      current
    DESCRIPTION
        "Name/index of a RAID device relating to the event."
    ::= { fmTrapObject 2 }

fmLogRate OBJECT-TYPE
    SYNTAX      Gauge32
    MAX-ACCESS  accessible-for-notify
    STATUS      current
    DESCRIPTION
        "Log receiving rate in number of logs per second."
    ::= { fmTrapObject 3 }

fmLogRateThreshold OBJECT-TYPE
    SYNTAX      Gauge32
    MAX-ACCESS  accessible-for-notify
    STATUS      current
    DESCRIPTION
        "Threshold for log rate in number of logs per second."
    ::= { fmTrapObject 4 }

fmLogDataRate OBJECT-TYPE
    SYNTAX      Gauge32
    MAX-ACCESS  accessible-for-notify
    STATUS      current
    DESCRIPTION
        "Log receiving data rate in number of KB per second."
    ::= { fmTrapObject 5 }

fmLogDataRateThreshold OBJECT-TYPE
    SYNTAX      Gauge32
    MAX-ACCESS  accessible-for-notify
    STATUS      current
    DESCRIPTION
        "Threshold for log data rate in number of KB per second."
    ::= { fmTrapObject 6 }

fmLicGbDay OBJECT-TYPE
    SYNTAX      Gauge32
    MAX-ACCESS  accessible-for-notify
    STATUS      current
    DESCRIPTION
        "Log data used in number of GB per day."
    ::= { fmTrapObject 7 }

fmLicGbDayThreshold OBJECT-TYPE
    SYNTAX      Gauge32
    MAX-ACCESS  accessible-for-notify
    STATUS      current
    DESCRIPTION
        "Licensed threshold for log data in number of GB per day."
    ::= { fmTrapObject 8 }

fmLicDevQuota OBJECT-TYPE
    SYNTAX      Gauge32
    MAX-ACCESS  accessible-for-notify
    STATUS      current
    DESCRIPTION
        "Device quota used in number of GB."
    ::= { fmTrapObject 9 }

fmLicDevQuotaThreshold OBJECT-TYPE
    SYNTAX      Gauge32
    MAX-ACCESS  accessible-for-notify
    STATUS      current
    DESCRIPTION
        "Licensed threshold for device quota in number of GB."
    ::= { fmTrapObject 10 }

fmSensorState OBJECT-TYPE
    SYNTAX      FmSensorEntState
    MAX-ACCESS  accessible-for-notify
    STATUS      current
    DESCRIPTION
        "Sensor status."
    ::= { fmTrapObject 11 }

fmSensorName OBJECT-TYPE
    SYNTAX      DisplayString
    MAX-ACCESS  accessible-for-notify
    STATUS      current
    DESCRIPTION
        "Sensor name."
    ::= { fmTrapObject 12 }

--
-- fortinet.fnFortiManagerMib.fmModel
--

fmModel OBJECT IDENTIFIER
    ::= { fnFortiManagerMib 1 }

fmgvm OBJECT IDENTIFIER
    ::= { fmModel 64 }

fmg100 OBJECT IDENTIFIER
    ::= { fmModel 1000 }

fmg100C OBJECT IDENTIFIER
    ::= { fmModel 1003 }

fmg200D OBJECT IDENTIFIER
    ::= { fmModel 2004 }

fmg200E OBJECT IDENTIFIER
    ::= { fmModel 2005 }

fmg200F OBJECT IDENTIFIER
    ::= { fmModel 2006 }

fmg200G OBJECT IDENTIFIER
    ::= { fmModel 2007 }

fmg300D OBJECT IDENTIFIER
    ::= { fmModel 3004 }

fmg300E OBJECT IDENTIFIER
    ::= { fmModel 3005 }

fmg300F OBJECT IDENTIFIER
    ::= { fmModel 3006 }

fmg400 OBJECT IDENTIFIER
    ::= { fmModel 4000 }

fmg400A OBJECT IDENTIFIER
    ::= { fmModel 4001 }

fmg400B OBJECT IDENTIFIER
    ::= { fmModel 4002 }

fmg400C OBJECT IDENTIFIER
    ::= { fmModel 4003 }

fmg400E OBJECT IDENTIFIER
    ::= { fmModel 4005 }

fmg400G OBJECT IDENTIFIER
    ::= { fmModel 4007 }

fmg410G OBJECT IDENTIFIER
    ::= { fmModel 4107 }

fmg1000C OBJECT IDENTIFIER
    ::= { fmModel 10003 }

fmg1000D OBJECT IDENTIFIER
    ::= { fmModel 10004 }

fmg1000F OBJECT IDENTIFIER
    ::= { fmModel 10006 }

fmg1000G OBJECT IDENTIFIER
    ::= { fmModel 10007 }

fmg2000E OBJECT IDENTIFIER
    ::= { fmModel 20005 }

fmg2000XL OBJECT IDENTIFIER
    ::= { fmModel 20000 }

fmg3000 OBJECT IDENTIFIER
    ::= { fmModel 30000 }

fmg3000B OBJECT IDENTIFIER
    ::= { fmModel 30002 }

fmg3000C OBJECT IDENTIFIER
    ::= { fmModel 30003 }

fmg3000F OBJECT IDENTIFIER
    ::= { fmModel 30006 }

fmg3000G OBJECT IDENTIFIER
    ::= { fmModel 30007 }

fmg3100G OBJECT IDENTIFIER
    ::= { fmModel 31007 }

fmg3700F OBJECT IDENTIFIER
    ::= { fmModel 37006 }
fmg3700G OBJECT IDENTIFIER
    ::= { fmModel 37007 }
fmg3750G OBJECT IDENTIFIER
    ::= { fmModel 37507 }

fmg3900E OBJECT IDENTIFIER
    ::= { fmModel 39005 }

fmg4000D OBJECT IDENTIFIER
    ::= { fmModel 40004 }

fmg4000E OBJECT IDENTIFIER
    ::= { fmModel 40005 }

fmg5001A OBJECT IDENTIFIER
    ::= { fmModel 50011 }

--
-- fortinet.fnFortiManagerMib.fmSystem
--

fmSystem OBJECT IDENTIFIER
    ::= { fnFortiManagerMib 2 }

--
-- fortinet.fnFortiManagerMib.fmSystem.fmSystemInfo
--

fmSystemInfo OBJECT IDENTIFIER
    ::= { fmSystem 1 }

fmSysCpuUsage OBJECT-TYPE
    SYNTAX      Integer32 (0..100)
    MAX-ACCESS  read-only
    STATUS      current
    DESCRIPTION
        "Current CPU usage (percentage)"
    ::= { fmSystemInfo 1 }

fmSysMemUsed OBJECT-TYPE
    SYNTAX      Gauge32
    MAX-ACCESS  read-only
    STATUS      current
    DESCRIPTION
        "Current memory used (KB)"
    ::= { fmSystemInfo 2 }

fmSysMemCapacity OBJECT-TYPE
    SYNTAX      Gauge32
    MAX-ACCESS  read-only
    STATUS      current
    DESCRIPTION
        "Total physical and swap memory installed (KB)"
    ::= { fmSystemInfo 3 }

fmSysDiskUsage OBJECT-TYPE
    SYNTAX      Gauge32
    MAX-ACCESS  read-only
    STATUS      current
    DESCRIPTION
        "Current hard disk usage (MB)"
    ::= { fmSystemInfo 4 }

fmSysDiskCapacity OBJECT-TYPE
    SYNTAX      Gauge32
    MAX-ACCESS  read-only
    STATUS      current
    DESCRIPTION
        "Total hard disk capacity (MB)"
    ::= { fmSystemInfo 5 }

fmSysCpuUsageExcludedNice OBJECT-TYPE
    SYNTAX      Gauge32 (0..100)
    MAX-ACCESS  read-only
    STATUS      current
    DESCRIPTION
        "Current CPU usage excluded nice processes usage (percentage)"
    ::= { fmSystemInfo 6 }

fmSysVersion OBJECT-TYPE
    SYNTAX      DisplayString
    MAX-ACCESS  read-only
    STATUS      current
    DESCRIPTION
        "Firmware version of the device"
    ::= { fmSystemInfo 7 }

fmSysUpTime OBJECT-TYPE
    SYNTAX      Counter64
    UNITS       "hundredths of a second"
    MAX-ACCESS  read-only
    STATUS      current
    DESCRIPTION
        "The 64bit time (in hundredths of a second) since the network management portion of the system was last re-initialized."
    ::= { fmSystemInfo 8 }

fmSysLogRate OBJECT-TYPE
    SYNTAX      Gauge32
    UNITS       "logs per second"
    MAX-ACCESS  read-only
    STATUS      current
    DESCRIPTION
        "Log receiving rate in number of logs per second."
    ::= { fmSystemInfo 9 }

fmSysLogRateHr OBJECT-TYPE
    SYNTAX      FmHundredths
    UNITS       "logs per second"
    MAX-ACCESS  read-only
    STATUS      current
    DESCRIPTION
        "Log receiving rate in number of logs per second in higher resolution with two decimal places,
        e.g., value 12345 should be interpreted as 123.45 logs per second."
    ::= { fmSystemInfo 10 }

fmSysLogIndexingRate OBJECT-TYPE
    SYNTAX      FmHundredths
    UNITS       "logs per second"
    MAX-ACCESS  read-only
    STATUS      current
    DESCRIPTION
        "After logs are received, they will be indexed. It shows log indexing rate in number of logs per second with two decimal places."
    ::= { fmSystemInfo 11 }

fmSysLogLagTime OBJECT-TYPE
    SYNTAX      Gauge32
    UNITS       "second"
    MAX-ACCESS  read-only
    STATUS      current
    DESCRIPTION
        "The time difference between log receiving and indexing."
    ::= { fmSystemInfo 12 }

fmSysLicGbDayToday OBJECT-TYPE
    SYNTAX      FmHundredths
    MAX-ACCESS  read-only
    STATUS      current
    DESCRIPTION
        "The gibi bytes (GiB) of logs received today with two decimal places."
    ::= { fmSystemInfo 13 }

fmSysLicGbDayYesterday OBJECT-TYPE
    SYNTAX      FmHundredths
    MAX-ACCESS  read-only
    STATUS      current
    DESCRIPTION
        "The gibi bytes (GiB) of logs received yesterday with two decimal places."
    ::= { fmSystemInfo 14 }

fmSysLicGbDayWeekAvg OBJECT-TYPE
    SYNTAX      FmHundredths
    MAX-ACCESS  read-only
    STATUS      current
    DESCRIPTION
        "The daily average gibi bytes (GiB) of logs received over last seven days with two decimal places."
    ::= { fmSystemInfo 15 }

--- fmsys disk table
fmSysDiskInfo OBJECT IDENTIFIER
    ::= { fmSystemInfo 16 }

fmSysDiskNumber OBJECT-TYPE
    SYNTAX      Gauge32
    MAX-ACCESS  read-only
    STATUS      current
    DESCRIPTION
        "The number of disks in fmSysDiskTable."
    ::= { fmSysDiskInfo 1 }

fmSysDiskTable OBJECT-TYPE
    SYNTAX      SEQUENCE OF FmSysDiskEntry
    MAX-ACCESS  not-accessible
    STATUS      current
    DESCRIPTION
        "The table of disks on this device.
        Every type of disk is an entry of this table."
    ::= { fmSystemInfo 17 }

fmSysDiskEntry OBJECT-TYPE
    SYNTAX      FmSysDiskEntry
    MAX-ACCESS  not-accessible
    STATUS      current
    DESCRIPTION
        "An entry containing disk detailed info."
    INDEX       { fmSysDiskEntIndex }
    ::= { fmSysDiskTable 1 }

FmSysDiskEntry ::= SEQUENCE {
    fmSysDiskEntIndex      FnIndex,
    fmSysDiskEntName       DisplayString,
    fmSysDiskEntUsage      Gauge32,
    fmSysDiskEntCapacity   Gauge32,
    fmSysDiskEntIOUtil     FmTenths
}

fmSysDiskEntIndex OBJECT-TYPE
    SYNTAX      FnIndex
    MAX-ACCESS  not-accessible
    STATUS      current
    DESCRIPTION
        "An index value that uniquely identifies the disk entry."
    ::= { fmSysDiskEntry 1 }

fmSysDiskEntName OBJECT-TYPE
    SYNTAX      DisplayString
    MAX-ACCESS  read-only
    STATUS      current
    DESCRIPTION
        "The name of the disk."
    ::= { fmSysDiskEntry 2 }

fmSysDiskEntUsage OBJECT-TYPE
    SYNTAX      Gauge32
    MAX-ACCESS  read-only
    STATUS      current
    DESCRIPTION
        "Current disk usage (MB)."
    ::= { fmSysDiskEntry 3 }

fmSysDiskEntCapacity OBJECT-TYPE
    SYNTAX      Gauge32
    MAX-ACCESS  read-only
    STATUS      current
    DESCRIPTION
        "Total disk capacity (MB)."
    ::= { fmSysDiskEntry 4 }

fmSysDiskEntIOUtil OBJECT-TYPE
    SYNTAX      FmTenths
    MAX-ACCESS  read-only
    STATUS      current
    DESCRIPTION
        "Current disk IO utilization (percentage) with one decimal place."
    ::= { fmSysDiskEntry 5 }
---

--- fmsys log-forward table
fmSysLogForwardInfo OBJECT IDENTIFIER
    ::= { fmSystemInfo 18 }

fmSysLogForwardNumber OBJECT-TYPE
    SYNTAX      Gauge32
    MAX-ACCESS  read-only
    STATUS      current
    DESCRIPTION
        "The number of log-forward targets in fmSysLogForwardTable."
    ::= { fmSysLogForwardInfo 1 }

fmSysLogForwardTable OBJECT-TYPE
    SYNTAX      SEQUENCE OF FmSysLogForwardEntry
    MAX-ACCESS  not-accessible
    STATUS      current
    DESCRIPTION
        "The table of log-forward targets configured on the device."
    ::= { fmSystemInfo 19 }

fmSysLogForwardEntry OBJECT-TYPE
    SYNTAX      FmSysLogForwardEntry
    MAX-ACCESS  not-accessible
    STATUS      current
    DESCRIPTION
        "An entry containing information applicable to a particular log-forward target."
    INDEX       { fmSysLogForwardIndex }
    ::= { fmSysLogForwardTable 1 }

FmSysLogForwardEntry ::= SEQUENCE {
    fmSysLogForwardIndex   FnIndex,
    fmSysLogForwardName    DisplayString,
    fmSysLogForwardRate    FmHundredths
}

fmSysLogForwardIndex OBJECT-TYPE
    SYNTAX      FnIndex
    MAX-ACCESS  not-accessible
    STATUS      current
    DESCRIPTION
        "An index value that uniquely identifies the log-forward target."
    ::= { fmSysLogForwardEntry 1 }

fmSysLogForwardName OBJECT-TYPE
    SYNTAX      DisplayString
    MAX-ACCESS  read-only
    STATUS      current
    DESCRIPTION
        "The name of the log-forward target."
    ::= { fmSysLogForwardEntry 2 }

fmSysLogForwardRate OBJECT-TYPE
    SYNTAX      FmHundredths
    UNITS       "logs per second"
    MAX-ACCESS  read-only
    STATUS      current
    DESCRIPTION
        "Log forwarding rate to the particular target in number of logs per second with two decimal places."
    ::= { fmSysLogForwardEntry 3 }
---

fmTrapHASwitch NOTIFICATION-TYPE
    OBJECTS     { fnSysSerial, sysName }
    STATUS      current
    DESCRIPTION
        "FortiManager HA cluster has been re-arranged. A new master has been selected and asserted."
    ::= { fmTrapPrefix 401 }

fmTrapRAIDStatusChange NOTIFICATION-TYPE
    OBJECTS     { fnSysSerial, sysName,
	              fmRAIDStatus, fmRAIDDevIndex }
    STATUS      current
    DESCRIPTION
        "Trap is sent when there is a change in the status of the RAID array, if present."
    ::= { fmTrapPrefix 402 }

fmTrapLogAlert NOTIFICATION-TYPE
    OBJECTS     { fnSysSerial, sysName, fnGenTrapMsg }
    STATUS      current
    DESCRIPTION
        "Trap is sent when a log based alert has been triggered.
         Alert description included in trap."
    ::= { fmTrapPrefix 403 }

fmTrapLogRateThreshold NOTIFICATION-TYPE
    OBJECTS     { fnSysSerial, sysName, fmLogRate, fmLogRateThreshold }
    STATUS      current
    DESCRIPTION
        "Indicates that the incoming log rate has exceeded the threshold"
    ::= { fmTrapPrefix 404 }

fmTrapLogDataRateThreshold NOTIFICATION-TYPE
    OBJECTS     { fnSysSerial, sysName, fmLogDataRate, fmLogDataRateThreshold }
    STATUS      current
    DESCRIPTION
        "Indicates that the incoming log data rate has exceeded the threshold"
    ::= { fmTrapPrefix 405 }

fmTrapLicGbDayThreshold NOTIFICATION-TYPE
    OBJECTS     { fnSysSerial, sysName, fmLicGbDay, fmLicGbDayThreshold }
    STATUS      current
    DESCRIPTION
        "Indicates that the used log has exceeded the licensed GB/Day"
    ::= { fmTrapPrefix 407 }

fmTrapLicDevQuotaThreshold NOTIFICATION-TYPE
    OBJECTS     { fnSysSerial, sysName, fmLicDevQuota, fmLicDevQuotaThreshold }
    STATUS      current
    DESCRIPTION
        "Indicates that the used device quota has exceeded the licensed device quota"
    ::= { fmTrapPrefix 408 }

fmTrapCpuThresholdExcludeNice NOTIFICATION-TYPE
    OBJECTS     { fnSysSerial, sysName }
    STATUS      current
    DESCRIPTION
        "Indicates that the CPU usage excluding nice processes has exceeded the threshold"
    ::= { fmTrapPrefix 409 }

fmTrapPowerStateChange NOTIFICATION-TYPE
    OBJECTS     { fnSysSerial, sysName,
	              fmSensorState, fmSensorName }
    STATUS      current
    DESCRIPTION
        "Trap is sent when there is a change in the status of the power supply, if present."
    ::= { fmTrapPrefix 410 }

fmTrapFanStateChange NOTIFICATION-TYPE
    OBJECTS     { fnSysSerial, sysName,
	              fmSensorState, fmSensorName }
    STATUS      current
    DESCRIPTION
        "Trap is sent when there is a change in the status of the fan, if present."
    ::= { fmTrapPrefix 411 }

fmTrapTemperatureStateChange NOTIFICATION-TYPE
    OBJECTS     { fnSysSerial, sysName,
	              fmSensorState, fmSensorName }
    STATUS      current
    DESCRIPTION
        "Trap is sent when there is a change in the status of the temperature sensor, if present."
    ::= { fmTrapPrefix 412 }

fmTrapVoltageStateChange NOTIFICATION-TYPE
    OBJECTS     { fnSysSerial, sysName,
	              fmSensorState, fmSensorName }
    STATUS      current
    DESCRIPTION
        "Trap is sent when there is a change in the status of the voltage sensor, if present."
    ::= { fmTrapPrefix 413 }

--
-- fortinet.fnFortiManagerMib.faModel
--

faModel OBJECT IDENTIFIER
    ::= { fnFortiManagerMib 3 }

fazvm OBJECT IDENTIFIER
    ::= { faModel 64 }

faz100 OBJECT IDENTIFIER
    ::= { faModel 1000 }

faz100A OBJECT IDENTIFIER
    ::= { faModel 1001 }

faz100B OBJECT IDENTIFIER
    ::= { faModel 1002 }

faz100C OBJECT IDENTIFIER
    ::= { faModel 1003 }

faz150G OBJECT IDENTIFIER
    ::= {faModel 1507 }

faz200D OBJECT IDENTIFIER
    ::= { faModel 2004 }

faz200E OBJECT IDENTIFIER
    ::= {faModel 2005 }

faz200F OBJECT IDENTIFIER
    ::= {faModel 2006 }

faz300D OBJECT IDENTIFIER
    ::= { faModel 3004 }

faz300F OBJECT IDENTIFIER
    ::= { faModel 3006 }

faz300G OBJECT IDENTIFIER
    ::= { faModel 3007 }

faz400E OBJECT IDENTIFIER
    ::= { faModel 4005 }

faz400 OBJECT IDENTIFIER
    ::= { faModel 4000 }

faz400B OBJECT IDENTIFIER
    ::= { faModel 4002 }

faz400C OBJECT IDENTIFIER
    ::= { faModel 4003 }

faz800 OBJECT IDENTIFIER
    ::= { faModel 8000 }

faz800B OBJECT IDENTIFIER
    ::= { faModel 8002 }

faz800F OBJECT IDENTIFIER
    ::= { faModel 8006 }

faz800G OBJECT IDENTIFIER
    ::= { faModel 8007 }

faz810G OBJECT IDENTIFIER
    ::= { faModel 8107 }

faz1000B OBJECT IDENTIFIER
    ::= { faModel 10002 }

faz1000C OBJECT IDENTIFIER
    ::= { faModel 10003 }

faz1000D OBJECT IDENTIFIER
    ::= { faModel 10004 }

faz1000E OBJECT IDENTIFIER
    ::= { faModel 10005 }

faz1000F OBJECT IDENTIFIER
    ::= { faModel 10006 }

faz1000G OBJECT IDENTIFIER
    ::= { faModel 10007 }

faz2000 OBJECT IDENTIFIER
    ::= { faModel 20000 }

faz2000A OBJECT IDENTIFIER
    ::= { faModel 20001 }

faz2000B OBJECT IDENTIFIER
    ::= { faModel 20002 }

faz2000E OBJECT IDENTIFIER
    ::= { faModel 20005 }

faz3000D OBJECT IDENTIFIER
    ::= { faModel 30004 }

faz3000E OBJECT IDENTIFIER
    ::= { faModel 30005 }

faz3000F OBJECT IDENTIFIER
    ::= { faModel 30006 }

faz3000G OBJECT IDENTIFIER
    ::= { faModel 30007 }

faz3100G OBJECT IDENTIFIER
    ::= { faModel 31007 }

faz3500E OBJECT IDENTIFIER
    ::= { faModel 35005 }

faz3500F OBJECT IDENTIFIER
    ::= { faModel 35006 }

faz3500G OBJECT IDENTIFIER
    ::= { faModel 35007 }

faz3510G OBJECT IDENTIFIER
    ::= { faModel 35107 }

faz3700F OBJECT IDENTIFIER
    ::= { faModel 37006 }

faz3700G OBJECT IDENTIFIER
    ::= { faModel 37007 }

faz3750G OBJECT IDENTIFIER
    ::= { faModel 37507 }

faz3900E OBJECT IDENTIFIER
    ::= { faModel 39005 }

faz4000 OBJECT IDENTIFIER
    ::= { faModel 40000 }

faz4000A OBJECT IDENTIFIER
    ::= { faModel 40001 }

faz4000B OBJECT IDENTIFIER
    ::= { faModel 40002 }

--
-- fortinet.fnFortiManagerMib.fmInetProto
--

fmInetProto OBJECT IDENTIFIER
    ::= { fnFortiManagerMib 4 }

fmInetProtoInfo OBJECT IDENTIFIER
    ::= { fmInetProto 1 }

fmInetProtoTables OBJECT IDENTIFIER
    ::= { fmInetProto 2 }

fmIpSessTable OBJECT-TYPE
    SYNTAX      SEQUENCE OF FmIpSessEntry
    MAX-ACCESS  not-accessible
    STATUS      current
    DESCRIPTION
        "Information on the IP sessions active on the device"
    ::= { fmInetProtoTables 1 }

fmIpSessEntry OBJECT-TYPE
    SYNTAX      FmIpSessEntry
    MAX-ACCESS  not-accessible
    STATUS      current
    DESCRIPTION
        "Information on a specific session, including source and destination"
    INDEX       { fmIpSessIndex }
    ::= { fmIpSessTable 1 }

FmIpSessEntry ::= SEQUENCE {
    fmIpSessIndex       FnIndex,
    fmIpSessProto       FmSessProto,
    fmIpSessFromAddr    IpAddress,
    fmIpSessFromPort    InetPortNumber,
    fmIpSessToAddr      IpAddress,
    fmIpSessToPort      InetPortNumber,
    fmIpSessExp         Counter32
}

fmIpSessIndex OBJECT-TYPE
    SYNTAX      FnIndex
    MAX-ACCESS  not-accessible
    STATUS      current
    DESCRIPTION
        "An index value that uniquely identifies
         an IP session within the fmIpSessTable"
    ::= { fmIpSessEntry 1 }

fmIpSessProto OBJECT-TYPE
    SYNTAX      FmSessProto
    MAX-ACCESS  read-only
    STATUS      current
    DESCRIPTION
        "The protocol the session is using (IP, TCP, UDP, etc.)"
    ::= { fmIpSessEntry 2 }

fmIpSessFromAddr OBJECT-TYPE
    SYNTAX      IpAddress
    MAX-ACCESS  read-only
    STATUS      current
    DESCRIPTION
        "Source IP address (IPv4 only) of the session"
    ::= { fmIpSessEntry 3 }

fmIpSessFromPort OBJECT-TYPE
    SYNTAX      InetPortNumber
    MAX-ACCESS  read-only
    STATUS      current
    DESCRIPTION
        "Source port number (UDP and TCP only) of the session"
    ::= { fmIpSessEntry 4 }

fmIpSessToAddr OBJECT-TYPE
    SYNTAX      IpAddress
    MAX-ACCESS  read-only
    STATUS      current
    DESCRIPTION
        "Destination IP address (IPv4 only) of the session"
    ::= { fmIpSessEntry 5 }

fmIpSessToPort OBJECT-TYPE
    SYNTAX      InetPortNumber
    MAX-ACCESS  read-only
    STATUS      current
    DESCRIPTION
        "Destination Port number (UDP and TCP only) of the session"
    ::= { fmIpSessEntry 6 }

fmIpSessExp OBJECT-TYPE
    SYNTAX      Counter32
    MAX-ACCESS  read-only
    STATUS      current
    DESCRIPTION
        "Number of seconds remaining before the session expires (if idle)"
    ::= { fmIpSessEntry 7 }

--
-- fortinet.fnFortiManagerMib.fmAdom
--

fmAdom OBJECT IDENTIFIER
    ::= { fnFortiManagerMib 5 }

fmAdomInfo OBJECT IDENTIFIER
    ::= { fmAdom 1 }

fmAdomEnabled OBJECT-TYPE
    SYNTAX      FnBoolState
    MAX-ACCESS  read-only
    STATUS      current
    DESCRIPTION
        "Whether administrative domains are enabled on this device"
    ::= { fmAdomInfo 1 }

fmAdomNumber OBJECT-TYPE
    SYNTAX      Integer32
    MAX-ACCESS  read-only
    STATUS      current
    DESCRIPTION
        "The number of administrative domains in fmAdomTable"
    ::= { fmAdomInfo 2 }

fmAdomMax OBJECT-TYPE
    SYNTAX      Integer32
    MAX-ACCESS  read-only
    STATUS      current
    DESCRIPTION
        "The maximum number of administrative domains allowed on the device as allowed by hardware and/or licensing"
    ::= { fmAdomInfo 3 }

fmAdomTable OBJECT-TYPE
    SYNTAX      SEQUENCE OF FmAdomEntry
    MAX-ACCESS  not-accessible
    STATUS      current
    DESCRIPTION
        "A table of administrative domains configured on the device"
    ::= { fmAdom 2 }

fmAdomEntry OBJECT-TYPE
    SYNTAX      FmAdomEntry
    MAX-ACCESS  not-accessible
    STATUS      current
    DESCRIPTION
        "An entry containing information applicable
         to a particular administrative domain"
    INDEX       { fmAdomEntIndex }
    ::= { fmAdomTable 1 }

FmAdomEntry ::= SEQUENCE {
    fmAdomEntIndex                         FnIndex,
    fmAdomEntName                          DisplayString,
    fmAdomEntState                         FnBoolState,
    fmAdomEntMode                          FmAdomEntMode,
    fmAdomEntFgtNumber                     Integer32,
    fmAdomEntPolicyPackageNumber           Integer32,
    fmAdomEntOsVersion                     Integer32,
    fmAdomEntMr                            Integer32,
    fmAdomEntVpnMode                       FmAdomEntVpnMode,
    fmAdomEntLogRateMinute                 FmHundredths,
    fmAdomEntArchiveLogRetention           Gauge32,
    fmAdomEntArchiveLogQuota               Gauge32,
    fmAdomEntArchiveLogUsedSpace           Gauge32,
    fmAdomEntArchiveLogUsedSpacePercent    FmTenths,
    fmAdomEntAnalyticsLogRetention         Gauge32,
    fmAdomEntAnalyticsLogQuota             Gauge32,
    fmAdomEntAnalyticsLogUsedSpace         Gauge32,
    fmAdomEntAnalyticsLogUsedSpacePercent  FmTenths,
    fmAdomEntLicGbDayToday                 FmHundredths,
    fmAdomEntLicGbDayYesterday             FmHundredths,
    fmAdomEntLicGbDayWeekAvg               FmHundredths
}

fmAdomEntIndex OBJECT-TYPE
    SYNTAX      FnIndex
    MAX-ACCESS  not-accessible
    STATUS      current
    DESCRIPTION
        "An index value that uniquely identifies the entry"
    ::= { fmAdomEntry 1 }

fmAdomEntName OBJECT-TYPE
    SYNTAX      DisplayString
    MAX-ACCESS  read-only
    STATUS      current
    DESCRIPTION
        "The name of the administrative domain"
    ::= { fmAdomEntry 2 }

fmAdomEntState OBJECT-TYPE
    SYNTAX      FnBoolState
    MAX-ACCESS  read-only
    STATUS      current
    DESCRIPTION
        "Whether adom is enabled or disabled"
    ::= { fmAdomEntry 3 }

FmAdomEntMode ::= TEXTUAL-CONVENTION
    STATUS      current
    DESCRIPTION
        "Whether adom is in normal or backup mode"
    SYNTAX      INTEGER {
        normal (1),
        backup (2)
    }

fmAdomEntMode OBJECT-TYPE
    SYNTAX      FmAdomEntMode
    MAX-ACCESS  read-only
    STATUS      current
    DESCRIPTION
        "Whether adom is in normal or backup mode"
    ::= { fmAdomEntry 4 }

fmAdomEntFgtNumber OBJECT-TYPE
    SYNTAX      Integer32
    MAX-ACCESS  read-only
    STATUS      current
    DESCRIPTION
        "Number of FortiGates in adom"
    ::= { fmAdomEntry 5 }

fmAdomEntPolicyPackageNumber OBJECT-TYPE
    SYNTAX      Integer32
    MAX-ACCESS  read-only
    STATUS      current
    DESCRIPTION
        "Number of policy packages in adom"
    ::= { fmAdomEntry 6 }

fmAdomEntOsVersion OBJECT-TYPE
    SYNTAX      Integer32
    MAX-ACCESS  read-only
    STATUS      current
    DESCRIPTION
        "OS version supported by adom"
    ::= { fmAdomEntry 7 }

fmAdomEntMr OBJECT-TYPE
    SYNTAX      Integer32
    MAX-ACCESS  read-only
    STATUS      current
    DESCRIPTION
        "MR version supported by adom"
    ::= { fmAdomEntry 8 }

FmAdomEntVpnMode ::= TEXTUAL-CONVENTION
    STATUS      current
    DESCRIPTION
        "Adom VPN mode"
    SYNTAX      INTEGER {
        central-console (1),
        policy-and-device (2),
        not-applicable (3)
    }

fmAdomEntVpnMode OBJECT-TYPE
    SYNTAX      FmAdomEntVpnMode
    MAX-ACCESS  read-only
    STATUS      current
    DESCRIPTION
        "Adom VPN mode"
    ::= { fmAdomEntry 9 }

fmAdomEntLogRateMinute OBJECT-TYPE
    SYNTAX      FmHundredths
    UNITS       "logs per second"
    MAX-ACCESS  read-only
    STATUS      current
    DESCRIPTION
        "The adom log receiving rate in number of logs per second over last one minute with two decimal places."
    ::= { fmAdomEntry 10 }

fmAdomEntArchiveLogRetention OBJECT-TYPE
    SYNTAX      Gauge32
    UNITS       "days"
    MAX-ACCESS  read-only
    STATUS      current
    DESCRIPTION
        "The number of days adom archive logs will be kept according to the data policy."
    ::= { fmAdomEntry 11 }

fmAdomEntArchiveLogQuota OBJECT-TYPE
    SYNTAX      Gauge32
    MAX-ACCESS  read-only
    STATUS      current
    DESCRIPTION
        "The maximum disk space (MB) allocated for adom archive logs."
    ::= { fmAdomEntry 12 }

fmAdomEntArchiveLogUsedSpace OBJECT-TYPE
    SYNTAX      Gauge32
    MAX-ACCESS  read-only
    STATUS      current
    DESCRIPTION
        "Disk space (MB) adom archive logs have used."
    ::= { fmAdomEntry 13 }

fmAdomEntArchiveLogUsedSpacePercent OBJECT-TYPE
    SYNTAX      FmTenths
    MAX-ACCESS  read-only
    STATUS      current
    DESCRIPTION
        "Disk usage percentage of quota for adom archive logs with one decimal place."
    ::= { fmAdomEntry 14 }

fmAdomEntAnalyticsLogRetention OBJECT-TYPE
    SYNTAX      Gauge32
    UNITS       "days"
    MAX-ACCESS  read-only
    STATUS      current
    DESCRIPTION
        "The number of days adom analytics logs will be kept according to the data policy."
    ::= { fmAdomEntry 15 }

fmAdomEntAnalyticsLogQuota OBJECT-TYPE
    SYNTAX      Gauge32
    MAX-ACCESS  read-only
    STATUS      current
    DESCRIPTION
        "The maximum disk space (MB) allocated for adom analytics logs."
    ::= { fmAdomEntry 16 }

fmAdomEntAnalyticsLogUsedSpace OBJECT-TYPE
    SYNTAX      Gauge32
    MAX-ACCESS  read-only
    STATUS      current
    DESCRIPTION
        "Disk space (MB) adom analytics logs have used."
    ::= { fmAdomEntry 17 }

fmAdomEntAnalyticsLogUsedSpacePercent OBJECT-TYPE
    SYNTAX      FmTenths
    MAX-ACCESS  read-only
    STATUS      current
    DESCRIPTION
        "Disk usage percentage of quota for adom analytics logs with one decimal place."
    ::= { fmAdomEntry 18 }

fmAdomEntLicGbDayToday OBJECT-TYPE
    SYNTAX      FmHundredths
    MAX-ACCESS  read-only
    STATUS      current
    DESCRIPTION
        "The gibi bytes (GiB) of adom logs received today with two decimal places."
    ::= { fmAdomEntry 19 }

fmAdomEntLicGbDayYesterday OBJECT-TYPE
    SYNTAX      FmHundredths
    MAX-ACCESS  read-only
    STATUS      current
    DESCRIPTION
        "The gibi bytes (GiB) of adom logs received yesterday with two decimal places."
    ::= { fmAdomEntry 20 }

fmAdomEntLicGbDayWeekAvg OBJECT-TYPE
    SYNTAX      FmHundredths
    MAX-ACCESS  read-only
    STATUS      current
    DESCRIPTION
        "The daily average gibi bytes (GiB) of adom logs received over last seven days with two decimal places."
    ::= { fmAdomEntry 21 }
---

--
-- fortinet.fnFortiManagerMib.fmDevice
--

fmDevice OBJECT IDENTIFIER
    ::= { fnFortiManagerMib 6 }

fmDeviceInfo OBJECT IDENTIFIER
    ::= { fmDevice 1 }

fmDeviceNumber OBJECT-TYPE
    SYNTAX      Integer32
    MAX-ACCESS  read-only
    STATUS      current
    DESCRIPTION
        "The number of devices in fmDeviceTable"
    ::= { fmDeviceInfo 1 }

fmVdomNumber OBJECT-TYPE
    SYNTAX      Integer32
    MAX-ACCESS  read-only
    STATUS      current
    DESCRIPTION
        "The total number of VDOMS"
    ::= { fmDeviceInfo 2 }

fmDeviceTable OBJECT-TYPE
    SYNTAX      SEQUENCE OF FmDeviceEntry
    MAX-ACCESS  not-accessible
    STATUS      current
    DESCRIPTION
        "A table of devices configured on the device"
    ::= { fmDevice 2 }

fmDeviceEntry OBJECT-TYPE
    SYNTAX      FmDeviceEntry
    MAX-ACCESS  not-accessible
    STATUS      current
    DESCRIPTION
        "An entry containing information applicable
         to a particular device"
    INDEX       { fmDeviceEntIndex }
    ::= { fmDeviceTable 1 }

FmDeviceEntry ::= SEQUENCE {
    fmDeviceEntIndex                FnIndex,
    fmDeviceEntName                 DisplayString,
    fmDeviceEntSn                   DisplayString,
    fmDeviceEntMode                 FmDeviceEntMode,
    fmDeviceEntAdom                 DisplayString,
    fmDeviceEntIp                   DisplayString,
    fmDeviceEntOsVersion            Integer32,
    fmDeviceEntMr                   Integer32,
    fmDeviceEntBuild                Integer32,
    fmDeviceEntHaMode               FmDeviceEntHaMode,
    fmDeviceEntHaGroup              DisplayString,
    fmDeviceEntConnectState         FmDeviceEntConnectState,
    fmDeviceEntDbState              FmDeviceEntDbState,
    fmDeviceEntConfigState          FmDeviceEntConfigState,
    fmDeviceEntState                FmDeviceEntState,
    fmDeviceEntPlatform             DisplayString,
    fmDeviceEntVdomEnabled          FnBoolState,
    fmDeviceEntSupportState         FmDeviceEntSupportState,
    fmDeviceEntAvExpireDate         DisplayString,
    fmDeviceEntIpsExpireDate        DisplayString,
    fmDeviceEntWfExpireDate         DisplayString,
    fmDeviceEntAsExpireDate         DisplayString,
    fmDeviceEntPolicyPackageState   DisplayString,
    fmDeviceEntDesc                 DisplayString,
    fmDeviceEntLogRateHour          FmHundredths,
    fmDeviceEntLogRateDay           FmHundredths,
    fmDeviceEntLogRateWeek          FmHundredths,
    fmDeviceEntArchiveLogUsedSpace  Gauge32
}

fmDeviceEntIndex OBJECT-TYPE
    SYNTAX      FnIndex
    MAX-ACCESS  not-accessible
    STATUS      current
    DESCRIPTION
        "An index value that uniquely identifies the entry"
    ::= { fmDeviceEntry 1 }

fmDeviceEntName OBJECT-TYPE
    SYNTAX      DisplayString
    MAX-ACCESS  read-only
    STATUS      current
    DESCRIPTION
        "The name of the device"
    ::= { fmDeviceEntry 2 }

fmDeviceEntSn OBJECT-TYPE
    SYNTAX      DisplayString
    MAX-ACCESS  read-only
    STATUS      current
    DESCRIPTION
        "The serial number of the device"
    ::= { fmDeviceEntry 3 }

FmDeviceEntMode ::= TEXTUAL-CONVENTION
    STATUS      current
    DESCRIPTION
        "Device management mode"
    SYNTAX      INTEGER {
        unregistered (0),
        fmg (1),
        faz (2),
        fmg-faz (3)
    }

fmDeviceEntMode OBJECT-TYPE
    SYNTAX      FmDeviceEntMode
    MAX-ACCESS  read-only
    STATUS      current
    DESCRIPTION
        "Device management mode"
    ::= { fmDeviceEntry 4 }

fmDeviceEntAdom OBJECT-TYPE
    SYNTAX      DisplayString
    MAX-ACCESS  read-only
    STATUS      current
    DESCRIPTION
        "The adom name the device belongs to"
    ::= { fmDeviceEntry 5 }

fmDeviceEntIp OBJECT-TYPE
    SYNTAX      DisplayString
    MAX-ACCESS  read-only
    STATUS      current
    DESCRIPTION
        "The IP of the device"
    ::= { fmDeviceEntry 6 }

fmDeviceEntOsVersion OBJECT-TYPE
    SYNTAX      Integer32
    MAX-ACCESS  read-only
    STATUS      current
    DESCRIPTION
        "The OS version of the device"
    ::= { fmDeviceEntry 7 }

fmDeviceEntMr OBJECT-TYPE
    SYNTAX      Integer32
    MAX-ACCESS  read-only
    STATUS      current
    DESCRIPTION
        "The MR version of the device"
    ::= { fmDeviceEntry 8 }

fmDeviceEntBuild OBJECT-TYPE
    SYNTAX      Integer32
    MAX-ACCESS  read-only
    STATUS      current
    DESCRIPTION
        "The build number of the device"
    ::= { fmDeviceEntry 9 }

FmDeviceEntHaMode ::= TEXTUAL-CONVENTION
    STATUS      current
    DESCRIPTION
        "Device HA mode"
    SYNTAX      INTEGER {
        standalone (0),
        a-p (1),
        a-a (2),
        elbc (3),
        dual (4),
        fmg (5)
    }

fmDeviceEntHaMode OBJECT-TYPE
    SYNTAX      FmDeviceEntHaMode
    MAX-ACCESS  read-only
    STATUS      current
    DESCRIPTION
        "Device HA mode"
    ::= { fmDeviceEntry 10 }

fmDeviceEntHaGroup OBJECT-TYPE
    SYNTAX      DisplayString
    MAX-ACCESS  read-only
    STATUS      current
    DESCRIPTION
        "Device HA group name"
    ::= { fmDeviceEntry 11 }

FmDeviceEntConnectState ::= TEXTUAL-CONVENTION
    STATUS      current
    DESCRIPTION
        "Device connection status"
    SYNTAX      INTEGER {
        unknown (0),
        up (1),
        down (2)
    }

fmDeviceEntConnectState OBJECT-TYPE
    SYNTAX      FmDeviceEntConnectState
    MAX-ACCESS  read-only
    STATUS      current
    DESCRIPTION
        "Device connection status"
    ::= { fmDeviceEntry 12 }

FmDeviceEntDbState ::= TEXTUAL-CONVENTION
    STATUS      current
    DESCRIPTION
        "Device DB status"
    SYNTAX      INTEGER {
        unknown (0),
        not-modified (1),
        modified (2)
    }

fmDeviceEntDbState OBJECT-TYPE
    SYNTAX      FmDeviceEntDbState
    MAX-ACCESS  read-only
    STATUS      current
    DESCRIPTION
        "Device DB status"
    ::= { fmDeviceEntry 13 }

FmDeviceEntConfigState ::= TEXTUAL-CONVENTION
    STATUS      current
    DESCRIPTION
        "Device config status"
    SYNTAX      INTEGER {
        unknown (0),
        in-sync (1),
        out-of-sync (2)
    }

fmDeviceEntConfigState OBJECT-TYPE
    SYNTAX      FmDeviceEntConfigState
    MAX-ACCESS  read-only
    STATUS      current
    DESCRIPTION
        "Device config status"
    ::= { fmDeviceEntry 14 }

FmDeviceEntState ::= TEXTUAL-CONVENTION
    STATUS      current
    DESCRIPTION
        "Device status"
    SYNTAX      INTEGER {
        none (0),
        unknown (1),
        checked-in (2),
        in-progress (3),
        installed (4),
        aborted (5),
        sched (6),
        retry (7),
        canceled (8),
        pending (9),
        retrieved (10),
        changed-conf (11),
        sync-fail (12),
        timeout (13),
        rev-reverted (14),
        auto-updated (15)
    }

fmDeviceEntState OBJECT-TYPE
    SYNTAX      FmDeviceEntState
    MAX-ACCESS  read-only
    STATUS      current
    DESCRIPTION
        "Device status"
    ::= { fmDeviceEntry 15 }

fmDeviceEntPlatform OBJECT-TYPE
    SYNTAX      DisplayString
    MAX-ACCESS  read-only
    STATUS      current
    DESCRIPTION
        "The platform of the device"
    ::= { fmDeviceEntry 16 }

fmDeviceEntVdomEnabled OBJECT-TYPE
    SYNTAX      FnBoolState
    MAX-ACCESS  read-only
    STATUS      current
    DESCRIPTION
        "Whether vdom enabled on the device"
    ::= { fmDeviceEntry 17 }

FmDeviceEntSupportState ::= TEXTUAL-CONVENTION
    STATUS      current
    DESCRIPTION
        "The support status of the device"
    SYNTAX      INTEGER {
        expired  (0),
        valid (1)
    }

fmDeviceEntSupportState OBJECT-TYPE
    SYNTAX      FmDeviceEntSupportState
    MAX-ACCESS  read-only
    STATUS      current
    DESCRIPTION
        "The support status of the device"
    ::= { fmDeviceEntry 18 }

fmDeviceEntAvExpireDate OBJECT-TYPE
    SYNTAX      DisplayString
    MAX-ACCESS  read-only
    STATUS      current
    DESCRIPTION
        "The AV license of the device"
    ::= { fmDeviceEntry 19 }

fmDeviceEntIpsExpireDate OBJECT-TYPE
    SYNTAX      DisplayString
    MAX-ACCESS  read-only
    STATUS      current
    DESCRIPTION
        "The IPS license of the device"
    ::= { fmDeviceEntry 20 }

fmDeviceEntWfExpireDate OBJECT-TYPE
    SYNTAX      DisplayString
    MAX-ACCESS  read-only
    STATUS      current
    DESCRIPTION
        "The WCF license of the device"
    ::= { fmDeviceEntry 21 }

fmDeviceEntAsExpireDate OBJECT-TYPE
    SYNTAX      DisplayString
    MAX-ACCESS  read-only
    STATUS      current
    DESCRIPTION
        "The AS license of the device"
    ::= { fmDeviceEntry 22 }

fmDeviceEntPolicyPackageState OBJECT-TYPE
    SYNTAX      DisplayString
    MAX-ACCESS  read-only
    STATUS      current
    DESCRIPTION
        "All the policy package status of the device"
    ::= { fmDeviceEntry 23 }

fmDeviceEntDesc OBJECT-TYPE
    SYNTAX      DisplayString
    MAX-ACCESS  read-only
    STATUS      current
    DESCRIPTION
        "The description of the device"
    ::= { fmDeviceEntry 24 }

fmDeviceEntLogRateHour  OBJECT-TYPE
    SYNTAX       FmHundredths
    UNITS        "logs per second"
    MAX-ACCESS   read-only
    STATUS       current
    DESCRIPTION
        "The device log receiving rate in number of logs per second over last one hour with two decimal places."
    ::= { fmDeviceEntry 25}

fmDeviceEntLogRateDay  OBJECT-TYPE
    SYNTAX       FmHundredths
    UNITS        "logs per second"
    MAX-ACCESS   read-only
    STATUS       current
    DESCRIPTION
        "The device log receiving rate in number of logs per second over last one day with two decimal places."
    ::= { fmDeviceEntry 26}

fmDeviceEntLogRateWeek  OBJECT-TYPE
    SYNTAX       FmHundredths
    UNITS        "logs per second"
    MAX-ACCESS   read-only
    STATUS       current
    DESCRIPTION
        "The device log receiving rate in number of logs per second over last seven days with two decimal places."
    ::= { fmDeviceEntry 27}

fmDeviceEntArchiveLogUsedSpace  OBJECT-TYPE
    SYNTAX       Gauge32
    MAX-ACCESS   read-only
    STATUS       current
    DESCRIPTION
        "Disk space (MB) device archive logs have used."
    ::= { fmDeviceEntry 28}

--
-- fortinet.fnFortiManagerMib.fmRaid
--

fmRaid OBJECT IDENTIFIER
    ::= { fnFortiManagerMib 7 }

fmRaidInfo OBJECT IDENTIFIER
    ::= { fmRaid 1 }

FmRaidLevel ::= TEXTUAL-CONVENTION
    STATUS      current
    DESCRIPTION
        "Raid level"
    SYNTAX      INTEGER {
        unavailable (0),
        linear   (1),
        raid-0   (2),
        raid-1   (3),
        raid-1s  (4),
        raid-5   (5),
        raid-5s  (6),
        raid-6   (7),
        raid-6s  (8),
        raid-10  (9),
        raid-10s (10),
        raid-50  (11),
        raid-50s (12),
        raid-60  (13),
        raid-60s (14)
    }

fmRaidLevel OBJECT-TYPE
    SYNTAX      FmRaidLevel
    MAX-ACCESS  read-only
    STATUS      current
    DESCRIPTION
        "Raid level"
    ::= { fmRaidInfo 1 }

FmRaidState ::= TEXTUAL-CONVENTION
    STATUS      current
    DESCRIPTION
        "Raid status"
    SYNTAX      INTEGER {
        unavailable (0),
        ok (1),
        degraded (2),
        failed (3),
        background-initializing (4),
        background-verifying (5),
        background-rebuilding (6)
    }

fmRaidState OBJECT-TYPE
    SYNTAX      FmRaidState
    MAX-ACCESS  read-only
    STATUS      current
    DESCRIPTION
        "Raid status"
    ::= { fmRaidInfo 2 }

fmRaidSize OBJECT-TYPE
    SYNTAX      Integer32
    UNITS       "GB"
    MAX-ACCESS  read-only
    STATUS      current
    DESCRIPTION
        "Raid size in GB"
    ::= { fmRaidInfo 3 }

fmRaidDiskNumber OBJECT-TYPE
    SYNTAX      Integer32
    MAX-ACCESS  read-only
    STATUS      current
    DESCRIPTION
        "Disk numbers in the Raid"
    ::= { fmRaidInfo 4 }

fmRaidDiskTable OBJECT-TYPE
    SYNTAX      SEQUENCE OF FmRaidDiskEntry
    MAX-ACCESS  not-accessible
    STATUS      current
    DESCRIPTION
        "A table of disks in the raid"
    ::= { fmRaid 2 }

fmRaidDiskEntry OBJECT-TYPE
    SYNTAX      FmRaidDiskEntry
    MAX-ACCESS  not-accessible
    STATUS      current
    DESCRIPTION
        "An entry containing information applicable
         to a particular raid disk"
    INDEX       { fmRaidDiskEntIndex }
    ::= { fmRaidDiskTable 1 }

FmRaidDiskEntry ::= SEQUENCE {
    fmRaidDiskEntIndex      FnIndex,
    fmRaidDiskEntState      FmRaidDiskEntState,
    fmRaidDiskEntSize       Integer32
}

fmRaidDiskEntIndex OBJECT-TYPE
    SYNTAX      FnIndex
    MAX-ACCESS  not-accessible
    STATUS      current
    DESCRIPTION
        "An index value that uniquely identifies the entry"
    ::= { fmRaidDiskEntry 1 }

FmRaidDiskEntState ::= TEXTUAL-CONVENTION
    STATUS      current
    DESCRIPTION
        "Raid disk status"
    SYNTAX      INTEGER {
        unavailable (0),
        failed (1),
        unused (2),
        ok (3),
        rebuilding (4),
        spare (5)
    }

fmRaidDiskEntState OBJECT-TYPE
    SYNTAX      FmRaidDiskEntState
    MAX-ACCESS  read-only
    STATUS      current
    DESCRIPTION
        "Raid disk status"
    ::= { fmRaidDiskEntry 2 }

fmRaidDiskEntSize OBJECT-TYPE
    SYNTAX      Integer32
    UNITS       "GB"
    MAX-ACCESS  read-only
    STATUS      current
    DESCRIPTION
        "Raid disk size in GB"
    ::= { fmRaidDiskEntry 3 }

--
-- fortinet.fnFortiManagerMib.fmSensor
--

fmSensor OBJECT IDENTIFIER
    ::= { fnFortiManagerMib 8 }

fmSensorTable OBJECT-TYPE
    SYNTAX      SEQUENCE OF FmSensorEntry
    MAX-ACCESS  not-accessible
    STATUS      current
    DESCRIPTION
        "A table of sensor status"
    ::= { fmSensor 2 }

fmSensorEntry OBJECT-TYPE
    SYNTAX      FmSensorEntry
    MAX-ACCESS  not-accessible
    STATUS      current
    DESCRIPTION
        "An entry containing information applicable
         to a particular sensor"
    INDEX       { fmSensorEntIndex }
    ::= { fmSensorTable 1 }

FmSensorEntry ::= SEQUENCE {
    fmSensorEntIndex      FnIndex,
    fmSensorEntName       DisplayString,
    fmSensorEntVal        DisplayString,
    fmSensorEntType       FmSensorEntType,
    fmSensorEntState      FmSensorEntState
}

fmSensorEntIndex OBJECT-TYPE
    SYNTAX      FnIndex
    MAX-ACCESS  not-accessible
    STATUS      current
    DESCRIPTION
        "An index value that uniquely identifies the entry"
    ::= { fmSensorEntry 1 }

FmSensorEntType ::= TEXTUAL-CONVENTION
    STATUS      current
    DESCRIPTION
        "Sensor type"
    SYNTAX      INTEGER {
        power (0),
        fan (1),
        temperature (2),
        voltage (3)
    }

fmSensorEntName OBJECT-TYPE
    SYNTAX      DisplayString
    MAX-ACCESS  read-only
    STATUS      current
    DESCRIPTION
        "Sensor name"
    ::= { fmSensorEntry 2 }

fmSensorEntVal OBJECT-TYPE
    SYNTAX      DisplayString
    MAX-ACCESS  read-only
    STATUS      current
    DESCRIPTION
        "Sensor value"
    ::= { fmSensorEntry 3 }

fmSensorEntType OBJECT-TYPE
    SYNTAX      FmSensorEntType
    MAX-ACCESS  read-only
    STATUS      current
    DESCRIPTION
        "Sensor status"
    ::= { fmSensorEntry 4 }

FmSensorEntState ::= TEXTUAL-CONVENTION
    STATUS      current
    DESCRIPTION
        "Sensor status"
    SYNTAX      INTEGER {
        ok (0),
        failed (1),
        out-of-range-not-critical (2),
        out-of-range-critical (3),
        out-of-range-not-recoverable (4),
        input-lost (5),
        not-present (6)
    }

fmSensorEntState OBJECT-TYPE
    SYNTAX      FmSensorEntState
    MAX-ACCESS  read-only
    STATUS      current
    DESCRIPTION
        "Sensor status"
    ::= { fmSensorEntry 5 }

--
-- fortinet.fnFortiManagerMib.fmHa
--

fmHa OBJECT IDENTIFIER
    ::= { fnFortiManagerMib 9 }

fmHaInfo OBJECT IDENTIFIER
    ::= { fmHa 1 }

FmHaMode ::= TEXTUAL-CONVENTION
    STATUS      current
    DESCRIPTION
        "Ha mode"
    SYNTAX      INTEGER {
        standalone (0),
        master   (1),
        slave   (2)
    }

fmHaMode OBJECT-TYPE
    SYNTAX      FmHaMode
    MAX-ACCESS  read-only
    STATUS      current
    DESCRIPTION
        "Ha mode"
    ::= { fmHaInfo 1 }

fmHaClusterId OBJECT-TYPE
    SYNTAX      Integer32
    MAX-ACCESS  read-only
    STATUS      current
    DESCRIPTION
        "Ha cluster ID"
    ::= { fmHaInfo 2 }

fmHaPeerNumber OBJECT-TYPE
    SYNTAX      Integer32
    MAX-ACCESS  read-only
    STATUS      current
    DESCRIPTION
        "Peer numbers in the Ha"
    ::= { fmHaInfo 3 }

fmHaPeerTable OBJECT-TYPE
    SYNTAX      SEQUENCE OF FmHaPeerEntry
    MAX-ACCESS  not-accessible
    STATUS      current
    DESCRIPTION
        "A table of peers in the Ha"
    ::= { fmHa 2 }

fmHaPeerEntry OBJECT-TYPE
    SYNTAX      FmHaPeerEntry
    MAX-ACCESS  not-accessible
    STATUS      current
    DESCRIPTION
        "An entry containing information applicable
         to a particular Ha peer"
    INDEX       { fmHaPeerEntIndex }
    ::= { fmHaPeerTable 1 }

FmHaPeerEntry ::= SEQUENCE {
    fmHaPeerEntIndex    FnIndex,
    fmHaPeerEntIp       DisplayString,
    fmHaPeerEntSn       DisplayString,
    fmHaPeerEntEnabled  FnBoolState,
    fmHaPeerEntHostName DisplayString,
    fmHaPeerEntState    FmHaPeerEntState
}

fmHaPeerEntIndex OBJECT-TYPE
    SYNTAX      FnIndex
    MAX-ACCESS  not-accessible
    STATUS      current
    DESCRIPTION
        "An index value that uniquely identifies the entry"
    ::= { fmHaPeerEntry 1 }

fmHaPeerEntIp OBJECT-TYPE
    SYNTAX      DisplayString
    MAX-ACCESS  read-only
    STATUS      current
    DESCRIPTION
        "Peer IP"
    ::= { fmHaPeerEntry 2 }

fmHaPeerEntSn OBJECT-TYPE
    SYNTAX      DisplayString
    MAX-ACCESS  read-only
    STATUS      current
    DESCRIPTION
        "Peer serial number"
    ::= { fmHaPeerEntry 3 }

fmHaPeerEntEnabled OBJECT-TYPE
    SYNTAX      FnBoolState
    MAX-ACCESS  read-only
    STATUS      current
    DESCRIPTION
        "Whether peer is enabled"
    ::= { fmHaPeerEntry 4 }

fmHaPeerEntHostName OBJECT-TYPE
    SYNTAX      DisplayString
    MAX-ACCESS  read-only
    STATUS      current
    DESCRIPTION
        "Peer host name"
    ::= { fmHaPeerEntry 5 }

FmHaPeerEntState ::= TEXTUAL-CONVENTION
    STATUS      current
    DESCRIPTION
        "Peer status"
    SYNTAX      INTEGER {
        down (0),
        negotiating   (1),
        synchronizing   (2),
        up (3)
    }

fmHaPeerEntState OBJECT-TYPE
    SYNTAX      FmHaPeerEntState
    MAX-ACCESS  read-only
    STATUS      current
    DESCRIPTION
        "Peer status"
    ::= { fmHaPeerEntry 6 }

--
-- fortinet.fnFortiManagerMib.fmMibConformance
--

fmMIBConformance OBJECT IDENTIFIER
    ::= { fnFortiManagerMib 10 }

fmTrapsComplianceGroup NOTIFICATION-GROUP
    NOTIFICATIONS { fmTrapHASwitch, fmTrapRAIDStatusChange,
                    fmTrapLogAlert, fmTrapLogRateThreshold,
                    fmTrapLogDataRateThreshold,
                    fmTrapLicGbDayThreshold,
                    fmTrapLicDevQuotaThreshold,
                    fmTrapCpuThresholdExcludeNice,
                    fmTrapPowerStateChange,
                    fmTrapFanStateChange,
                    fmTrapTemperatureStateChange,
                    fmTrapVoltageStateChange }
    STATUS      current
    DESCRIPTION
        "Event notifications"
    ::= { fmMIBConformance 1 }

fmSystemObjectGroup OBJECT-GROUP
    OBJECTS     { fmSysMemUsed,         fmSysMemCapacity,
                  fmSysCpuUsage,        fmSysDiskCapacity,
                  fmSysDiskUsage,       fmSysCpuUsageExcludedNice,
                  fmSysVersion,         fmSysUpTime,
                  fmSysLogRate,         fmSysLogRateHr,
                  fmSysLogLagTime,      fmSysLogIndexingRate,
                  fmSysLicGbDayToday,   fmSysLicGbDayYesterday,
                  fmSysLicGbDayWeekAvg, fmSysDiskNumber,
                  fmSysDiskEntName,     fmSysDiskEntUsage,
                  fmSysDiskEntCapacity, fmSysDiskEntIOUtil,
                  fmSysLogForwardName,  fmSysLogForwardNumber, 
                  fmSysLogForwardRate }
    STATUS      current
    DESCRIPTION
        "Objects pertaining to the system status of the device."
    ::= { fmMIBConformance 2 }

fmNotificationObjComplianceGroup OBJECT-GROUP
    OBJECTS     { fmRAIDStatus, fmRAIDDevIndex,
                  fmLogRate, fmLogRateThreshold,
                  fmLogDataRate, fmLogDataRateThreshold,
                  fmLicGbDay, fmLicGbDayThreshold,
                  fmLicDevQuota, fmLicDevQuotaThreshold,
                  fmSensorState, fmSensorName }
    STATUS      current
    DESCRIPTION
        "Object identifiers used in notifications"
    ::= { fmMIBConformance 3 }

fmSessionComplianceGroup OBJECT-GROUP
    OBJECTS {
        fmIpSessProto,
        fmIpSessFromAddr,
        fmIpSessFromPort,
        fmIpSessToAddr,
        fmIpSessToPort,
        fmIpSessExp
        }
    STATUS current
    DESCRIPTION "Session related instrumentation"
	::= { fmMIBConformance 4 }

fmAdomComplianceGroup OBJECT-GROUP
    OBJECTS     { fmAdomEnabled,                  fmAdomNumber,
                  fmAdomMax,                      fmAdomEntName,
                  fmAdomEntState,                 fmAdomEntMode,
                  fmAdomEntFgtNumber,             fmAdomEntPolicyPackageNumber,
                  fmAdomEntOsVersion,             fmAdomEntMr,
                  fmAdomEntVpnMode,               fmAdomEntLogRateMinute,
                  fmAdomEntArchiveLogRetention,   fmAdomEntArchiveLogQuota,
                  fmAdomEntArchiveLogUsedSpace,   fmAdomEntArchiveLogUsedSpacePercent,
                  fmAdomEntAnalyticsLogRetention, fmAdomEntAnalyticsLogQuota,
                  fmAdomEntAnalyticsLogUsedSpace, fmAdomEntAnalyticsLogUsedSpacePercent,
                  fmAdomEntLicGbDayToday,         fmAdomEntLicGbDayYesterday,
                  fmAdomEntLicGbDayWeekAvg }
    STATUS      current
    DESCRIPTION
        "Adom-related configuration and statistics."
    ::= { fmMIBConformance 5 }

fmDeviceComplianceGroup OBJECT-GROUP
    OBJECTS     { fmDeviceNumber,                 fmVdomNumber,
                  fmDeviceEntName,                fmDeviceEntSn,
                  fmDeviceEntMode,                fmDeviceEntAdom,
                  fmDeviceEntIp,                  fmDeviceEntOsVersion,
                  fmDeviceEntMr,                  fmDeviceEntBuild,
                  fmDeviceEntHaMode,              fmDeviceEntHaGroup,
                  fmDeviceEntConnectState,        fmDeviceEntDbState,
                  fmDeviceEntConfigState,         fmDeviceEntState,
                  fmDeviceEntPlatform,            fmDeviceEntVdomEnabled,
                  fmDeviceEntSupportState,        fmDeviceEntAvExpireDate,
                  fmDeviceEntIpsExpireDate,       fmDeviceEntWfExpireDate,
                  fmDeviceEntAsExpireDate,        fmDeviceEntPolicyPackageState,
                  fmDeviceEntDesc,                fmDeviceEntLogRateHour,
                  fmDeviceEntLogRateDay,          fmDeviceEntLogRateWeek,
                  fmDeviceEntArchiveLogUsedSpace }
    STATUS      current
    DESCRIPTION
        "Device-related configuration and statistics."
    ::= { fmMIBConformance 6 }

fmMIBCompliance MODULE-COMPLIANCE
    STATUS      current
    DESCRIPTION
        "The compliance statement for the FortiManager FortiAnalyzer MIB."

    MODULE      -- this module

        GROUP   fmTrapsComplianceGroup
        DESCRIPTION
              "Traps are optional. Not all models support all traps. Consult product literature to see which traps are supported."

        GROUP   fmSystemObjectGroup
        DESCRIPTION
              "Model and feature specific."

        GROUP   fmNotificationObjComplianceGroup
        DESCRIPTION
   	          "Object identifiers used in notifications. Objects are required if their containing trap is implemented."

        GROUP   fmSessionComplianceGroup
        DESCRIPTION
   	          "IP session related implementation."

        GROUP   fmAdomComplianceGroup
        DESCRIPTION
              "This group is mandatory for adom-related configuration and statistics."

        GROUP   fmDeviceComplianceGroup
        DESCRIPTION
              "This group is mandatory for device-related configuration and statistics."

    ::= { fmMIBConformance 100 }

--
-- fortinet.fnFortiManagerMib.fmUm
--

fmUm OBJECT IDENTIFIER
    ::= { fnFortiManagerMib 11 }

-- fortinet.fnFortiManagerMib.fmUm.fmUmContract
fmUmContract OBJECT IDENTIFIER
    ::= { fmUm 1 }

fmUmContractTable OBJECT-TYPE
    SYNTAX      SEQUENCE OF FmUmContractEntry
    MAX-ACCESS  not-accessible
    STATUS      current
    DESCRIPTION
        "A table of Contract"
    ::= { fmUmContract 1 }

fmUmContractEntry OBJECT-TYPE
    SYNTAX      FmUmContractEntry
    MAX-ACCESS  not-accessible
    STATUS      current
    DESCRIPTION
        "Contarct entry"
    INDEX       { fmUmContractEntryIndex }
    ::= { fmUmContractTable 1 }

FmUmContractEntry ::= SEQUENCE {
     fmUmContractEntryIndex  FnIndex,
     fmUmContractEntrySerial DisplayString,
     fmUmContractEntryData   DisplayString
}

fmUmContractEntryIndex OBJECT-TYPE
    SYNTAX      FnIndex
    MAX-ACCESS  not-accessible
    STATUS      current
    DESCRIPTION
        "An index value that uniquely identifies within the fmUmContractTable"
    ::= { fmUmContractEntry 1 }

fmUmContractEntrySerial OBJECT-TYPE
    SYNTAX      DisplayString (SIZE(16))
    MAX-ACCESS  read-only
    STATUS      current
    DESCRIPTION
        "Device Serial Number"
    ::= { fmUmContractEntry 2 }

fmUmContractEntryData OBJECT-TYPE
    SYNTAX      DisplayString (SIZE(0..512))
    MAX-ACCESS  read-only
    STATUS      current
    DESCRIPTION
        "Contract Raw Data"
    ::= { fmUmContractEntry 3 }

------------------------------------------------------------
FmUmServiceStatus ::= TEXTUAL-CONVENTION
    STATUS      current
    DESCRIPTION
        "Service Status"
    SYNTAX      INTEGER {
        unknown (0),
        up (1),
        down (2)
    }

FmUmBoolState ::= TEXTUAL-CONVENTION
    STATUS      current
    DESCRIPTION
        "Boolean state"
    SYNTAX      INTEGER {
        unknown (0),
        yes (1),
        no (2)
    }

-- fortinet.fnFortiManagerMib.fmUm.fmUmFds
fmUmFds OBJECT IDENTIFIER
    ::= { fmUm 2 }

-- fortinet.fnFortiManagerMib.fmUm.fmUmFds.fmUmFdsServiceFds
fmUmFdsServiceFds OBJECT IDENTIFIER
    ::= { fmUmFds 1 }

fmUmFdsServiceFdsStatus OBJECT-TYPE
    SYNTAX     FmUmServiceStatus
    MAX-ACCESS  read-only
    STATUS      current
    DESCRIPTION
        "FDS Service Status"
    ::= { fmUmFdsServiceFds 1 }

fmUmFdsServiceFdsServerTable OBJECT-TYPE
    SYNTAX      SEQUENCE OF FmUmFdsServiceFdsServerEntry
    MAX-ACCESS  not-accessible
    STATUS      current
    DESCRIPTION
        "A table of server list for FDS service"
    ::= { fmUmFdsServiceFds 2 }

fmUmFdsServiceFdsServerEntry OBJECT-TYPE
    SYNTAX      FmUmFdsServiceFdsServerEntry
    MAX-ACCESS  not-accessible
    STATUS      current
    DESCRIPTION
        "server info for FDS service"
    INDEX       { fmUmFdsServiceFdsServerEntryIndex }
    ::= { fmUmFdsServiceFdsServerTable 1 }

FmUmFdsServiceFdsServerEntry ::= SEQUENCE {
     fmUmFdsServiceFdsServerEntryIndex FnIndex,
     fmUmFdsServiceFdsServerAddr       InetAddress,
     fmUmFdsServiceFdsServerPort       InetPortNumber,
     fmUmFdsServiceFdsServerTimeZone   Integer32,
     fmUmFdsServiceFdsServerCurrent    FmUmBoolState
}

fmUmFdsServiceFdsServerEntryIndex OBJECT-TYPE
    SYNTAX      FnIndex
    MAX-ACCESS  not-accessible
    STATUS      current
    DESCRIPTION
        "An index value that uniquely identifies within the fmUmFdsServiceFdsServerTable"
    ::= { fmUmFdsServiceFdsServerEntry 1 }

fmUmFdsServiceFdsServerAddr OBJECT-TYPE
    SYNTAX      InetAddress
    MAX-ACCESS  read-only
    STATUS      current
    DESCRIPTION "Server's Address"
    ::= { fmUmFdsServiceFdsServerEntry 2 }

fmUmFdsServiceFdsServerPort OBJECT-TYPE
    SYNTAX      InetPortNumber
    MAX-ACCESS  read-only
    STATUS      current
    DESCRIPTION "Server's Port"
    ::= { fmUmFdsServiceFdsServerEntry 3 }

fmUmFdsServiceFdsServerTimeZone OBJECT-TYPE
    SYNTAX      Integer32
    MAX-ACCESS  read-only
    STATUS      current
    DESCRIPTION "Server's Time Zone"
    ::= { fmUmFdsServiceFdsServerEntry 4 }

fmUmFdsServiceFdsServerCurrent OBJECT-TYPE
    SYNTAX      FmUmBoolState
    MAX-ACCESS  read-only
    STATUS      current
    DESCRIPTION "Current Server"
    ::= { fmUmFdsServiceFdsServerEntry 5 }

-- fortinet.fnFortiManagerMib.fmUm.fmUmFds.fmUmFdsServiceFct
fmUmFdsServiceFct OBJECT IDENTIFIER
    ::= { fmUmFds 2 }

fmUmFdsServiceFctStatus OBJECT-TYPE
    SYNTAX     FmUmServiceStatus
    MAX-ACCESS  read-only
    STATUS      current
    DESCRIPTION
        "FDS Service Status"
    ::= { fmUmFdsServiceFct 1 }

fmUmFdsServiceFctServerTable OBJECT-TYPE
    SYNTAX      SEQUENCE OF FmUmFdsServiceFctServerEntry
    MAX-ACCESS  not-accessible
    STATUS      current
    DESCRIPTION
        "A table of server list for FDS service"
    ::= { fmUmFdsServiceFct 2 }

fmUmFdsServiceFctServerEntry OBJECT-TYPE
    SYNTAX      FmUmFdsServiceFctServerEntry
    MAX-ACCESS  not-accessible
    STATUS      current
    DESCRIPTION
        "server info for FDS service"
    INDEX       { fmUmFdsServiceFctServerEntryIndex }
    ::= { fmUmFdsServiceFctServerTable 1 }

FmUmFdsServiceFctServerEntry ::= SEQUENCE {
     fmUmFdsServiceFctServerEntryIndex FnIndex,
     fmUmFdsServiceFctServerAddr       InetAddress,
     fmUmFdsServiceFctServerPort       InetPortNumber,
     fmUmFdsServiceFctServerTimeZone   Integer32,
     fmUmFdsServiceFctServerCurrent    FmUmBoolState
}

fmUmFdsServiceFctServerEntryIndex OBJECT-TYPE
    SYNTAX      FnIndex
    MAX-ACCESS  not-accessible
    STATUS      current
    DESCRIPTION
        "An index value that uniquely identifies within the fmUmFdsServiceFctServerTable"
    ::= { fmUmFdsServiceFctServerEntry 1 }

fmUmFdsServiceFctServerAddr OBJECT-TYPE
    SYNTAX      InetAddress
    MAX-ACCESS  read-only
    STATUS      current
    DESCRIPTION "Server's Address"
    ::= { fmUmFdsServiceFctServerEntry 2 }

fmUmFdsServiceFctServerPort OBJECT-TYPE
    SYNTAX      InetPortNumber
    MAX-ACCESS  read-only
    STATUS      current
    DESCRIPTION "Server's Port"
    ::= { fmUmFdsServiceFctServerEntry 3 }

fmUmFdsServiceFctServerTimeZone OBJECT-TYPE
    SYNTAX      Integer32
    MAX-ACCESS  read-only
    STATUS      current
    DESCRIPTION "Server's Time Zone"
    ::= { fmUmFdsServiceFctServerEntry 4 }

fmUmFdsServiceFctServerCurrent OBJECT-TYPE
    SYNTAX      FmUmBoolState
    MAX-ACCESS  read-only
    STATUS      current
    DESCRIPTION "Current Server"
    ::= { fmUmFdsServiceFctServerEntry 5 }

-- fortinet.fnFortiManagerMib.fmUm.fmUmFds.fmUmPackage
fmUmFdsPackage OBJECT IDENTIFIER
    ::= { fmUmFds 3 }

fmUmFdsObjectTable OBJECT-TYPE
    SYNTAX      SEQUENCE OF FmUmFdsObjectEntry
    MAX-ACCESS  not-accessible
    STATUS      current
    DESCRIPTION
        "A table of server list for FDS object"
    ::= { fmUmFdsPackage 1 }

fmUmFdsObjectEntry OBJECT-TYPE
    SYNTAX     FmUmFdsObjectEntry
    MAX-ACCESS  not-accessible
    STATUS      current
    DESCRIPTION
        "FDS object"
    INDEX       { fmUmFdsObjectEntryIndex }
    ::= { fmUmFdsObjectTable 1 }

FmUmFdsObjectEntry::= SEQUENCE {
     fmUmFdsObjectEntryIndex   FnIndex,
     fmUmFdsObjectEntryObjid   DisplayString,
     fmUmFdsObjectEntryVersion DisplayString,
     fmUmFdsObjectEntryDate    DisplayString,
     fmUmFdsObjectEntrySize    Counter64,
     fmUmFdsObjectEntryDesc    DisplayString,
     fmUmFdsObjectEntryProduct DisplayString
}

fmUmFdsObjectEntryIndex OBJECT-TYPE
    SYNTAX      FnIndex
    MAX-ACCESS  not-accessible
    STATUS      current
    DESCRIPTION
        "index of fmUmFdsObjectTable"
    ::= { fmUmFdsObjectEntry 1 }

fmUmFdsObjectEntryObjid OBJECT-TYPE
    SYNTAX      DisplayString (SIZE(17))
    MAX-ACCESS  read-only
    STATUS      current
    DESCRIPTION
        "object id"
    ::= { fmUmFdsObjectEntry 2 }

fmUmFdsObjectEntryVersion OBJECT-TYPE
    SYNTAX      DisplayString (SIZE(0..16))
    MAX-ACCESS  read-only
    STATUS      current
    DESCRIPTION
        "object version"
    ::= { fmUmFdsObjectEntry 3 }

fmUmFdsObjectEntryDate OBJECT-TYPE
    SYNTAX      DisplayString (SIZE(0..32))
    MAX-ACCESS  read-only
    STATUS      current
    DESCRIPTION
        "object date"
    ::= { fmUmFdsObjectEntry 4 }

fmUmFdsObjectEntrySize OBJECT-TYPE
    SYNTAX      Counter64
    MAX-ACCESS  read-only
    STATUS      current
    DESCRIPTION
        "object size"
    ::= { fmUmFdsObjectEntry 5 }

fmUmFdsObjectEntryDesc OBJECT-TYPE
    SYNTAX      DisplayString (SIZE(0..256))
    MAX-ACCESS  read-only
    STATUS      current
    DESCRIPTION
        "object description"
    ::= { fmUmFdsObjectEntry 6 }

fmUmFdsObjectEntryProduct OBJECT-TYPE
    SYNTAX      DisplayString (SIZE(0..16))
    MAX-ACCESS  read-only
    STATUS      current
    DESCRIPTION
        "proudct"
    ::= { fmUmFdsObjectEntry 7 }


----------------------------------------------------------------------------
-- fortinet.fnFortiManagerMib.fmUm.fmUmFds.fmUmDevice.fmUmDeviceStatus
fmUmDevice OBJECT IDENTIFIER
    ::= { fmUmFds 4 }

fmUmDeviceStatusTable OBJECT-TYPE
    SYNTAX      SEQUENCE OF FmUmDeviceStatusEntry
    MAX-ACCESS  not-accessible
    STATUS      current
    DESCRIPTION
        "table of device status"
    ::= { fmUmDevice 1 }

fmUmDeviceStatusEntry OBJECT-TYPE
    SYNTAX     FmUmDeviceStatusEntry
    MAX-ACCESS  not-accessible
    STATUS      current
    DESCRIPTION
        "FDS object"
    INDEX       { fmUmDeviceStatusEntryIndex }
    ::= { fmUmDeviceStatusTable 1 }

FmUmDeviceStatusEntry::= SEQUENCE {
     fmUmDeviceStatusEntryIndex      FnIndex,
     fmUmDeviceStatusEntrySerial     DisplayString,
     fmUmDeviceStatusEntryStatus     DisplayString,
     fmUmDeviceStatusEntryUpdateTime Counter64
}

fmUmDeviceStatusEntryIndex OBJECT-TYPE
    SYNTAX      FnIndex
    MAX-ACCESS  not-accessible
    STATUS      current
    DESCRIPTION
        "index of fmUmDeviceStatusTable"
    ::= { fmUmDeviceStatusEntry 1 }

fmUmDeviceStatusEntrySerial OBJECT-TYPE
    SYNTAX      DisplayString (SIZE(16))
    MAX-ACCESS  read-only
    STATUS      current
    DESCRIPTION
        "Device Serial Number"
    ::= { fmUmDeviceStatusEntry 2 }

fmUmDeviceStatusEntryStatus OBJECT-TYPE
    SYNTAX      DisplayString (SIZE(0..16))
    MAX-ACCESS  read-only
    STATUS      current
    DESCRIPTION
        "Device update status"
    ::= { fmUmDeviceStatusEntry 3 }

fmUmDeviceStatusEntryUpdateTime OBJECT-TYPE
    SYNTAX      Counter64
    MAX-ACCESS  read-only
    STATUS      current
    DESCRIPTION
        "Device update time"
    ::= { fmUmDeviceStatusEntry 4 }

-- fortinet.fnFortiManagerMib.fmUm.fmUmFds.fmUmDevice.fmUmDeviceObject

fmUmDeviceObjectTable OBJECT-TYPE
    SYNTAX      SEQUENCE OF FmUmDeviceObjectEntry
    MAX-ACCESS  not-accessible
    STATUS      current
    DESCRIPTION
        "table of device status"
    ::= { fmUmDevice 2 }

fmUmDeviceObjectEntry OBJECT-TYPE
    SYNTAX     FmUmDeviceObjectEntry
    MAX-ACCESS  not-accessible
    STATUS      current
    DESCRIPTION
        "FDS object"
    INDEX       { fmUmDeviceObjectEntryIndex }
    ::= { fmUmDeviceObjectTable 1 }

FmUmDeviceObjectEntry::= SEQUENCE {
     fmUmDeviceObjectEntryIndex         FnIndex,
     fmUmDeviceObjectEntrySerial        DisplayString,
     fmUmDeviceObjectEntryObjid         DisplayString,
     fmUmDeviceObjectEntryDeviceVersion DisplayString,
     fmUmDeviceObjectEntryServerVersion DisplayString,
     fmUmDeviceObjectEntryPreferVersion DisplayString
}

fmUmDeviceObjectEntryIndex OBJECT-TYPE
    SYNTAX      FnIndex
    MAX-ACCESS  not-accessible
    STATUS      current
    DESCRIPTION
        "index of fmUmDeviceObjectTable"
    ::= { fmUmDeviceObjectEntry 1 }

fmUmDeviceObjectEntrySerial OBJECT-TYPE
    SYNTAX      DisplayString (SIZE(16))
    MAX-ACCESS  read-only
    STATUS      current
    DESCRIPTION
        "Device Serial Number"
    ::= { fmUmDeviceObjectEntry 2 }

fmUmDeviceObjectEntryObjid OBJECT-TYPE
    SYNTAX      DisplayString (SIZE(17))
    MAX-ACCESS  read-only
    STATUS      current
    DESCRIPTION
        "object id"
    ::= { fmUmDeviceObjectEntry 3 }

fmUmDeviceObjectEntryDeviceVersion OBJECT-TYPE
    SYNTAX      DisplayString (SIZE(0..16))
    MAX-ACCESS  read-only
    STATUS      current
    DESCRIPTION
        "object version"
    ::= { fmUmDeviceObjectEntry 4 }

fmUmDeviceObjectEntryServerVersion OBJECT-TYPE
    SYNTAX      DisplayString (SIZE(0..16))
    MAX-ACCESS  read-only
    STATUS      current
    DESCRIPTION
        "object version"
    ::= { fmUmDeviceObjectEntry 5 }

fmUmDeviceObjectEntryPreferVersion OBJECT-TYPE
    SYNTAX      DisplayString (SIZE(0..16))
    MAX-ACCESS  read-only
    STATUS      current
    DESCRIPTION
        "object version"
    ::= { fmUmDeviceObjectEntry 6 }

----------------------------------------------------------------------------

-- fortinet.fnFortiManagerMib.fmUm.fmUmFgd
fmUmFgd OBJECT IDENTIFIER
    ::= { fmUm 3 }

-- fortinet.fnFortiManagerMib.fmUm.fmUmFgd.fmUmFgdServiceFgd
fmUmFgdServiceFgd OBJECT IDENTIFIER
    ::= { fmUmFgd 1 }

fmUmFgdServiceFgdStatus OBJECT-TYPE
    SYNTAX     FmUmServiceStatus
    MAX-ACCESS  read-only
    STATUS      current
    DESCRIPTION
        "FGD Service Status"
    ::= { fmUmFgdServiceFgd 1 }

fmUmFgdServiceFgdServerTable OBJECT-TYPE
    SYNTAX      SEQUENCE OF FmUmFgdServiceFgdServerEntry
    MAX-ACCESS  not-accessible
    STATUS      current
    DESCRIPTION
        "A table of server list for FDS service"
    ::= { fmUmFgdServiceFgd 2 }

fmUmFgdServiceFgdServerEntry OBJECT-TYPE
    SYNTAX      FmUmFgdServiceFgdServerEntry
    MAX-ACCESS  not-accessible
    STATUS      current
    DESCRIPTION
        "server info for FDS service"
    INDEX       { fmUmFgdServiceFgdServerEntryIndex }
    ::= { fmUmFgdServiceFgdServerTable 1 }

FmUmFgdServiceFgdServerEntry ::= SEQUENCE {
     fmUmFgdServiceFgdServerEntryIndex FnIndex,
     fmUmFgdServiceFgdServerAddr       InetAddress,
     fmUmFgdServiceFgdServerPort       InetPortNumber,
     fmUmFgdServiceFgdServerTimeZone   Integer32,
     fmUmFgdServiceFgdServerCurrent    FmUmBoolState
}

fmUmFgdServiceFgdServerEntryIndex OBJECT-TYPE
    SYNTAX      FnIndex
    MAX-ACCESS  not-accessible
    STATUS      current
    DESCRIPTION
        "An index value that uniquely identifies within the fmUmFgdServiceFgdServerTable"
    ::= { fmUmFgdServiceFgdServerEntry 1 }

fmUmFgdServiceFgdServerAddr OBJECT-TYPE
    SYNTAX      InetAddress
    MAX-ACCESS  read-only
    STATUS      current
    DESCRIPTION "Server's Address"
    ::= { fmUmFgdServiceFgdServerEntry 2 }

fmUmFgdServiceFgdServerPort OBJECT-TYPE
    SYNTAX      InetPortNumber
    MAX-ACCESS  read-only
    STATUS      current
    DESCRIPTION "Server's Port"
    ::= { fmUmFgdServiceFgdServerEntry 3 }

fmUmFgdServiceFgdServerTimeZone OBJECT-TYPE
    SYNTAX      Integer32
    MAX-ACCESS  read-only
    STATUS      current
    DESCRIPTION "Server's Time Zone"
    ::= { fmUmFgdServiceFgdServerEntry 4 }

fmUmFgdServiceFgdServerCurrent OBJECT-TYPE
    SYNTAX      FmUmBoolState
    MAX-ACCESS  read-only
    STATUS      current
    DESCRIPTION "Current Server"
    ::= { fmUmFgdServiceFgdServerEntry 5 }

fmUmFgdServiceFgfq OBJECT IDENTIFIER
    ::= { fmUmFgd 2 }

fmUmFgdServiceFgfqStatus OBJECT-TYPE
    SYNTAX     FmUmServiceStatus
    MAX-ACCESS  read-only
    STATUS      current
    DESCRIPTION
        "FGD Service Status"
    ::= { fmUmFgdServiceFgfq 1 }

fmUmFgdServiceFgfqServerTable OBJECT-TYPE
    SYNTAX      SEQUENCE OF FmUmFgdServiceFgfqServerEntry
    MAX-ACCESS  not-accessible
    STATUS      current
    DESCRIPTION
        "A table of server list for FDS service"
    ::= { fmUmFgdServiceFgfq 2 }

fmUmFgdServiceFgfqServerEntry OBJECT-TYPE
    SYNTAX      FmUmFgdServiceFgfqServerEntry
    MAX-ACCESS  not-accessible
    STATUS      current
    DESCRIPTION
        "server info for FDS service"
    INDEX       { fmUmFgdServiceFgfqServerEntryIndex }
    ::= { fmUmFgdServiceFgfqServerTable 1 }

FmUmFgdServiceFgfqServerEntry ::= SEQUENCE {
     fmUmFgdServiceFgfqServerEntryIndex FnIndex,
     fmUmFgdServiceFgfqServerAddr       InetAddress,
     fmUmFgdServiceFgfqServerPort       InetPortNumber,
     fmUmFgdServiceFgfqServerTimeZone   Integer32,
     fmUmFgdServiceFgfqServerCurrent    FmUmBoolState
}

fmUmFgdServiceFgfqServerEntryIndex OBJECT-TYPE
    SYNTAX      FnIndex
    MAX-ACCESS  not-accessible
    STATUS      current
    DESCRIPTION
        "An index value that uniquely identifies within the fmUmFgdServiceFgfqServerTable"
    ::= { fmUmFgdServiceFgfqServerEntry 1 }

fmUmFgdServiceFgfqServerAddr OBJECT-TYPE
    SYNTAX      InetAddress
    MAX-ACCESS  read-only
    STATUS      current
    DESCRIPTION "Server's Address"
    ::= { fmUmFgdServiceFgfqServerEntry 2 }

fmUmFgdServiceFgfqServerPort OBJECT-TYPE
    SYNTAX      InetPortNumber
    MAX-ACCESS  read-only
    STATUS      current
    DESCRIPTION "Server's Port"
    ::= { fmUmFgdServiceFgfqServerEntry 3 }

fmUmFgdServiceFgfqServerTimeZone OBJECT-TYPE
    SYNTAX      Integer32
    MAX-ACCESS  read-only
    STATUS      current
    DESCRIPTION "Server's Time Zone"
    ::= { fmUmFgdServiceFgfqServerEntry 4 }

fmUmFgdServiceFgfqServerCurrent OBJECT-TYPE
    SYNTAX      FmUmBoolState
    MAX-ACCESS  read-only
    STATUS      current
    DESCRIPTION "Current Server"
    ::= { fmUmFgdServiceFgfqServerEntry 5 }

-- fortinet.fnFortiManagerMib.fmUm.fmUmFgd.fmUmFgdPackage
fmUmFgdPackage OBJECT IDENTIFIER
    ::= { fmUmFgd 3 }

fmUmFgdDBVersionTable OBJECT-TYPE
    SYNTAX      SEQUENCE OF FmUmFgdDBVersionEntry
    MAX-ACCESS  not-accessible
    STATUS      current
    DESCRIPTION
        "A table of server list for fgd db version object"
    ::= { fmUmFgdPackage 1 }

fmUmFgdDBVersionEntry OBJECT-TYPE
    SYNTAX    FmUmFgdDBVersionEntry
    MAX-ACCESS  not-accessible
    STATUS      current
    DESCRIPTION
        "fgd db version"
    INDEX       { fmUmFgdDBVersionEntryIndex }
    ::= { fmUmFgdDBVersionTable 1 }

FmUmFgdDBVersionEntry::= SEQUENCE {
     fmUmFgdDBVersionEntryIndex    FnIndex,
     fmUmFgdDBVersionEntryCategory DisplayString,
     fmUmFgdDBVersionEntryVersion  DisplayString,
     fmUmFgdDBVersionEntrySize     Counter64,
     fmUmFgdDBVersionEntryDate     Counter64,
     fmUmFgdDBVersionEntryDesc     DisplayString
}

fmUmFgdDBVersionEntryIndex OBJECT-TYPE
    SYNTAX      FnIndex
    MAX-ACCESS  not-accessible
    STATUS      current
    DESCRIPTION
        "index of fmUmFgdDBVersionTable"
    ::= { fmUmFgdDBVersionEntry 1 }

fmUmFgdDBVersionEntryCategory OBJECT-TYPE
    SYNTAX      DisplayString (SIZE(0..16))
    MAX-ACCESS  read-only
    STATUS      current
    DESCRIPTION
        "category"
    ::= { fmUmFgdDBVersionEntry 2 }

fmUmFgdDBVersionEntryVersion OBJECT-TYPE
    SYNTAX      DisplayString (SIZE(0..16))
    MAX-ACCESS  read-only
    STATUS      current
    DESCRIPTION
        "version"
    ::= { fmUmFgdDBVersionEntry 3 }

fmUmFgdDBVersionEntrySize OBJECT-TYPE
    SYNTAX      Counter64
    MAX-ACCESS  read-only
    STATUS      current
    DESCRIPTION
        "size"
    ::= { fmUmFgdDBVersionEntry 4 }

fmUmFgdDBVersionEntryDate OBJECT-TYPE
    SYNTAX      Counter64
    MAX-ACCESS  read-only
    STATUS      current
    DESCRIPTION
        "date"
    ::= { fmUmFgdDBVersionEntry 5 }

fmUmFgdDBVersionEntryDesc OBJECT-TYPE
    SYNTAX      DisplayString (SIZE(0..128))
    MAX-ACCESS  read-only
    STATUS      current
    DESCRIPTION
        "descriptions"
    ::= { fmUmFgdDBVersionEntry 6 }

-- fortinet.fnFortiManagerMib.fmUm.fmUmFgd.fmUmFgdQueryStatistic
fmUmFgdQueryStatistic OBJECT IDENTIFIER
    ::= { fmUmFgd 4 }

-- fortinet.fnFortiManagerMib.fmUm.fmUmFgd.fmUmFgdQueryStatistic.fmUmFgdQueryStatisticTop10SitesTable
fmUmFgdQueryStatisticTop10SitesTable OBJECT-TYPE
    SYNTAX      SEQUENCE OF FmUmFgdQueryStatisticTop10SitesEntry
    MAX-ACCESS  not-accessible
    STATUS      current
    DESCRIPTION
        "Top 10 sites table"
    ::= { fmUmFgdQueryStatistic 1 }

fmUmFgdQueryStatisticTop10SitesEntry OBJECT-TYPE
    SYNTAX    FmUmFgdQueryStatisticTop10SitesEntry
    MAX-ACCESS  not-accessible
    STATUS      current
    DESCRIPTION
        "Index of top 10 sites table"
    INDEX       { fmUmFgdQueryStatisticTop10SitesEntryIndex }
    ::= { fmUmFgdQueryStatisticTop10SitesTable 1 }

FmUmFgdQueryStatisticTop10SitesEntry::= SEQUENCE {
     fmUmFgdQueryStatisticTop10SitesEntryIndex    FnIndex,
     fmUmFgdQueryStatisticTop10SitesEntryAddress  InetAddress,
     fmUmFgdQueryStatisticTop10SitesEntryVisits   Counter64
}

fmUmFgdQueryStatisticTop10SitesEntryIndex OBJECT-TYPE
    SYNTAX      FnIndex
    MAX-ACCESS  not-accessible
    STATUS      current
    DESCRIPTION
        "Index"
    ::= { fmUmFgdQueryStatisticTop10SitesEntry 1 }

fmUmFgdQueryStatisticTop10SitesEntryAddress OBJECT-TYPE
    SYNTAX      InetAddress
    MAX-ACCESS  read-only
    STATUS      current
    DESCRIPTION "Site Address"
    ::= { fmUmFgdQueryStatisticTop10SitesEntry 2 }

fmUmFgdQueryStatisticTop10SitesEntryVisits OBJECT-TYPE
    SYNTAX      Counter64
    MAX-ACCESS  read-only
    STATUS      current
    DESCRIPTION "Site Address"
    ::= { fmUmFgdQueryStatisticTop10SitesEntry 3 }

-- fortinet.fnFortiManagerMib.fmUm.fmUmFgd.fmUmFgdQueryStatistic.fmUmFgdQueryStatisticTop10DevicesTable
fmUmFgdQueryStatisticTop10DevicesTable OBJECT-TYPE
    SYNTAX      SEQUENCE OF FmUmFgdQueryStatisticTop10DevicesEntry
    MAX-ACCESS  not-accessible
    STATUS      current
    DESCRIPTION
        "Top 10 devices table"
    ::= { fmUmFgdQueryStatistic 2 }

fmUmFgdQueryStatisticTop10DevicesEntry OBJECT-TYPE
    SYNTAX    FmUmFgdQueryStatisticTop10DevicesEntry
    MAX-ACCESS  not-accessible
    STATUS      current
    DESCRIPTION
        "Index of top 10 devicess table"
    INDEX       { fmUmFgdQueryStatisticTop10DevicesEntryIndex }
    ::= { fmUmFgdQueryStatisticTop10DevicesTable 1 }

FmUmFgdQueryStatisticTop10DevicesEntry::= SEQUENCE {
     fmUmFgdQueryStatisticTop10DevicesEntryIndex    FnIndex,
     fmUmFgdQueryStatisticTop10DevicesEntryName     DisplayString,
     fmUmFgdQueryStatisticTop10DevicesEntryQueries  Counter64
}

fmUmFgdQueryStatisticTop10DevicesEntryIndex OBJECT-TYPE
    SYNTAX      FnIndex
    MAX-ACCESS  not-accessible
    STATUS      current
    DESCRIPTION
        "Index"
    ::= { fmUmFgdQueryStatisticTop10DevicesEntry 1 }

fmUmFgdQueryStatisticTop10DevicesEntryName OBJECT-TYPE
    SYNTAX      DisplayString (SIZE(1..512))
    MAX-ACCESS  read-only
    STATUS      current
    DESCRIPTION "Device name"
    ::= { fmUmFgdQueryStatisticTop10DevicesEntry 2 }

fmUmFgdQueryStatisticTop10DevicesEntryQueries OBJECT-TYPE
    SYNTAX      Counter64
    MAX-ACCESS  read-only
    STATUS      current
    DESCRIPTION "Query number of the device"
    ::= { fmUmFgdQueryStatisticTop10DevicesEntry 3 }


-- fortinet.fnFortiManagerMib.fmUm.fmUmFgd.fmUmFgdQueryStatistic.fmUmFgdQueryStatisticQueryHistoryTable
fmUmFgdQueryStatisticQueryHistoryTable OBJECT-TYPE
    SYNTAX      SEQUENCE OF FmUmFgdQueryStatisticQueryHistoryEntry
    MAX-ACCESS  not-accessible
    STATUS      current
    DESCRIPTION
        "Query history table"
    ::= { fmUmFgdQueryStatistic 3 }

fmUmFgdQueryStatisticQueryHistoryEntry OBJECT-TYPE
    SYNTAX    FmUmFgdQueryStatisticQueryHistoryEntry
    MAX-ACCESS  not-accessible
    STATUS      current
    DESCRIPTION
        "Index of Query history table"
    INDEX       { fmUmFgdQueryStatisticQueryHistoryEntryIndex }
    ::= { fmUmFgdQueryStatisticQueryHistoryTable 1 }

FmUmFgdQueryStatisticQueryHistoryEntry::= SEQUENCE {
     fmUmFgdQueryStatisticQueryHistoryEntryIndex         FnIndex,
     fmUmFgdQueryStatisticQueryHistoryEntryBeginTime     Counter64,
     fmUmFgdQueryStatisticQueryHistoryEntryEndTime       Counter64,
     fmUmFgdQueryStatisticQueryHistoryEntryDeviceName    DisplayString,
     fmUmFgdQueryStatisticQueryHistoryEntryDeviceAddress InetAddress,
     fmUmFgdQueryStatisticQueryHistoryEntryQueries       Counter64,
     fmUmFgdQueryStatisticQueryHistoryEntryHits          Counter64,
     fmUmFgdQueryStatisticQueryHistoryEntryMisses        Counter64,
     fmUmFgdQueryStatisticQueryHistoryEntryBandWidth     DisplayString
}

fmUmFgdQueryStatisticQueryHistoryEntryIndex OBJECT-TYPE
    SYNTAX      FnIndex
    MAX-ACCESS  not-accessible
    STATUS      current
    DESCRIPTION
        "Index"
    ::= { fmUmFgdQueryStatisticQueryHistoryEntry 1 }

fmUmFgdQueryStatisticQueryHistoryEntryBeginTime OBJECT-TYPE
    SYNTAX      Counter64
    MAX-ACCESS  read-only
    STATUS      current
    DESCRIPTION ""
    ::= { fmUmFgdQueryStatisticQueryHistoryEntry 2 }

fmUmFgdQueryStatisticQueryHistoryEntryEndTime OBJECT-TYPE
    SYNTAX      Counter64
    MAX-ACCESS  read-only
    STATUS      current
    DESCRIPTION ""
    ::= { fmUmFgdQueryStatisticQueryHistoryEntry 3 }

fmUmFgdQueryStatisticQueryHistoryEntryDeviceName OBJECT-TYPE
    SYNTAX      DisplayString (SIZE(1..512))
    MAX-ACCESS  read-only
    STATUS      current
    DESCRIPTION "Device name"
    ::= { fmUmFgdQueryStatisticQueryHistoryEntry 4 }

fmUmFgdQueryStatisticQueryHistoryEntryDeviceAddress OBJECT-TYPE
    SYNTAX      InetAddress
    MAX-ACCESS  read-only
    STATUS      current
    DESCRIPTION "Device address"
    ::= { fmUmFgdQueryStatisticQueryHistoryEntry 5 }

fmUmFgdQueryStatisticQueryHistoryEntryQueries OBJECT-TYPE
    SYNTAX      Counter64
    MAX-ACCESS  read-only
    STATUS      current
    DESCRIPTION ""
    ::= { fmUmFgdQueryStatisticQueryHistoryEntry 6 }

fmUmFgdQueryStatisticQueryHistoryEntryHits OBJECT-TYPE
    SYNTAX      Counter64
    MAX-ACCESS  read-only
    STATUS      current
    DESCRIPTION ""
    ::= { fmUmFgdQueryStatisticQueryHistoryEntry 7 }

fmUmFgdQueryStatisticQueryHistoryEntryMisses OBJECT-TYPE
    SYNTAX      Counter64
    MAX-ACCESS  read-only
    STATUS      current
    DESCRIPTION ""
    ::= { fmUmFgdQueryStatisticQueryHistoryEntry 8 }

fmUmFgdQueryStatisticQueryHistoryEntryBandWidth OBJECT-TYPE
    SYNTAX      DisplayString (SIZE(0..16))
    MAX-ACCESS  read-only
    STATUS      current
    DESCRIPTION "Device name"
    ::= { fmUmFgdQueryStatisticQueryHistoryEntry 9 }

END -- end of module FORTINET-FORTIMANAGER-FORTIANALYZER-MIB.
