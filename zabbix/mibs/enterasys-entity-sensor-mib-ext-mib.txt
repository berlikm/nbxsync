ENTERASYS-ENTITY-SENSOR-MIB-EXT-MIB DEFINITIONS ::= BEGIN

--  enterasys-entity-sensor-mib-ext-mib.txt
--
--  Part Number:
--
--

--  This module provides authoritative definitions for Enterasys
--  Networks' Entity Sensor MIB Extensions functionality.

--
--  This module will be extended, as needed.

--  Extreme Networks reserves the right to make changes in this
--  specification and other information contained in this document
--  without prior notice.  The reader should consult Extreme Networks
--  to determine whether any such changes have been made.
--
--  In no event shall Extreme Networks be liable for any incidental,
--  indirect, special, or consequential damages whatsoever (including
--  but not limited to lost profits) arising out of or related to this
--  document or the information contained in it, even if Extreme
--  Networks has been advised of, known, or should have known, the
--  possibility of such damages.
--
--  Extreme Networks grants vendors, end-users, and other interested
--  parties a non-exclusive license to use this Specification in
--  connection with the management of Extreme Networks products.

--  Copyright May 2014 Extreme Networks, Inc.

IMPORTS
    MODULE-IDENTITY, OBJECT-TYPE, NOTIFICATION-TYPE
        FROM SNMPv2-SMI
    MODULE-COMPLIANCE, OBJECT-GROUP, NOTIFICATION-GROUP
        FROM SNMPv2-CONF
    entPhysicalIndex
        FROM ENTITY-MIB
    entPhySensorScale, entPhySensorPrecision, entPhySensorValue,
    EntitySensorValue, entPhySensorOperStatus, entPhySensorUnitsDisplay
        FROM ENTITY-SENSOR-MIB
    EnabledStatus
        FROM P-BRIDGE-MIB
    etsysModules
        FROM ENTERASYS-MIB-NAMES;

etsysEntitySensorExtMIB MODULE-IDENTITY
    LAST-UPDATED "202210201620Z"  -- Thu Oct 20 16:20 UTC 2022
    ORGANIZATION "Extreme Networks Inc."
    CONTACT-INFO
        "Postal:  Extreme Networks, Inc.
                  145 Rio Robles
                  San Jose, CA 95134 USA

         Phone:   +1 408 579-2800
         E-mail:  support@extremenetworks.com
         WWW:     http://www.extremenetworks.com"

    DESCRIPTION
        "This MIB module defines a portion of the SNMP MIB under
         the Enterasys Networks enterprise OID that provide
         extensions to the industry proposed standard ENTITY-SENSOR-MIB."

    REVISION    "202210201620Z"  -- Thu Oct 20 16:20 UTC 2022
    DESCRIPTION
        "Added etsysEntitySfpSensorSupportedSpeeds to EtsysEntitySfpSensorExtEntry."

    REVISION    "202111051000Z"  -- Fri Nov 05 10:00 UTC 2021
    DESCRIPTION
        "Added etsysEntitySfpSensorTxDdm, etsysEntitySfpSensorTxDdmLastGasp,
         etsysEntitySfpSensorRxDdm and etsysEntitySfpSensorRxDdmLastGasp to
         EtsysEntitySfpSensorExtEntry."

    REVISION    "202110221514Z"  -- Fri Oct 22 15:14 UTC 2021
    DESCRIPTION
        "Added etsysEntitySfpSensorWavelength and
         etsysEntitySfpSensorPowerOnCounter to EtsysEntitySfpSensorExtEntry."

    REVISION    "201405131206Z"  -- Tue May 13 12:06 UTC 2014
    DESCRIPTION
        "Added the etsysEntitySfpSensorExt group."

    REVISION    "201110141449Z"  -- Fri Oct 14 14:49 UTC 2011
    DESCRIPTION
        "The initial version of this MIB module."
    ::= { etsysModules 85 }


-- -------------------------------------------------------------
-- MIB Objects
-- -------------------------------------------------------------

etsysEntitySensorExtObjects
         OBJECT IDENTIFIER ::= { etsysEntitySensorExtMIB 1 }

etsysEntitySensorExtNotifications
         OBJECT IDENTIFIER ::= { etsysEntitySensorExtObjects 0 }

etsysEntityTempSensorExt
         OBJECT IDENTIFIER ::= { etsysEntitySensorExtObjects 1 }

etsysEntitySfpSensorExt
         OBJECT IDENTIFIER ::= { etsysEntitySensorExtObjects 2 }

-- -------------------------------------------------------------
-- The Entity Temperature Sensor Extension Group
-- -------------------------------------------------------------

etsysEntityTempSensorExtTable OBJECT-TYPE
    SYNTAX       SEQUENCE OF EtsysEntityTempSensorExtEntry
    MAX-ACCESS   not-accessible
    STATUS       current
    DESCRIPTION
        "A table of per temperature sensor information that extends the
         general information provided in entPhySensorTable as defined in
         RFC3433.  This table should contain an entry for every object
         contained in entPhySensorTable that has an entPhySensorType
         of type celsius(8)."
    ::= {  etsysEntityTempSensorExt 1 }

etsysEntityTempSensorExtEntry OBJECT-TYPE
    SYNTAX       EtsysEntityTempSensorExtEntry
    MAX-ACCESS   not-accessible
    STATUS       current
    DESCRIPTION
        "An entry containing per temperature sensor information."
    INDEX  { entPhysicalIndex }    -- SPARSE-AUGMENTS
    ::= { etsysEntityTempSensorExtTable 1 }

EtsysEntityTempSensorExtEntry ::=
    SEQUENCE {
        etsysEntityTempSensorState
            INTEGER,
        etsysEntityTempSensorHotTemp
            EntitySensorValue,
        etsysEntityTempSensorWarmTemp
            EntitySensorValue,
        etsysEntityTempSensorCoolTemp
            EntitySensorValue,
        etsysEntityTempSensorColdTemp
            EntitySensorValue,
        etsysEntityTempSensorTrapEnable
            EnabledStatus
    }

etsysEntityTempSensorState OBJECT-TYPE
    SYNTAX       INTEGER {
                   unknown(1),             --  none of the following
                   cold(2),
                   cool(3),
                   normal(4),
                   warm(5),
                   hot(6)
                 }
    MAX-ACCESS   read-only
    STATUS       current
    DESCRIPTION
        "This object indicates the state of the temperature sensor."
    ::= { etsysEntityTempSensorExtEntry 1 }

etsysEntityTempSensorHotTemp OBJECT-TYPE
    SYNTAX        EntitySensorValue
    MAX-ACCESS    read-only
    STATUS        current
    DESCRIPTION
        "The temperature value above which the ambient temperature
         is deemed to be hot.

         To correctly interpret the value of this object, the
         associated entPhySensorType, entPhySensorScale, and
         entPhySensorPrecision objects must also be examined."
    ::= { etsysEntityTempSensorExtEntry 2 }

etsysEntityTempSensorWarmTemp OBJECT-TYPE
    SYNTAX        EntitySensorValue
    MAX-ACCESS    read-only
    STATUS        current
    DESCRIPTION
        "The temperature value above which the ambient temperature
         is deemed to be warm, if it is below or equal the hot
         value.

         To correctly interpret the value of this object, the
         associated entPhySensorType, entPhySensorScale, and
         entPhySensorPrecision objects must also be examined."
    ::= { etsysEntityTempSensorExtEntry 3 }

etsysEntityTempSensorCoolTemp OBJECT-TYPE
    SYNTAX        EntitySensorValue
    MAX-ACCESS    read-only
    STATUS        current
    DESCRIPTION
        "The temperature value below which the ambient temperature
         is deemed to be cool, if it is above or equal the cold
         value.

         To correctly interpret the value of this object, the
         associated entPhySensorType, entPhySensorScale, and
         entPhySensorPrecision objects must also be examined."
    ::= { etsysEntityTempSensorExtEntry 4 }

etsysEntityTempSensorColdTemp OBJECT-TYPE
    SYNTAX        EntitySensorValue
    MAX-ACCESS    read-only
    STATUS        current
    DESCRIPTION
        "The temperature value below which the ambient temperature
         is deemed to be cold.

         To correctly interpret the value of this object, the
         associated entPhySensorType, entPhySensorScale, and
         entPhySensorPrecision objects must also be examined."
    ::= { etsysEntityTempSensorExtEntry 5 }

etsysEntityTempSensorTrapEnable OBJECT-TYPE
    SYNTAX       EnabledStatus
    MAX-ACCESS   read-write
    STATUS       current
    DESCRIPTION
        "This object indicates whether the etsysEntityTempSensorStateChng
         notification will be sent when the sensor state changes as
         defined by etsysEntityTempSensorState."
    DEFVAL      { enabled }
    ::= { etsysEntityTempSensorExtEntry 6 }

-- -------------------------------------------------------------
-- The Entity Sfp Sensor Extension Group
-- -------------------------------------------------------------

etsysEntitySfpSensorExtTable OBJECT-TYPE
    SYNTAX       SEQUENCE OF EtsysEntitySfpSensorExtEntry
    MAX-ACCESS   not-accessible
    STATUS       current
    DESCRIPTION
        "A table of per SFP sensor information that extends the
         general information provided in entPhySensorTable as defined in
         RFC3433."
    ::= {  etsysEntitySfpSensorExt 1 }

etsysEntitySfpSensorExtEntry OBJECT-TYPE
    SYNTAX       EtsysEntitySfpSensorExtEntry
    MAX-ACCESS   not-accessible
    STATUS       current
    DESCRIPTION
        "An entry containing per SFP sensor information."
    INDEX  { entPhysicalIndex }    -- SPARSE-AUGMENTS
    ::= { etsysEntitySfpSensorExtTable 1 }

EtsysEntitySfpSensorExtEntry ::=
    SEQUENCE {
        etsysEntitySfpSensorState
            INTEGER,
        etsysEntitySfpSensorHighAlarm
            EntitySensorValue,
        etsysEntitySfpSensorHighWarning
            EntitySensorValue,
        etsysEntitySfpSensorLowWarning
            EntitySensorValue,
        etsysEntitySfpSensorLowAlarm
            EntitySensorValue,
        etsysEntitySfpSensorWavelength
            Integer32,
        etsysEntitySfpSensorPowerOnCounter
            Counter32,
        etsysEntitySfpSensorTxDdm
            Integer32,
        etsysEntitySfpSensorTxDdmLastGasp
            Integer32,
        etsysEntitySfpSensorRxDdm
            Integer32,
        etsysEntitySfpSensorRxDdmLastGasp
            Integer32,
        etsysEntitySfpSensorSupportedSpeeds
            Integer32
    }

etsysEntitySfpSensorState OBJECT-TYPE
    SYNTAX       INTEGER {
                   unknown(1),             --  none of the following
                   lowAlarm(2),
                   lowWarning(3),
                   normal(4),
                   highWarning(5),
                   highAlarm(6)
                 }
    MAX-ACCESS   read-only
    STATUS       current
    DESCRIPTION
        "This object indicates the state of the SFP sensor."
    ::= { etsysEntitySfpSensorExtEntry 1 }

etsysEntitySfpSensorHighAlarm OBJECT-TYPE
    SYNTAX        EntitySensorValue
    MAX-ACCESS    read-only
    STATUS        current
    DESCRIPTION
        "The threshold value above which the sensor reading
         indicates an alarm state.

         To correctly interpret the value of this object, the
         associated entPhySensorType, entPhySensorScale, and
         entPhySensorPrecision objects must also be examined."
    ::= { etsysEntitySfpSensorExtEntry 2 }

etsysEntitySfpSensorHighWarning OBJECT-TYPE
    SYNTAX        EntitySensorValue
    MAX-ACCESS    read-only
    STATUS        current
    DESCRIPTION
        "The threshold value above which the sensor reading
         indicates a warning state, if it is below or equal the
         hi alarm value.

         To correctly interpret the value of this object, the
         associated entPhySensorType, entPhySensorScale, and
         entPhySensorPrecision objects must also be examined."
    ::= { etsysEntitySfpSensorExtEntry 3 }

etsysEntitySfpSensorLowWarning OBJECT-TYPE
    SYNTAX        EntitySensorValue
    MAX-ACCESS    read-only
    STATUS        current
    DESCRIPTION
        "The threshold value below which the sensor reading
         indicates a warning state, if it is above or equal the
         lo alarm value.

         To correctly interpret the value of this object, the
         associated entPhySensorType, entPhySensorScale, and
         entPhySensorPrecision objects must also be examined."
    ::= { etsysEntitySfpSensorExtEntry 4 }

etsysEntitySfpSensorLowAlarm OBJECT-TYPE
    SYNTAX        EntitySensorValue
    MAX-ACCESS    read-only
    STATUS        current
    DESCRIPTION
        "The threshold value below which the sensor reading
         indicates an alarm state.

         To correctly interpret the value of this object, the
         associated entPhySensorType, entPhySensorScale, and
         entPhySensorPrecision objects must also be examined."
    ::= { etsysEntitySfpSensorExtEntry 5 }

etsysEntitySfpSensorWavelength OBJECT-TYPE
    SYNTAX        Integer32 (0..65535)
    MAX-ACCESS    read-only
    STATUS        current
    DESCRIPTION
        "This object indicates nominal transmitter output wavelength
         at room temperature.  It is expressed in nano-meters."
    ::= { etsysEntitySfpSensorExtEntry 6 }

etsysEntitySfpSensorPowerOnCounter OBJECT-TYPE
    SYNTAX        Counter32
    MAX-ACCESS    read-only
    STATUS        current
    DESCRIPTION
        "This object indicates the power-on counter.  Host increments
         it by 1 every 48 hours."
    ::= { etsysEntitySfpSensorExtEntry 7 }

etsysEntitySfpSensorTxDdm OBJECT-TYPE
    SYNTAX        Integer32
    MAX-ACCESS    read-only
    STATUS        current
    DESCRIPTION
        "This value represents the Tx dB from low alarm. Host sets
         it once only, after the first 48 consecutive hours of operation.
         Update only if Tx_disable is not active."
    ::= { etsysEntitySfpSensorExtEntry 8 }

etsysEntitySfpSensorTxDdmLastGasp OBJECT-TYPE
    SYNTAX        Integer32
    MAX-ACCESS    read-only
    STATUS        current
    DESCRIPTION
        "This value represents the last gasp of Tx dB from low alarm.
         Host updates it every 48 hours. Update only if Tx_disable is
         not active."
    ::= { etsysEntitySfpSensorExtEntry 9 }

etsysEntitySfpSensorRxDdm OBJECT-TYPE
    SYNTAX        Integer32
    MAX-ACCESS    read-only
    STATUS        current
    DESCRIPTION
        "This value represents the Rx dB from low alarm. Host sets
         it after the first 48 consecutive hours of operation since
         PMD power cycle. Update only if Rx_LOS is not asserted."
    ::= { etsysEntitySfpSensorExtEntry 10 }

etsysEntitySfpSensorRxDdmLastGasp OBJECT-TYPE
    SYNTAX        Integer32
    MAX-ACCESS    read-only
    STATUS        current
    DESCRIPTION
        "This value represents the last gasp of Rx dB from low alarm.
         Host updates it every 48 hours. Update only if Rx_LOS is
         not asserted."
    ::= { etsysEntitySfpSensorExtEntry 11 }

etsysEntitySfpSensorSupportedSpeeds OBJECT-TYPE
    SYNTAX        Integer32
    MAX-ACCESS    read-only
    STATUS        current
    DESCRIPTION
        "This value represents the set of speeds supported
         by transceivers present in the platform.  For each
         speed capability, 2 raised to the power noted below
         is added to the sum.  The unit for speed capability
         is 1 Mbps.

         For example, a transceiver that supports 10G would
         have a value of (2**6) or 64.  In contrast, a transceiver
         that supports both 1G and 10G would have a value of
         ((2**3) + (2**6)) or 72.

         Power  Capability
           0      other or unknown
           1      10
           2      100
           3      1000
           4      2500
           5      5000
           6      10000
           7      20000
           8      25000
           9      40000
          10      50000
          11      100000
          12      400000"
    ::= { etsysEntitySfpSensorExtEntry 12 }

etsysEntitySfpSensorTrapEnable OBJECT-TYPE
    SYNTAX       EnabledStatus
    MAX-ACCESS   read-write
    STATUS       current
    DESCRIPTION
        "This object indicates whether an etsysEntitySfpSensorStateChng
         notification will be sent when the sensor state changes as
         defined by etsysEntitySfpSensorState."
    DEFVAL      { enabled }
    ::= { etsysEntitySfpSensorExt 2 }

-- -------------------------------------------------------------
-- The Entity Temperature Sensor Extension Notification Group
-- -------------------------------------------------------------

etsysEntityTempSensorStateChng NOTIFICATION-TYPE
    OBJECTS { etsysEntityTempSensorState, entPhySensorOperStatus,
              entPhySensorScale, entPhySensorPrecision,
              entPhySensorValue, entPhySensorUnitsDisplay }
    STATUS        current
    DESCRIPTION
        "An etsysEntityTempSensorStateChng trap signifies that the
         SNMP entity, acting in an agent role, has detected the
         transition of etsysEntityTempSensorState from one
         enumerated state to another.  It is RECOMMENDED that devices
         implementing this trap optionally varbind the entPhysicalName
         and entPhysicalDescr objects for this sensor."
    ::= { etsysEntitySensorExtNotifications 1 }

-- -------------------------------------------------------------
-- The Entity Sfp Sensor Extension Notification Group
-- -------------------------------------------------------------

etsysEntitySfpSensorStateChng NOTIFICATION-TYPE
    OBJECTS { etsysEntitySfpSensorState, entPhySensorOperStatus,
              entPhySensorScale, entPhySensorPrecision,
              entPhySensorValue, entPhySensorUnitsDisplay }
    STATUS        current
    DESCRIPTION
        "An etsysEntitySfpSensorStateChng trap signifies that the
         SNMP entity, acting in an agent role, has detected the
         transition of etsysEntitySfpSensorState from one
         enumerated state to another.  It is RECOMMENDED that devices
         implementing this trap optionally varbind the entPhysicalName
         and entPhysicalDescr objects for this sensor."
    ::= { etsysEntitySensorExtNotifications 2 }

-- -------------------------------------------------------------
-- Conformance Information
-- -------------------------------------------------------------

etsysEntitySensorExtConformance OBJECT IDENTIFIER
    ::= { etsysEntitySensorExtMIB 2 }

etsysEntitySensorExtGroups      OBJECT IDENTIFIER
    ::= { etsysEntitySensorExtConformance 1 }

etsysEntitySensorExtCompliances OBJECT IDENTIFIER
    ::= { etsysEntitySensorExtConformance 2 }


-- -------------------------------------------------------------
-- Units of conformance
-- -------------------------------------------------------------

etsysEntityTempSensorGroup OBJECT-GROUP
    OBJECTS {
        etsysEntityTempSensorState,
        etsysEntityTempSensorHotTemp,
        etsysEntityTempSensorWarmTemp,
        etsysEntityTempSensorCoolTemp,
        etsysEntityTempSensorColdTemp,
        etsysEntityTempSensorTrapEnable
    }
    STATUS        current
    DESCRIPTION
        "The group that controls and reports per temperature sensor
         extensions."
    ::= { etsysEntitySensorExtGroups 1 }

etsysEntityTempSensorNotificationGroup NOTIFICATION-GROUP
    NOTIFICATIONS {
        etsysEntityTempSensorStateChng
    }
    STATUS        current
    DESCRIPTION
        "The group of per temperature sensor notifications for Entity
         Sensor Extensions."
    ::= { etsysEntitySensorExtGroups 2 }

etsysEntitySfpSensorGroup OBJECT-GROUP
    OBJECTS {
        etsysEntitySfpSensorState,
        etsysEntitySfpSensorHighAlarm,
        etsysEntitySfpSensorHighWarning,
        etsysEntitySfpSensorLowWarning,
        etsysEntitySfpSensorLowAlarm,
        etsysEntitySfpSensorWavelength,
        etsysEntitySfpSensorPowerOnCounter,
        etsysEntitySfpSensorTxDdm,
        etsysEntitySfpSensorTxDdmLastGasp,
        etsysEntitySfpSensorRxDdm,
        etsysEntitySfpSensorRxDdmLastGasp,
        etsysEntitySfpSensorSupportedSpeeds,
        etsysEntitySfpSensorTrapEnable
    }
    STATUS        current
    DESCRIPTION
        "The group that controls and reports per SFP sensor
         extensions."
    ::= { etsysEntitySensorExtGroups 3 }

etsysEntitySfpSensorNotificationGroup NOTIFICATION-GROUP
    NOTIFICATIONS {
        etsysEntitySfpSensorStateChng
    }
    STATUS        current
    DESCRIPTION
        "The group of per SFP sensor notifications for Entity
         Sensor Extensions."
    ::= { etsysEntitySensorExtGroups 4 }

-- -------------------------------------------------------------
-- Compliance statements
-- -------------------------------------------------------------

etsysEntitySensorExtCompliance MODULE-COMPLIANCE
    STATUS     current
    DESCRIPTION
        "The compliance statement for devices that support per temperature
         sensor extensions."

    MODULE
        MANDATORY-GROUPS { etsysEntityTempSensorGroup }

        GROUP       etsysEntityTempSensorNotificationGroup
        DESCRIPTION
            "This group is mandatory for all devices that support per
             temperature sensor state change notifications."

        OBJECT      etsysEntityTempSensorTrapEnable
        MIN-ACCESS  read-only
        DESCRIPTION
            "Write access is not required."
    ::= { etsysEntitySensorExtCompliances 1 }

etsysEntitySensorSfpExtCompliance MODULE-COMPLIANCE
    STATUS     current
    DESCRIPTION
        "The compliance statement for devices that support per SFP
         sensor extensions."

    MODULE
        MANDATORY-GROUPS { etsysEntitySfpSensorGroup }

        GROUP       etsysEntitySfpSensorNotificationGroup
        DESCRIPTION
            "This group is mandatory for all devices that support per
             SFP sensor state change notifications."

        OBJECT      etsysEntitySfpSensorTrapEnable
        MIN-ACCESS  read-only
        DESCRIPTION
            "Write access is not required."
    ::= { etsysEntitySensorExtCompliances 2 }

END
